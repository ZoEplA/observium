--
-- HUAWEI-SWITCH-L2MAM-EXT-MIB.mib
-- MIB generated by MG-SOFT Visual MIB Builder Version 4.0 Build 347
-- Wednesday, March 19, 2014 at 14:06:58 

--  ===================================================================
-- Copyright (C) 2014 by HUAWEI TECHNOLOGIES. All rights reserved.
-- Description:
-- Reference:
-- Version: V1.04
-- ===================================================================

	HUAWEI-SWITCH-L2MAM-EXT-MIB DEFINITIONS ::= BEGIN
 
		IMPORTS
			entPhysicalName			
				FROM ENTITY-MIB			
			hwBaseTrapSeverity, hwBaseTrapProbableCause, hwBaseTrapEventType			
				FROM HUAWEI-BASE-TRAP-MIB			
			hwCfgFdbMac, hwCfgFdbVlanId, hwMacEntityUsage, hwMacEntityUsageThreshold, hwPortSecurityProtectAction, hwCfgFdbVsiName			
				FROM HUAWEI-L2MAM-MIB			
			hwDatacomm			
				FROM HUAWEI-MIB			
			ifDescr, InterfaceIndex			
				FROM IF-MIB			
			OBJECT-GROUP, MODULE-COMPLIANCE, NOTIFICATION-GROUP			
				FROM SNMPv2-CONF			
			Integer32, OBJECT-TYPE, MODULE-IDENTITY, NOTIFICATION-TYPE			
				FROM SNMPv2-SMI;
	
	
		-- 1.3.6.1.4.1.2011.5.25.315
		hwSWITCH-L2MAM-EXT MODULE-IDENTITY 
			LAST-UPDATED "201403261600Z"		-- March 26, 2014 at 16:00 GMT
			ORGANIZATION 
				"Huawei Technologies Co.,Ltd."
			CONTACT-INFO 
				"Huawei Industrial Base
				Bantian, Longgang
				 Shenzhen 518129
				 People's Republic of China
				 Website: http://www.huawei.com
				 Email: support@huawei.com"
			DESCRIPTION 
				"THIS IS THE LAYER 2 MAC-ADDRESS MANAGEMENT MIB."

                                                    REVISION "201403261600Z" 
                                                    DESCRIPTION 
                                                    "Modify code hwMacTrapPortCfgAlarm" 

                                                    REVISION "201403261600Z" 
                                                    DESCRIPTION 
                                                    "Modify code hwMacTrapHashConflictAlarm " 

                                                       REVISION "201403191600Z" 
                                                       DESCRIPTION 
                                                      "Edit the mib file by OM stard guide" 

                                                       REVISION "201402141600Z" 
                                                       DESCRIPTION 
                                                      "Add code hwMacTrapPortCfgAlarm" 

			REVISION "200406080000Z"		-- June 08, 2004 at 00:00 GMT
			DESCRIPTION 
				"
				V1.00, Inital version.
				"
			REVISION "199610310000Z"		-- October 31, 1996 at 00:00 GMT
			DESCRIPTION 
				"Initial version (version 1), published as
				RFC 2037."
			REVISION "199912070000Z"		-- December 07, 1999 at 00:00 GMT
			DESCRIPTION 
				"Initial Version of Entity MIB (Version 2).
				This revision obsoletes RFC 2037.
				This version published as RFC 2737."
			REVISION "200406080000Z"		-- June 08, 2004 at 00:00 GMT
			DESCRIPTION 
				"
				V1.00, Inital version.
				"
			REVISION "200406080000Z"		-- June 08, 2004 at 00:00 GMT
			DESCRIPTION 
				"
				V1.00, Inital version.
				"
			REVISION "199610310000Z"		-- October 31, 1996 at 00:00 GMT
			DESCRIPTION 
				"Initial version (version 1), published as
				RFC 2037."
			REVISION "199912070000Z"		-- December 07, 1999 at 00:00 GMT
			DESCRIPTION 
				"Initial Version of Entity MIB (Version 2).
				This revision obsoletes RFC 2037.
				This version published as RFC 2737."
			REVISION "200406080000Z"		-- June 08, 2004 at 00:00 GMT
			DESCRIPTION 
				"
				V1.00, Inital version.
				"
			REVISION "199610310000Z"		-- October 31, 1996 at 00:00 GMT
			DESCRIPTION 
				"Initial version (version 1), published as
				RFC 2037."
			REVISION "199912070000Z"		-- December 07, 1999 at 00:00 GMT
			DESCRIPTION 
				"Initial Version of Entity MIB (Version 2).
				This revision obsoletes RFC 2037.
				This version published as RFC 2737."
			REVISION "199610310000Z"		-- October 31, 1996 at 00:00 GMT
			DESCRIPTION 
				"Initial version (version 1), published as
				RFC 2037."
			REVISION "199912070000Z"		-- December 07, 1999 at 00:00 GMT
			DESCRIPTION 
				"Initial Version of Entity MIB (Version 2).
				This revision obsoletes RFC 2037.
				This version published as RFC 2737."
			REVISION "200406080000Z"		-- June 08, 2004 at 00:00 GMT
			DESCRIPTION 
				"
				V1.00, Inital version.
				"
			REVISION "200406080000Z"		-- June 08, 2004 at 00:00 GMT
			DESCRIPTION 
				"
				V1.00, Inital version.
				"
			REVISION "200406080000Z"		-- June 08, 2004 at 00:00 GMT
			DESCRIPTION 
				"
				V1.00, Inital version.
				"
			REVISION "201008111600Z"		-- August 11, 2010 at 16:00 GMT
			DESCRIPTION 
				"V1.00, initial version."
			REVISION "201402141600Z"		-- February 14, 2014 at 16:00 GMT
			DESCRIPTION 
				"Add code hwMacTrapPortCfgAlarm"
			::= { hwDatacomm 315 }

		
	
	
--
-- Node definitions
--
	
		-- 1.3.6.1.4.1.2011.5.25.315.1
		hwSwitchL2MamExtObjects OBJECT IDENTIFIER ::= { hwSWITCH-L2MAM-EXT 1 }

		
		-- 1.3.6.1.4.1.2011.5.25.315.1.1
		hwMacTrapPortCfgTable OBJECT-TYPE
			SYNTAX SEQUENCE OF HwMacTrapPortCfgEntry
			MAX-ACCESS not-accessible
			STATUS current
			DESCRIPTION
				"The mac-trap Table.The table that contains the mac-trap information currently operating on this device."
			::= { hwSwitchL2MamExtObjects 1 }

		
		-- 1.3.6.1.4.1.2011.5.25.315.1.1.1
		hwMacTrapPortCfgEntry OBJECT-TYPE
			SYNTAX HwMacTrapPortCfgEntry
			MAX-ACCESS not-accessible
			STATUS current
			DESCRIPTION
				"Entries of the mac-trap table."
			INDEX { hwMacTrapPortCfgIfIndex }
			::= { hwMacTrapPortCfgTable 1 }

		
		HwMacTrapPortCfgEntry ::=
			SEQUENCE { 
				hwMacTrapPortCfgIfIndex
					InterfaceIndex,
				hwMacTrapPortCfgLearn
					INTEGER,
				hwMacTrapPortCfgAging
					INTEGER
			 }

		-- 1.3.6.1.4.1.2011.5.25.315.1.1.1.1
		hwMacTrapPortCfgIfIndex OBJECT-TYPE
			SYNTAX InterfaceIndex
			MAX-ACCESS not-accessible
			STATUS current
			DESCRIPTION
				"The IfIndex which will be configured mac-trap."
			::= { hwMacTrapPortCfgEntry 1 }

		
		-- 1.3.6.1.4.1.2011.5.25.315.1.1.1.2
		hwMacTrapPortCfgLearn OBJECT-TYPE
			SYNTAX INTEGER
				{
				enable(1),
				disable(2)
				}
			MAX-ACCESS read-write
			STATUS current
			DESCRIPTION
				"The alarm switch of the new mac. The meanings of the values are: enable(1),disanle(2)."
			::= { hwMacTrapPortCfgEntry 2 }

		
		-- 1.3.6.1.4.1.2011.5.25.315.1.1.1.3
		hwMacTrapPortCfgAging OBJECT-TYPE
			SYNTAX INTEGER
				{
				enable(1),
				disable(2)
				}
			MAX-ACCESS read-write
			STATUS current
			DESCRIPTION
				"The alarm switch of the delete mac. The meanings of the values are: enable(1),disanle(2)."
			::= { hwMacTrapPortCfgEntry 3 }

		
		-- 1.3.6.1.4.1.2011.5.25.315.2
		hwSwitchL2MamExtGeneralObjects OBJECT IDENTIFIER ::= { hwSWITCH-L2MAM-EXT 2 }

		
		-- 1.3.6.1.4.1.2011.5.25.315.2.1
		hwMacTrapInterval OBJECT-TYPE
			SYNTAX Integer32
			MAX-ACCESS read-write
			STATUS current
			DESCRIPTION
				"The interval of trap the mac change."
			::= { hwSwitchL2MamExtGeneralObjects 1 }

		
		-- 1.3.6.1.4.1.2011.5.25.315.2.2
		hwMacTrapMacInfo OBJECT-TYPE
			SYNTAX OCTET STRING
			MAX-ACCESS accessible-for-notify
			STATUS current
			DESCRIPTION
				"The information of mac-trap."
			::= { hwSwitchL2MamExtGeneralObjects 2 }

		
		-- 1.3.6.1.4.1.2011.5.25.315.3
		hwSwitchL2MamExtTraps OBJECT IDENTIFIER ::= { hwSWITCH-L2MAM-EXT 3 }

		
		-- 1.3.6.1.4.1.2011.5.25.315.3.1
		hwMacTrapAlarm NOTIFICATION-TYPE
			OBJECTS { hwMacTrapMacInfo }
			STATUS current
			DESCRIPTION 
				"The trap when mac-address is learned or aging."
			::= { hwSwitchL2MamExtTraps 1 }

		
		-- 1.3.6.1.4.1.2011.5.25.315.3.2
		hwPortVlanSecureMacAlarm NOTIFICATION-TYPE
			OBJECTS { ifDescr, hwCfgFdbMac, hwCfgFdbVlanId, hwPortSecurityProtectAction }
			STATUS current
			DESCRIPTION 
				"The alarm when MAC addresses that received are illegal
				
				"
			::= { hwSwitchL2MamExtTraps 2 }

		
		-- 1.3.6.1.4.1.2011.5.25.315.3.3
		hwSlotMacUsageRaisingThreshold NOTIFICATION-TYPE
			OBJECTS { hwBaseTrapEventType, hwBaseTrapSeverity, hwBaseTrapProbableCause, hwMacEntityUsage, hwMacEntityUsageThreshold, 
				entPhysicalName }
			STATUS current
			DESCRIPTION 
				"This notification indicates the MAC usage of the slot raising the threshold
				"
			::= { hwSwitchL2MamExtTraps 3 }

		
		-- 1.3.6.1.4.1.2011.5.25.315.3.4
		hwSlotMacUsageFallingThreshold NOTIFICATION-TYPE
			OBJECTS { hwBaseTrapEventType, hwBaseTrapSeverity, hwBaseTrapProbableCause, entPhysicalName }
			STATUS current
			DESCRIPTION 
				"This notification indicates the MAC usage of the slot falling the threshold
				"
			::= { hwSwitchL2MamExtTraps 4 }

		
		-- 1.3.6.1.4.1.2011.5.25.315.3.5
		hwMacTrapPortCfgAlarm NOTIFICATION-TYPE
			OBJECTS { hwMacTrapMacInfo, hwCfgFdbMac, hwCfgFdbVlanId, ifDescr }
			STATUS current
			DESCRIPTION 
				"The trap when mac-address is learned or aging."
			::= { hwSwitchL2MamExtTraps 5 }


		-- 1.3.6.1.4.1.2011.5.25.315.3.6
		hwMacTrapHashConflictAlarm NOTIFICATION-TYPE
			OBJECTS { ifDescr,hwCfgFdbMac, hwCfgFdbVlanId ,hwCfgFdbVsiName}
			STATUS current
			DESCRIPTION 
				"This notification indicates that MAC address hash conflict occurred."
			::= { hwSwitchL2MamExtTraps 6 }

		
		-- 1.3.6.1.4.1.2011.5.25.315.4
		hwSwitchL2MamExtConformance OBJECT IDENTIFIER ::= { hwSWITCH-L2MAM-EXT 4 }

		
		-- 1.3.6.1.4.1.2011.5.25.315.4.1
		hwSwitchL2MamExtCompliances OBJECT IDENTIFIER ::= { hwSwitchL2MamExtConformance 1 }

		
		-- 1.3.6.1.4.1.2011.5.25.315.4.1.1
		hwSwitchL2MamExtFullCompliance MODULE-COMPLIANCE
			STATUS current
			DESCRIPTION 
				"hwSwitchL2MamExtFullCompliance"
			MODULE HwSWITCH-L2MAM-EXT
				MANDATORY-GROUPS { hwMacTrapGroups, hwL2MAMExtGeneralGrops, hwL2MAMExtTrapGroup }
			::= { hwSwitchL2MamExtCompliances 1 }

		
		-- 1.3.6.1.4.1.2011.5.25.315.4.2
		hwSwitchL2MamExtGroups OBJECT IDENTIFIER ::= { hwSwitchL2MamExtConformance 2 }

		
		-- 1.3.6.1.4.1.2011.5.25.315.4.2.1
		hwMacTrapGroups OBJECT-GROUP
			OBJECTS { hwMacTrapPortCfgLearn, hwMacTrapPortCfgAging }
			STATUS current
			DESCRIPTION 
				"A collection of objects providing information about mac trap table."
			::= { hwSwitchL2MamExtGroups 1 }

		
		-- 1.3.6.1.4.1.2011.5.25.315.4.2.2
		hwL2MAMExtGeneralGrops OBJECT-GROUP
			OBJECTS { hwMacTrapInterval, hwMacTrapMacInfo }
			STATUS current
			DESCRIPTION 
				"A collection of objects providing information about  Mac addresses."
			::= { hwSwitchL2MamExtGroups 2 }

		
		-- 1.3.6.1.4.1.2011.5.25.315.4.2.3
		hwL2MAMExtTrapGroup NOTIFICATION-GROUP
			NOTIFICATIONS { hwMacTrapAlarm, hwMacTrapPortCfgAlarm, hwPortVlanSecureMacAlarm, hwSlotMacUsageFallingThreshold, hwSlotMacUsageRaisingThreshold, hwMacTrapHashConflictAlarm 
				 }
			STATUS current
			DESCRIPTION 
				"The trap enable group."
			::= { hwSwitchL2MamExtGroups 3 }

		
	
	END

--
-- HUAWEI-SWITCH-L2MAM-EXT-MIB.mib
--
