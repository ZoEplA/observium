-- ***************************************************************************
-- ***************************************************************************
--
-- File         : chkpnt-gaia-traps.mib
-- Description  : Check Point traps
--
--
--
-- ***************************************************************************
-- ***************************************************************************

CHECKPOINT-GAIA-TRAP-MIB DEFINITIONS ::= BEGIN

        -- SUBTREE: 1.3.6.1.4.1.2620.1
        -- iso.org.dod.internet.private.enterprises.checkpoint.products

		IMPORTS
			MODULE-IDENTITY, OBJECT-TYPE, NOTIFICATION-TYPE, enterprises
				FROM SNMPv2-SMI
			NOTIFICATION-GROUP
				FROM SNMPv2-CONF
			DisplayString
				FROM SNMPv2-TC
			tempertureSensorName,tempertureSensorValue,fanSpeedSensorName,fanSpeedSensorValue,voltageSensorName,voltageSensorValue, powerSupplyIndex, powerSupplyStatus
					FROM CHECKPOINT-MIB
			raidVolumeState,raidVolumeFlags
					FROM CHECKPOINT-MIB;
chkpntTrapMibModule MODULE-IDENTITY
LAST-UPDATED "201005101431Z"
ORGANIZATION
	"Check Point"
CONTACT-INFO
	"Check Point"
DESCRIPTION
	"Check Point GAIA SMIv2 Traps"
REVISION "201005101431Z"
DESCRIPTION
	"The initial version"
::= { chkpntTrapInfo 0 }

            

        chkpntTrapOID  OBJECT-TYPE   
                       SYNTAX  DisplayString
                       MAX-ACCESS  read-only
                       STATUS  current
                       DESCRIPTION
                       "The trap OID that triggered this event."
                       ::= { chkpntTrapInfo 10 } 

        chkpntTrapMsgText  OBJECT-TYPE
                       SYNTAX  DisplayString
                       MAX-ACCESS  read-only
                       STATUS  current
                       DESCRIPTION
                       "Alert Message Text"
                       ::= { chkpntTrapInfo 12 }

        tempertureSensorName  OBJECT-TYPE
                       SYNTAX  DisplayString
                       MAX-ACCESS  read-only
                       STATUS  current
                       DESCRIPTION
                       "Temperature sensor name"
                       ::= { tempertureSensorEntry 2 }
					   
        tempertureSensorValue  OBJECT-TYPE
                       SYNTAX  DisplayString
                       MAX-ACCESS  read-only
                       STATUS  current
                       DESCRIPTION
                       "Temperature sensor value"
                       ::= { tempertureSensorEntry 3 }
			
        fanSpeedSensorName  OBJECT-TYPE   
                       SYNTAX  DisplayString
                       MAX-ACCESS  read-only
                       STATUS  current
                       DESCRIPTION
                       "Fan sensor name."
                       ::= { fanSpeedSensorEntry 2 }
 
        fanSpeedSensorValue  OBJECT-TYPE
                       SYNTAX  DisplayString
                       MAX-ACCESS  read-only
                       STATUS  current
                       DESCRIPTION
                       "Fan sensor value."
                       ::= { fanSpeedSensorEntry 3 }

		voltageSensorName  OBJECT-TYPE   
                       SYNTAX  DisplayString
                       MAX-ACCESS  read-only
                       STATUS  current
                       DESCRIPTION
                       "Voltage sensor name."
                       ::= { voltageSensorEntry 2 } 

        voltageSensorValue  OBJECT-TYPE
                       SYNTAX  DisplayString
                       MAX-ACCESS  read-only
                       STATUS  current
                       DESCRIPTION
                       "Voltage sensor value."
                       ::= { voltageSensorEntry 3 }
					  
		powerSupplyIndex  OBJECT-TYPE   
                       SYNTAX  DisplayString
                       MAX-ACCESS  read-only
                       STATUS  current
                       DESCRIPTION
                       "Power supply sensor name."
                       ::= { powerSupplyEntry 2 } 

        powerSupplyStatus  OBJECT-TYPE
                       SYNTAX  DisplayString
                       MAX-ACCESS  read-only
                       STATUS  current
                       DESCRIPTION
                       "Power supply sensor value."
                       ::= { powerSupplyEntry 3 }					  
					  
        raidVolumeState  OBJECT-TYPE   
                       SYNTAX  DisplayString
                       MAX-ACCESS  read-only
                       STATUS  current
                       DESCRIPTION
                       "RAID volume state for this event."
                       ::= { raidVolumeEntry 6 } 

        raidVolumeFlags  OBJECT-TYPE
                       SYNTAX  DisplayString
                       MAX-ACCESS  read-only
                       STATUS  current
                       DESCRIPTION
                       "RAID volume flags for this event."
                       ::= { raidVolumeEntry 7 }
 
-- textual conventions

    DisplayString ::=
            OCTET STRING
        -- This data type is used to model textual information taken
        -- from the NVT ASCII character set.  By convention, objects
        -- with this syntax are declared as having
        --
        --      SIZE (0..255)

    checkpoint      			OBJECT IDENTIFIER ::= { enterprises 2620 }
	products        			OBJECT IDENTIFIER ::= { checkpoint 1 }
	chkpntTrap      	   		OBJECT IDENTIFIER ::= { products 3000 } 
	chkpntTrapInfo				OBJECT IDENTIFIER ::= { chkpntTrap 0 } 
    chkpntTrapHWSensor			OBJECT IDENTIFIER ::= { chkpntTrap 5 }
	chkpntTrapConfiguration		OBJECT IDENTIFIER ::= { chkpntTrap 10 }
	chkpntTrapDisk				OBJECT IDENTIFIER ::= { chkpntTrap 2 }

	svn							OBJECT IDENTIFIER ::= { products 6 } 
	svnPerf						OBJECT IDENTIFIER ::= { svn 7 }
	sensorInfo					OBJECT IDENTIFIER ::= { svnPerf 8 }
	tempertureSensorTable		OBJECT IDENTIFIER ::= { sensorInfo 1 }
	tempertureSensorEntry		OBJECT IDENTIFIER ::= { tempertureSensorTable 1 }
	fanSpeedSensorTable			OBJECT IDENTIFIER ::= { sensorInfo 2 }
	fanSpeedSensorEntry			OBJECT IDENTIFIER ::= { fanSpeedSensorTable 1 }
	voltageSensorTable			OBJECT IDENTIFIER ::= { sensorInfo 3 }
	voltageSensorEntry			OBJECT IDENTIFIER ::= { voltageSensorTable 1 }
	powerSupplyInfo				OBJECT IDENTIFIER ::= { svnPerf 9 }
	powerSupplyTable			OBJECT IDENTIFIER ::= { powerSupplyInfo 1 }
	powerSupplyEntry			OBJECT IDENTIFIER ::= { powerSupplyTable 1 }
	raidInfo					OBJECT IDENTIFIER ::= { svnPerf 6 }
	raidVolumeTable				OBJECT IDENTIFIER ::= { raidInfo 1 }
	raidVolumeEntry				OBJECT IDENTIFIER ::= { raidVolumeTable 1 }

-- ******************************************
-- HW Sensor Traps
-- ******************************************
    chkpntTrapTempertureSensor	OBJECT IDENTIFIER ::= { chkpntTrapHWSensor 1 }
    chkpntTrapFanSpeedSensor	OBJECT IDENTIFIER ::= { chkpntTrapHWSensor 2 }
    chkpntTrapVoltageSensor		OBJECT IDENTIFIER ::= { chkpntTrapHWSensor 3 }	
	chkpntTrapPowerSupplySensor	OBJECT IDENTIFIER ::= { chkpntTrapHWSensor 4 }	
        	
        	
          chkpntTempertureTrap NOTIFICATION-TYPE
                          OBJECTS
                                {
                                chkpntTrapOID,
                                chkpntTrapMsgText,
                                tempertureSensorName,
                                tempertureSensorValue
                                }
                          STATUS        current 
                          DESCRIPTION
                          "Temperture sensor alert (Sensor name provided in trap)"
                          ::= { chkpntTrapTempertureSensor 1 }
          

          chkpntFanSpeedTrap NOTIFICATION-TYPE
                          OBJECTS
                                {
                                chkpntTrapOID,
                                chkpntTrapMsgText,
                                fanSpeedSensorName,
                                fanSpeedSensorValue
                                }
                          STATUS        current 
                          DESCRIPTION
                          "Fan speed sensor alert (Sensor name provided in trap)"
                          ::= { chkpntTrapFanSpeedSensor 1 }
                          
          chkpntVoltageTrap NOTIFICATION-TYPE
                          OBJECTS
                                {
                                chkpntTrapOID,
                                chkpntTrapMsgText,
                                voltageSensorName,
                                voltageSensorValue
                                }
                          STATUS        current 
                          DESCRIPTION
                          "Voltage sensor alert (Sensor name provided in trap)"
                          ::= { chkpntTrapVoltageSensor 1 }
            
	    chkpntPowerSupplyTrap NOTIFICATION-TYPE
                          OBJECTS
                                {
                                chkpntTrapOID,
                                chkpntTrapMsgText,
                                powerSupplyIndex,
                                powerSupplyStatus
                                }
                          STATUS        current 
                          DESCRIPTION
                          "Power supply sensor alert (Sensor index provided in trap)"
                          ::= { chkpntTrapPowerSupplySensor 1 }
            

-- ******************************************
-- System Configuration Traps
-- ******************************************
          chkpntTrapSystemConfiguration		OBJECT IDENTIFIER ::= { chkpntTrapConfiguration 1 }

	  chkpntSystemConfigurationChangeTrap NOTIFICATION-TYPE
                          OBJECTS
                                {
                                chkpntTrapOID,
                                chkpntTrapMsgText
                                }
                          STATUS        current 
                          DESCRIPTION
                          "System configuration was changed"
                          ::= { chkpntTrapSystemConfiguration 1 }
	
	  chkpntSystemConfigurationSaveTrap NOTIFICATION-TYPE
                          OBJECTS
                                {
                                chkpntTrapOID,
                                chkpntTrapMsgText
                                }
                          STATUS        current 
                          DESCRIPTION
                          "System configuration was saved"
                          ::= { chkpntTrapSystemConfiguration 2 }
	
-- ******************************************
-- RAID Traps
-- ******************************************
          chkpntTrapRAID		OBJECT IDENTIFIER ::= { chkpntTrapDisk 1 }
                           
	  chkpntRAIDVolumeStateTrap NOTIFICATION-TYPE
                          OBJECTS
                                {
                                chkpntTrapOID,
                                chkpntTrapMsgText,
				raidVolumeState,
				raidVolumeFlags
                                }
                          STATUS        current 
                          DESCRIPTION
                          "The RAID volume state is not optimal. Volume state, volume flags, disk state and disk flags are included."
                          ::= { chkpntTrapRAID 1 }
END
