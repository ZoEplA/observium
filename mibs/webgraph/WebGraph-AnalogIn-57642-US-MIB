WebGraph-AnalogIn-57642-US-MIB DEFINITIONS ::= BEGIN
----------------------------------------------------------------
-- Revison: 1.29
----------------------------------------------------------------
-- 22.06.2010 	Webio
--		Syntax correction 
----------------------------------------------------------------
-- Revison: 1.28
----------------------------------------------------------------
-- 02.12.2008 	Webio
--		New Graphics java script base parameter 
----------------------------------------------------------------
-- Revison: 1.27
----------------------------------------------------------------
-- 09.11.2006 	Webio
--		DHCP enable 
----------------------------------------------------------------
-- Revison: 1.26
----------------------------------------------------------------
-- 28.06.2006 	New: Community String Trap
--		
----------------------------------------------------------------
-- Revison: 1.25
----------------------------------------------------------------
-- 26.07.2005 	#57642, WebGraph AnalogIn 2x 0/4..20mA
--
----------------------------------------------------------------
-- Revison: 1.24
----------------------------------------------------------------
-- 26.07.2005 	#57642, WebGraph AnalogIn
--		CRON timer function
----------------------------------------------------------------
-- Revison: 1.23
----------------------------------------------------------------
-- 14.07.2005 	#57642, WebGraph AnalogIn
--		FTP functions
----------------------------------------------------------------
-- Revison: 1.22
----------------------------------------------------------------
-- 17.05.2005 	#57642, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--		     
----------------------------------------------------------------
-- Revison: 1.19
----------------------------------------------------------------
-- 08.09.2004 	#57606 WebGraph Thermo-Hygrometer
--		New: 
--			wtWebGraphThermHygroAlarmRHMin
--			wtWebGraphThermHygroAlarmRHMax
--			wtWebGraphThermHygroAlarmRHHysteresis
--			wtWebGraphThermHygroPortSensorSelect
--			wtWebGraphThermHygroAlarmDeltaTemp		
--			wtWebGraphThermHygroAlarmAHMin		
--			wtWebGraphThermHygroAlarmAHMax		
----------------------------------------------------------------
-- Revison: 1.18
----------------------------------------------------------------
-- 21.07.2004 	#57601/3/4, Webio Anx
--		New: 
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                			OBJECT IDENTIFIER ::= { enterprises 5040 }
    wtComServer        			OBJECT IDENTIFIER ::= { wut 1 }
    wtWebio            			OBJECT IDENTIFIER ::= { wtComServer 2 }

--  wtWebGraph Tree

    wtWebGraphAnalogIn57642  		OBJECT IDENTIFIER ::= { wtWebio 11 }
    
--  wtWebGraphAnalogIn57642 Tree

    wtWebGraphAnalogIn57642Inventory    OBJECT IDENTIFIER ::= { wtWebGraphAnalogIn57642 1 }
    wtWebGraphAnalogIn57642SessCntrl 	OBJECT IDENTIFIER ::= { wtWebGraphAnalogIn57642 2 }
    wtWebGraphAnalogIn57642Config    	OBJECT IDENTIFIER ::= { wtWebGraphAnalogIn57642 3 }
    wtWebGraphAnalogIn57642Diag    	OBJECT IDENTIFIER ::= { wtWebGraphAnalogIn57642 4 }
    
--  wtWebGraphAnalogIn57642Config Tree

    wtWebGraphAnalogIn57642Device    	OBJECT IDENTIFIER ::= { wtWebGraphAnalogIn57642Config 1 }
    wtWebGraphAnalogIn57642Ports     	OBJECT IDENTIFIER ::= { wtWebGraphAnalogIn57642Config 2 }	
    wtWebGraphAnalogIn57642Manufact  	OBJECT IDENTIFIER ::= { wtWebGraphAnalogIn57642Config 3 }	

--  wtWebGraphAnalogIn57642Device Tree

    wtWebGraphAnalogIn57642Text		OBJECT IDENTIFIER ::= { wtWebGraphAnalogIn57642Device 1 }	
    wtWebGraphAnalogIn57642TimeDate 	OBJECT IDENTIFIER ::= { wtWebGraphAnalogIn57642Device 2 }
    wtWebGraphAnalogIn57642Basic	OBJECT IDENTIFIER ::= { wtWebGraphAnalogIn57642Device 3 }	
    wtWebGraphAnalogIn57642Datalogger	OBJECT IDENTIFIER ::= { wtWebGraphAnalogIn57642Device 4 }	
    wtWebGraphAnalogIn57642Alarm	OBJECT IDENTIFIER ::= { wtWebGraphAnalogIn57642Device 5 }
    wtWebGraphAnalogIn57642Graphics 	OBJECT IDENTIFIER ::= { wtWebGraphAnalogIn57642Device 6 }	
    
--  wtWebGraphAnalogIn57642TimeDate Tree

    wtWebGraphAnalogIn57642TimeZone	OBJECT IDENTIFIER ::= { wtWebGraphAnalogIn57642TimeDate 1 }
    wtWebGraphAnalogIn57642TimeServer	OBJECT IDENTIFIER ::= { wtWebGraphAnalogIn57642TimeDate 2 }	
    wtWebGraphAnalogIn57642DeviceClock	OBJECT IDENTIFIER ::= { wtWebGraphAnalogIn57642TimeDate 3 }

--  wtWebGraphAnalogIn57642Basic Tree
    
    wtWebGraphAnalogIn57642Network	OBJECT IDENTIFIER ::= { wtWebGraphAnalogIn57642Basic 1 }
    wtWebGraphAnalogIn57642HTTP		OBJECT IDENTIFIER ::= { wtWebGraphAnalogIn57642Basic 2 }
    wtWebGraphAnalogIn57642Mail		OBJECT IDENTIFIER ::= { wtWebGraphAnalogIn57642Basic 3 }	
    wtWebGraphAnalogIn57642SNMP		OBJECT IDENTIFIER ::= { wtWebGraphAnalogIn57642Basic 4 }
    wtWebGraphAnalogIn57642UDP		OBJECT IDENTIFIER ::= { wtWebGraphAnalogIn57642Basic 5 }
    wtWebGraphAnalogIn57642Syslog	OBJECT IDENTIFIER ::= { wtWebGraphAnalogIn57642Basic 6 }
    wtWebGraphAnalogIn57642FTP		OBJECT IDENTIFIER ::= { wtWebGraphAnalogIn57642Basic 7 }

--  wtWebGraphAnalogIn57641Graphics Tree
    
    wtWebGraphAnalogIn57642GraphicsBase 	OBJECT IDENTIFIER ::= { wtWebGraphAnalogIn57641Graphics 1 }
    wtWebGraphAnalogIn57642GraphicsSelect 	OBJECT IDENTIFIER ::= { wtWebGraphAnalogIn57641Graphics 2 }
    wtWebGraphAnalogIn57642GraphicsScale 	OBJECT IDENTIFIER ::= { wtWebGraphAnalogIn57641Graphics 3 }
    
       
-- wtWebGraphAnalogIn57642Inventory Group
------------------------

wtWebGraphAnalogIn57642Sensors OBJECT-TYPE
    SYNTAX INTEGER (1..2)
    ACCESS read-only
    STATUS mandatory
    DESCRIPTION
        "Number of sensors"
    ::= { wtWebGraphAnalogIn57642Inventory 1 }

-- Interface Table

wtWebGraphAnalogIn57642SensorTable OBJECT-TYPE
    SYNTAX SEQUENCE OF WtWebGraphAnalogIn57642SensorEntry
    ACCESS not-accessible
    STATUS mandatory
    DESCRIPTION
        "List of sensors."
    ::= { wtWebGraphAnalogIn57642Inventory 2 }

wtWebGraphAnalogIn57642SensorEntry OBJECT-TYPE
    SYNTAX WtWebGraphAnalogIn57642SensorEntry
    ACCESS not-accessible
    STATUS mandatory
    DESCRIPTION
        "List of sensor numbers."
    INDEX  { wtWebGraphAnalogIn57642SensorNo }
    ::= { wtWebGraphAnalogIn57642SensorTable 1 }

WtWebGraphAnalogIn57642SensorEntry ::= SEQUENCE {
    wtWebGraphAnalogIn57642SensorNo INTEGER
}

wtWebGraphAnalogIn57642SensorNo OBJECT-TYPE
    SYNTAX INTEGER (1..2)
    ACCESS read-only
    STATUS mandatory
    DESCRIPTION
        "Sensor number."
    ::= { wtWebGraphAnalogIn57642SensorEntry 1 }


-- wtWebGraphAnalogIn57642Values Table

wtWebGraphAnalogIn57642ValuesTable OBJECT-TYPE
    SYNTAX SEQUENCE OF WtWebGraphAnalogIn57642ValuesEntry
    ACCESS not-accessible
    STATUS mandatory
    DESCRIPTION
        "List of measurement values corresponding to the channel numbers."
    ::= { wtWebGraphAnalogIn57642Inventory 3 }

wtWebGraphAnalogIn57642ValuesEntry OBJECT-TYPE
    SYNTAX WtWebGraphAnalogIn57642ValuesEntry
    ACCESS not-accessible
    STATUS mandatory
    DESCRIPTION
        "Measurement values of the sensors."
    INDEX  { wtWebGraphAnalogIn57642SensorNo }
    ::= { wtWebGraphAnalogIn57642ValuesTable 1 }

WtWebGraphAnalogIn57642ValuesEntry ::= SEQUENCE{
    wtWebGraphAnalogIn57642Values OCTET STRING
}

wtWebGraphAnalogIn57642Values OBJECT-TYPE
    SYNTAX OCTET STRING (SIZE (5))
    ACCESS read-only
    STATUS mandatory
    DESCRIPTION
        "Measurement value of the sensor, ASCII, 7 characters in length."
    ::= { wtWebGraphAnalogIn57642ValuesEntry 1 }

-- wtWebGraphAnalogIn57642BinaryValues Table

wtWebGraphAnalogIn57642BinaryValuesTable OBJECT-TYPE
    SYNTAX SEQUENCE OF WtWebGraphAnalogIn57642BinaryValuesEntry
    ACCESS not-accessible
    STATUS mandatory
    DESCRIPTION
        "List of binary measurement values corresponding to the channel numbers."
    ::= { wtWebGraphAnalogIn57642Inventory 4 }

wtWebGraphAnalogIn57642BinaryValuesEntry OBJECT-TYPE
    SYNTAX WtWebGraphAnalogIn57642BinaryValuesEntry
    ACCESS not-accessible
    STATUS mandatory
    DESCRIPTION
        "Binary measurement values of the sensors."
    INDEX  { wtWebGraphAnalogIn57642SensorNo }
    ::= { wtWebGraphAnalogIn57642BinaryValuesTable 1 }

WtWebGraphAnalogIn57642BinaryValuesEntry ::= SEQUENCE{
    wtWebGraphAnalogIn57642BinaryValues INTEGER
}    

wtWebGraphAnalogIn57642BinaryValues OBJECT-TYPE
    SYNTAX INTEGER
    ACCESS read-only
    STATUS mandatory
    DESCRIPTION
        "Binary measurement value of the sensor in 1/10 degrees Celsius or 1/10 per cent,
        signed number, 0x4FFF6 indicates an 
        invalid measured value."
    ::= { wtWebGraphAnalogIn57642BinaryValuesEntry 1 }

-- wtWebGraphAnalogIn57642SessCntrl Group
--------------------------------

wtWebGraphAnalogIn57642SessCntrlPassword OBJECT-TYPE
    SYNTAX OCTET STRING 
    ACCESS read-write
    STATUS mandatory
    DESCRIPTION
        "Entering this password opens a session which is ended by writing a 1 to 
        wtWebGraphAnalogIn57642SessCntrlLogout. When read this variable provides a string of
        length zero."
    ::= { wtWebGraphAnalogIn57642SessCntrl 1 }

wtWebGraphAnalogIn57642SessCntrlConfigMode OBJECT-TYPE
    SYNTAX INTEGER {
    wtWebGraphAnalogIn57642SessCntrl-NoSession(0),
    wtWebGraphAnalogIn57642SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalogIn57642SessCntrl 2 }

wtWebGraphAnalogIn57642SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebGraphAnalogIn57642SessCntrl 3 }

wtWebGraphAnalogIn57642SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebGraphAnalogIn57642SessCntrl 4 }

wtWebGraphAnalogIn57642SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebGraphAnalogIn57642SessCntrl 5 }
    

-- wtWebGraphAnalogIn57642Text Group
------------------------

wtWebGraphAnalogIn57642DeviceName OBJECT-TYPE
    SYNTAX OCTET STRING 
    ACCESS read-write
    STATUS mandatory
    DESCRIPTION
        "Name of the Webio, which is user definable."
    ::= { wtWebGraphAnalogIn57642Text 1 }

wtWebGraphAnalogIn57642DeviceText OBJECT-TYPE
    SYNTAX OCTET STRING 
    ACCESS read-write
    STATUS mandatory
    DESCRIPTION
        "Description of the Webio, which is user definable."
    ::= { wtWebGraphAnalogIn57642Text 2 }

wtWebGraphAnalogIn57642DeviceLocation OBJECT-TYPE
    SYNTAX OCTET STRING 
    ACCESS read-write
    STATUS mandatory
    DESCRIPTION
        "Description of the location of the Webio, which is user definable."
    ::= { wtWebGraphAnalogIn57642Text 3 }

wtWebGraphAnalogIn57642DeviceContact OBJECT-TYPE
    SYNTAX OCTET STRING 
    ACCESS read-write
    STATUS mandatory
    DESCRIPTION
        "Contact address of the system operator of the Webio, which is user definable."
    ::= { wtWebGraphAnalogIn57642Text 4 }

-- wtWebGraphAnalogIn57642TimeZone Group
----------------------------

wtWebGraphAnalogIn57642TzOffsetHrs OBJECT-TYPE
    SYNTAX INTEGER 
    ACCESS read-write
    STATUS mandatory
    DESCRIPTION
        "Offset hours for the time zone (winter time) with respect to UTC."
    ::= { wtWebGraphAnalogIn57642TimeZone 1 }

wtWebGraphAnalogIn57642TzOffsetMin OBJECT-TYPE
    SYNTAX INTEGER 
    ACCESS read-write
    STATUS mandatory
    DESCRIPTION
        "Offset minutes for the time zone (winter time) with respect to UTC."
    ::= { wtWebGraphAnalogIn57642TimeZone 2 }

wtWebGraphAnalogIn57642TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalogIn57642TimeZone 3 }    
    
wtWebGraphAnalogIn57642StTzOffsetHrs OBJECT-TYPE
    SYNTAX INTEGER 
    ACCESS read-write
    STATUS mandatory
    DESCRIPTION
        "Offset hours of the time zone (summer time) with respect to UTC."
    ::= { wtWebGraphAnalogIn57642TimeZone 4 }

wtWebGraphAnalogIn57642StTzOffsetMin OBJECT-TYPE
    SYNTAX INTEGER 
    ACCESS read-write
    STATUS mandatory
    DESCRIPTION
        "Offset minutes of the time zone (summer time) with respect to UTC."
    ::= { wtWebGraphAnalogIn57642TimeZone 5 }
    
wtWebGraphAnalogIn57642StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalogIn57642TimeZone 6 }       
    
wtWebGraphAnalogIn57642StTzStartMonth OBJECT-TYPE
    SYNTAX INTEGER {
    	wtWebGraphAnalogIn57642StartMonth-January(1),
    	wtWebGraphAnalogIn57642StartMonth-February(2),
    	wtWebGraphAnalogIn57642StartMonth-March(3),
    	wtWebGraphAnalogIn57642StartMonth-April(4),
    	wtWebGraphAnalogIn57642StartMonth-May(5),
    	wtWebGraphAnalogIn57642StartMonth-June(6),
    	wtWebGraphAnalogIn57642StartMonth-July(7),
    	wtWebGraphAnalogIn57642StartMonth-August(8),
    	wtWebGraphAnalogIn57642StartMonth-September(9),
    	wtWebGraphAnalogIn57642StartMonth-October(10),
    	wtWebGraphAnalogIn57642StartMonth-November(11),
    	wtWebGraphAnalogIn57642StartMonth-December(12)
    	}
    	
    ACCESS read-write
    STATUS mandatory
    DESCRIPTION
        "Month in which the change is made from winter time to summer time."
    ::= { wtWebGraphAnalogIn57642TimeZone 7 }

wtWebGraphAnalogIn57642StTzStartMode OBJECT-TYPE
    SYNTAX INTEGER {
    	wtWebGraphAnalogIn57642StartMode-first(1),
    	wtWebGraphAnalogIn57642StartMode-second(2),
    	wtWebGraphAnalogIn57642StartMode-third(3),
    	wtWebGraphAnalogIn57642StartMode-fourth(4),
    	wtWebGraphAnalogIn57642StartMode-last(5)
    	}
    	
    ACCESS read-write
    STATUS mandatory
    DESCRIPTION
        "Mode of the day of the week for which the change is made from winter time to summer time."
    ::= { wtWebGraphAnalogIn57642TimeZone 8 }

wtWebGraphAnalogIn57642StTzStartWday OBJECT-TYPE
    SYNTAX INTEGER {
    	wtWebGraphAnalogIn57642StartWday-Sunday(1),
    	wtWebGraphAnalogIn57642StartWday-Monday(2),
    	wtWebGraphAnalogIn57642StartWday-Tuesday(3),
    	wtWebGraphAnalogIn57642StartWday-Thursday(4),
    	wtWebGraphAnalogIn57642StartWday-Wednesday(5),
    	wtWebGraphAnalogIn57642StartWday-Friday(6),
    	wtWebGraphAnalogIn57642StartWday-Saturday(7)
    	}
    	
    ACCESS read-write
    STATUS mandatory
    DESCRIPTION
        "Day of the week on which the change is made from winter time to summer time"
    ::= { wtWebGraphAnalogIn57642TimeZone 9 }
    
wtWebGraphAnalogIn57642StTzStartHrs OBJECT-TYPE
    SYNTAX INTEGER 
    ACCESS read-write
    STATUS mandatory
    DESCRIPTION
        "Hour in which the time zone is changed from winter to summer time with
        respect to UTC."
    ::= { wtWebGraphAnalogIn57642TimeZone 10 }

wtWebGraphAnalogIn57642StTzStartMin OBJECT-TYPE
    SYNTAX INTEGER 
    ACCESS read-write
    STATUS mandatory
    DESCRIPTION
        "Minute in which the time zone is changed from winter to summer time with
        respect to UTC."
    ::= { wtWebGraphAnalogIn57642TimeZone 11 }
 
wtWebGraphAnalogIn57642StTzStopMonth OBJECT-TYPE
    SYNTAX INTEGER {
    	wtWebGraphAnalogIn57642StopMonth-January(1),
    	wtWebGraphAnalogIn57642StopMonth-February(2),
    	wtWebGraphAnalogIn57642StopMonth-March(3),
    	wtWebGraphAnalogIn57642StopMonth-April(4),
    	wtWebGraphAnalogIn57642StopMonth-May(5),
    	wtWebGraphAnalogIn57642StopMonth-June(6),
    	wtWebGraphAnalogIn57642StopMonth-July(7),
    	wtWebGraphAnalogIn57642StopMonth-August(8),
    	wtWebGraphAnalogIn57642StopMonth-September(9),
    	wtWebGraphAnalogIn57642StopMonth-October(10),
    	wtWebGraphAnalogIn57642StopMonth-November(11),
    	wtWebGraphAnalogIn57642StopMonth-December(12)
    	}
    ACCESS read-write
    STATUS mandatory
    DESCRIPTION
        "Month in which the change is made from summer time to winter time."
   ::= { wtWebGraphAnalogIn57642TimeZone 12 }

wtWebGraphAnalogIn57642StTzStopMode OBJECT-TYPE
    SYNTAX INTEGER {
    	wtWebGraphAnalogIn57642StopMode-first(1),
    	wtWebGraphAnalogIn57642StopMode-second(2),
    	wtWebGraphAnalogIn57642StopMode-third(3),
    	wtWebGraphAnalogIn57642StopMode-fourth(4),
    	wtWebGraphAnalogIn57642StopMode-last(5)
    	}
    ACCESS read-write
    STATUS mandatory
    DESCRIPTION
        "Mode of the week day on which the change is made from summer time to winter time."
    ::= { wtWebGraphAnalogIn57642TimeZone 13 }

wtWebGraphAnalogIn57642StTzStopWday OBJECT-TYPE
    SYNTAX INTEGER {
    	wtWebGraphAnalogIn57642StopWday-Sunday(1),
    	wtWebGraphAnalogIn57642StopWday-Monday(2),
    	wtWebGraphAnalogIn57642StopWday-Tuesday(3),
    	wtWebGraphAnalogIn57642StopWday-Thursday(4),
    	wtWebGraphAnalogIn57642StopWday-Wednesday(5),
    	wtWebGraphAnalogIn57642StopWday-Friday(6),
    	wtWebGraphAnalogIn57642StopWday-Saturday(7)
    	}
    ACCESS read-write
    STATUS mandatory
    DESCRIPTION
        "Day of the week on which the change is made from summer time to winter time."
    ::= { wtWebGraphAnalogIn57642TimeZone 14 }
    
wtWebGraphAnalogIn57642StTzStopHrs OBJECT-TYPE
    SYNTAX INTEGER 
    ACCESS read-write
    STATUS mandatory
    DESCRIPTION
        "Hour at which the time zone is changed from summer to winter time with
        respect to UTC."
    ::= { wtWebGraphAnalogIn57642TimeZone 15 }

wtWebGraphAnalogIn57642StTzStopMin OBJECT-TYPE
    SYNTAX INTEGER 
    ACCESS read-write
    STATUS mandatory
    DESCRIPTION
        "Minute at which the time zone is changed from summer to winter time with
        respect to UTC."
    ::= { wtWebGraphAnalogIn57642TimeZone 16 }

-- wtWebGraphAnalogIn57642TimeServer Group
----------------------------

wtWebGraphAnalogIn57642TimeServer1 OBJECT-TYPE
    SYNTAX OCTET STRING 
    ACCESS read-write
    STATUS mandatory
    DESCRIPTION
        "IP address or name of the 1st time server in ASCII"
    ::= { wtWebGraphAnalogIn57642TimeServer 1 }

wtWebGraphAnalogIn57642TimeServer2 OBJECT-TYPE
    SYNTAX OCTET STRING 
    ACCESS read-write
    STATUS mandatory
    DESCRIPTION
        "IP address or name of the 2nd time server in ASCII"
    ::= { wtWebGraphAnalogIn57642TimeServer 2 }
    
wtWebGraphAnalogIn57642TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalogIn57642TimeServer 3 }
    
wtWebGraphAnalogIn57642TsSyncTime OBJECT-TYPE
    SYNTAX INTEGER 
    ACCESS read-write
    STATUS mandatory
    DESCRIPTION
        "Daily synchronisation time with the time server (hour: 0-23)."
    ::= { wtWebGraphAnalogIn57642TimeServer 4 } 
    
-- wtWebGraphAnalogIn57642DeviceClock Group
----------------------------

wtWebGraphAnalogIn57642ClockHrs OBJECT-TYPE
    SYNTAX INTEGER (0..23)
    ACCESS read-write
    STATUS mandatory
    DESCRIPTION
        "Clock hours taking into account the time zone settings."
    ::= { wtWebGraphAnalogIn57642DeviceClock 1 }

wtWebGraphAnalogIn57642ClockMin OBJECT-TYPE
    SYNTAX INTEGER (0..59)
    ACCESS read-write
    STATUS mandatory
    DESCRIPTION
        "Clock minutes taking into account the time zone settings."
    ::= { wtWebGraphAnalogIn57642DeviceClock 2 }

wtWebGraphAnalogIn57642ClockDay OBJECT-TYPE
    SYNTAX INTEGER (1..31)
    ACCESS read-write
    STATUS mandatory
    DESCRIPTION
        "Date: Day of the month, taking into account the time zone settings."
    ::= { wtWebGraphAnalogIn57642DeviceClock 3 }

wtWebGraphAnalogIn57642ClockMonth OBJECT-TYPE
   SYNTAX INTEGER {
    	wtWebGraphAnalogIn57642ClockMonth-January(1),
    	wtWebGraphAnalogIn57642ClockMonth-February(2),
    	wtWebGraphAnalogIn57642ClockMonth-March(3),
    	wtWebGraphAnalogIn57642ClockMonth-April(4),
    	wtWebGraphAnalogIn57642ClockMonth-May(5),
    	wtWebGraphAnalogIn57642ClockMonth-June(6),
    	wtWebGraphAnalogIn57642ClockMonth-July(7),
    	wtWebGraphAnalogIn57642ClockMonth-August(8),
    	wtWebGraphAnalogIn57642ClockMonth-September(9),
    	wtWebGraphAnalogIn57642ClockMonth-October(10),
    	wtWebGraphAnalogIn57642ClockMonth-November(11),
    	wtWebGraphAnalogIn57642ClockMonth-December(12)
    	}
    ACCESS read-write
    STATUS mandatory
    DESCRIPTION
        "Date: Month, taking into account the time zone settings."
    ::= { wtWebGraphAnalogIn57642DeviceClock 4 }

wtWebGraphAnalogIn57642ClockYear OBJECT-TYPE
    SYNTAX INTEGER (0..65535)
    ACCESS read-write
    STATUS mandatory
    DESCRIPTION
        "Date: Year, taking into account the time zone settings."
    ::= { wtWebGraphAnalogIn57642DeviceClock 5 }
    

-- wtWebGraphAnalogIn57642Network Group
------------------------

wtWebGraphAnalogIn57642IpAddress OBJECT-TYPE
    SYNTAX IpAddress
    ACCESS read-write
    STATUS mandatory
    DESCRIPTION
        "IP address of the Webio"
    ::= { wtWebGraphAnalogIn57642Network 1 }

wtWebGraphAnalogIn57642SubnetMask OBJECT-TYPE
    SYNTAX IpAddress
    ACCESS read-write
    STATUS mandatory
    DESCRIPTION
        "Subnet mask of the Webio"
    ::= { wtWebGraphAnalogIn57642Network 2 }

wtWebGraphAnalogIn57642Gateway OBJECT-TYPE
    SYNTAX IpAddress
    ACCESS read-write
    STATUS mandatory
    DESCRIPTION
        "Gateway of the Webio"
    ::= { wtWebGraphAnalogIn57642Network 3 }

wtWebGraphAnalogIn57642DnsServer1 OBJECT-TYPE
    SYNTAX OCTET STRING 
    ACCESS read-write
    STATUS mandatory
    DESCRIPTION
        "IP address of the 1st DNS server in ASCII"
    ::= { wtWebGraphAnalogIn57642Network 4 }

wtWebGraphAnalogIn57642DnsServer2 OBJECT-TYPE
    SYNTAX OCTET STRING 
    ACCESS read-write
    STATUS mandatory
    DESCRIPTION
        "IP address of the 2nd DNS server in ASCII"
    ::= { wtWebGraphAnalogIn57642Network 5 }

wtWebGraphAnalogIn57642AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalogIn57642Network 6 }

--  wtWebGraphAnalogIn57642HTTP Group
--------------------------------

wtWebGraphAnalogIn57642Startup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalogIn57642HTTP 1 }

wtWebGraphAnalogIn57642GetHeaderEnable OBJECT-TYPE
    SYNTAX OCTET STRING 
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalogIn57642HTTP 2 }  
    
wtWebGraphAnalogIn57642HttpPort OBJECT-TYPE
    SYNTAX INTEGER (1..65535)
    ACCESS read-write
    STATUS mandatory
    DESCRIPTION
        "Definition of the standard HTML port (Default: 80)."
    ::= { wtWebGraphAnalogIn57642HTTP 3 }    


-- wtWebGraphAnalogIn57642Mail Group
--------------------------------

wtWebGraphAnalogIn57642MailAdName OBJECT-TYPE
    SYNTAX OCTET STRING 
    ACCESS read-write
    STATUS mandatory
    DESCRIPTION
        "Device name for mail administration."
    ::= { wtWebGraphAnalogIn57642Mail 1 }
    
wtWebGraphAnalogIn57642MailReply OBJECT-TYPE
    SYNTAX OCTET STRING 
    ACCESS read-write
    STATUS mandatory
    DESCRIPTION
        "Reply address for the mail server."
    ::= { wtWebGraphAnalogIn57642Mail 2 }
    
wtWebGraphAnalogIn57642MailServer OBJECT-TYPE
    SYNTAX OCTET STRING 
    ACCESS read-write
    STATUS mandatory
    DESCRIPTION
        "Name or IP address of the mail server."
    ::= { wtWebGraphAnalogIn57642Mail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalogIn57642Mail 4 }
    
wtWebGraphAnalogIn57642MailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalogIn57642Mail 5 }
    
wtWebGraphAnalogIn57642MailAuthUser OBJECT-TYPE
    SYNTAX OCTET STRING 
    ACCESS read-write
    STATUS mandatory
    DESCRIPTION
        "Name of the user to be authenticated."
    ::= { wtWebGraphAnalogIn57642Mail 6 }    
    
wtWebGraphAnalogIn57642MailAuthPassword OBJECT-TYPE
    SYNTAX OCTET STRING 
    ACCESS read-write
    STATUS mandatory
    DESCRIPTION
        "Authentication password."
    ::= { wtWebGraphAnalogIn57642Mail 7 }    
    
wtWebGraphAnalogIn57642MailPop3Server OBJECT-TYPE
    SYNTAX OCTET STRING 
    ACCESS read-write
    STATUS mandatory
    DESCRIPTION
        "Name or Ip-address of the POP3 Servers."
    ::= { wtWebGraphAnalogIn57642Mail 8 }            

-- wtWebGraphAnalogIn57642SNMP Group
--------------------------------

wtWebGraphAnalogIn57642SnmpCommunityStringRead OBJECT-TYPE
    SYNTAX OCTET STRING
    ACCESS read-write
    STATUS mandatory
    DESCRIPTION
        "Community string read only"
    ::= { wtWebGraphAnalogIn57642SNMP 1 }

wtWebGraphAnalogIn57642SnmpCommunityStringReadWrite OBJECT-TYPE
    SYNTAX OCTET STRING
    ACCESS read-write
    STATUS mandatory
    DESCRIPTION
        "Community string read / write"
    ::= { wtWebGraphAnalogIn57642SNMP 2 }

wtWebGraphAnalogIn57642SystemTrapManagerIP OBJECT-TYPE
    SYNTAX OCTET STRING 
    ACCESS read-write
    STATUS mandatory
    DESCRIPTION
        "Name or IP address of the TCP server which accepts the system trap."
    ::= { wtWebGraphAnalogIn57642SNMP 3 }
    
wtWebGraphAnalogIn57642SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalogIn57642SNMP 4 }
    
wtWebGraphAnalogIn57642SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebGraphAnalogIn57642SNMP 5 }
    
wtWebGraphAnalogIn57642SnmpCommunityStringTrap OBJECT-TYPE
    SYNTAX OCTET STRING
    ACCESS read-write
    STATUS mandatory
    DESCRIPTION
        "Community string send within traps."
    ::= { wtWebGraphAnalogIn57642SNMP 6 }    
        
    
    
-- wtWebGraphAnalogIn57642UDP Group
--------------------------------
    
wtWebGraphAnalogIn57642UdpPort OBJECT-TYPE
    SYNTAX INTEGER (1..65535)
    ACCESS read-write
    STATUS mandatory
    DESCRIPTION
        "Udp port to which the Udp queries ( short form GET requests) can be sent. This
        port number must be unique within the device."
    ::= { wtWebGraphAnalogIn57642UDP 1 }
    
wtWebGraphAnalogIn57642UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalogIn57642UDP 2 }
    
--  wtWebGraphAnalogIn57642Syslog Group
--------------------------------
    
wtWebGraphAnalogIn57642SyslogServerIP OBJECT-TYPE
    SYNTAX OCTET STRING 
    ACCESS read-write
    STATUS mandatory
    DESCRIPTION
        "Name or IP address of the Syslog server, which accepts the Syslog messgaes."
    ::= { wtWebGraphAnalogIn57642Syslog 1 }
    
wtWebGraphAnalogIn57642SyslogServerPort OBJECT-TYPE
    SYNTAX INTEGER
    ACCESS read-write
    STATUS mandatory
    DESCRIPTION
        "Portnumber of the Syslog servers, default 514."
    ::= { wtWebGraphAnalogIn57642Syslog 2 }

wtWebGraphAnalogIn57642SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalogIn57642Syslog 3 }    

wtWebGraphAnalogIn57642SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalogIn57642Syslog 4 }
    
--  wtWebGraphAnalogIn57642FTP Group
--------------------------------

wtWebGraphAnalogIn57642FTPServerIP OBJECT-TYPE
    SYNTAX OCTET STRING 
    ACCESS read-write
    STATUS mandatory
    DESCRIPTION
        "Name or IP address of the FTP server, which accepts the FTP messages."
    ::= { wtWebGraphAnalogIn57642FTP 1 }
    
wtWebGraphAnalogIn57642FTPServerControlPort OBJECT-TYPE
    SYNTAX INTEGER
    ACCESS read-write
    STATUS mandatory
    DESCRIPTION
        "Portnumber of the control port of the FTP server, default 21."
    ::= { wtWebGraphAnalogIn57642FTP 2 }
    
wtWebGraphAnalogIn57642FTPUserName OBJECT-TYPE
    SYNTAX OCTET STRING 
    ACCESS read-write
    STATUS mandatory
    DESCRIPTION
        "FTP Loggin: user name."
    ::= { wtWebGraphAnalogIn57642FTP 3 }
    
wtWebGraphAnalogIn57642FTPPassword OBJECT-TYPE
    SYNTAX OCTET STRING 
    ACCESS read-write
    STATUS mandatory
    DESCRIPTION
        "FTP Loggin: user password."
    ::= { wtWebGraphAnalogIn57642FTP 4 }

wtWebGraphAnalogIn57642FTPAccount OBJECT-TYPE
    SYNTAX OCTET STRING 
    ACCESS read-write
    STATUS mandatory
    DESCRIPTION
        "FTP Loggin: name of account."
    ::= { wtWebGraphAnalogIn57642FTP 5 }

wtWebGraphAnalogIn57642FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalogIn57642FTP 6 }
    
wtWebGraphAnalogIn57642FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalogIn57642FTP 7 }    
    
-- wtWebGraphAnalogIn57642Datalogger Group
--------------------------------

wtWebGraphAnalogIn57642LoggerTimebase OBJECT-TYPE
    SYNTAX INTEGER {
    wtWebGraphAnalogIn57642Datalogger-1Min(1),
    wtWebGraphAnalogIn57642Datalogger-5Min(2),
    wtWebGraphAnalogIn57642Datalogger-15Min(3),
    wtWebGraphAnalogIn57642Datalogger-60Min(4)
    }
    ACCESS read-write
    STATUS mandatory
    DESCRIPTION
        "Time base of the data logger"
    ::= { wtWebGraphAnalogIn57642Datalogger 1 }

wtWebGraphAnalogIn57642LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalogIn57642Datalogger 2 }

wtWebGraphAnalogIn57642DisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalogIn57642Datalogger 3 }    
    
-- Graph Sensor Color Table

wtWebGraphAnalogIn57642SensorColorTable OBJECT-TYPE
    SYNTAX SEQUENCE OF WtWebGraphAnalogIn57642SensorColorEntry
    ACCESS not-accessible
    STATUS mandatory
    DESCRIPTION
        "List of sensor colors for the praphical presentation."
    ::= { wtWebGraphAnalogIn57642Datalogger 4 }

wtWebGraphAnalogIn57642SensorColorEntry OBJECT-TYPE
    SYNTAX WtWebGraphAnalogIn57642SensorColorEntry
    ACCESS not-accessible
    STATUS mandatory
    DESCRIPTION
        "Index numbers of the sensors."
    INDEX  { wtWebGraphAnalogIn57642SensorNo }
    ::= { wtWebGraphAnalogIn57642SensorColorTable 1 }

WtWebGraphAnalogIn57642SensorColorEntry ::= SEQUENCE {
    wtWebGraphAnalogIn57642SensorColor OCTET STRING
}

wtWebGraphAnalogIn57642SensorColor OBJECT-TYPE
    SYNTAX OCTET STRING (SIZE(3))
    ACCESS read-write
    STATUS mandatory
    DESCRIPTION
        "Color of the sensors at the praphical presention."
    ::= { wtWebGraphAnalogIn57642SensorColorEntry 1 }
    
wtWebGraphAnalogIn57642AutoScaleEnable OBJECT-TYPE
    SYNTAX OCTET STRING 
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebGraphAnalogIn57642Datalogger 5 }
    
wtWebGraphAnalogIn57642VerticalUpperLimit OBJECT-TYPE
    SYNTAX OCTET STRING 
    ACCESS read-write
    STATUS mandatory
    DESCRIPTION
        "This value defines the maximum temperature shown in the graphical presentation,
        if no auto scaling is selected.
        Temperature in degrees with maximum 2 decimal places."
    ::= { wtWebGraphAnalogIn57642Datalogger 6 }

wtWebGraphAnalogIn57642VerticalLowerLimit OBJECT-TYPE
    SYNTAX OCTET STRING 
    ACCESS read-write
    STATUS mandatory
    DESCRIPTION
        "This value defines the minimum temperature shown in the graphical presentation,
        if no auto scaling is selected.
        Temperature in degrees with maximum 2 decimal places."
    ::= { wtWebGraphAnalogIn57642Datalogger 7 }
    
wtWebGraphAnalogIn57642HorizontalZoom OBJECT-TYPE
    SYNTAX INTEGER {
    wtWebGraphAnalogIn57642Zoom-25min(1),
    wtWebGraphAnalogIn57642Zoom-75min(2),
    wtWebGraphAnalogIn57642Zoom-5hrs(3),
    wtWebGraphAnalogIn57642Zoom-30hrs(4),
    wtWebGraphAnalogIn57642Zoom-5days(5),
    wtWebGraphAnalogIn57642Zoom-25days(6)
    }
    ACCESS read-write
    STATUS mandatory
    DESCRIPTION
        "Defines the default zoom stage, if no auto scaling is selected."
    ::= { wtWebGraphAnalogIn57642Datalogger 8 }    

-- wtWebGraphAnalogIn57642Alarm Group
----------------------------

wtWebGraphAnalogIn57642AlarmCount OBJECT-TYPE
    SYNTAX INTEGER (1..8)
    ACCESS read-only
    STATUS mandatory
    DESCRIPTION
        "Number of independent alarms."
    ::= { wtWebGraphAnalogIn57642Alarm 1 }
    
-- Alarm Interface Table

wtWebGraphAnalogIn57642AlarmIfTable OBJECT-TYPE
    SYNTAX SEQUENCE OF WtWebGraphAnalogIn57642AlarmIfEntry
    ACCESS not-accessible
    STATUS mandatory
    DESCRIPTION
        "List of alarm indices."
    ::= { wtWebGraphAnalogIn57642Alarm 2 }

wtWebGraphAnalogIn57642AlarmIfEntry OBJECT-TYPE
    SYNTAX WtWebGraphAnalogIn57642AlarmIfEntry
    ACCESS not-accessible
    STATUS mandatory
    DESCRIPTION
        "Numbers of the alarms."
    INDEX  { wtWebGraphAnalogIn57642AlarmNo }
    ::= { wtWebGraphAnalogIn57642AlarmIfTable 1 }

WtWebGraphAnalogIn57642AlarmIfEntry ::= SEQUENCE {
    wtWebGraphAnalogIn57642AlarmNo INTEGER
}

wtWebGraphAnalogIn57642AlarmNo OBJECT-TYPE
    SYNTAX INTEGER (1..8)
    ACCESS read-only
    STATUS mandatory
    DESCRIPTION
        "Alarm number."
    ::= { wtWebGraphAnalogIn57642AlarmIfEntry 1 }

-- Alarm Table

wtWebGraphAnalogIn57642AlarmTable OBJECT-TYPE
    SYNTAX SEQUENCE OF WtWebGraphAnalogIn57642AlarmEntry
    ACCESS not-accessible
    STATUS mandatory
    DESCRIPTION
        "List of settings depending on the alarm number."
    ::= { wtWebGraphAnalogIn57642Alarm 3 }

wtWebGraphAnalogIn57642AlarmEntry OBJECT-TYPE
    SYNTAX WtWebGraphAnalogIn57642AlarmEntry
    ACCESS not-accessible
    STATUS mandatory
    DESCRIPTION
        "Alarm parameters of the individual alarms."
    INDEX  { wtWebGraphAnalogIn57642AlarmNo }
    ::= { wtWebGraphAnalogIn57642AlarmTable 1 }

WtWebGraphAnalogIn57642AlarmEntry ::= SEQUENCE {
    wtWebGraphAnalogIn57642AlarmTrigger			OCTET STRING,
    wtWebGraphAnalogIn57642AlarmMin			OCTET STRING,
    wtWebGraphAnalogIn57642AlarmMax			OCTET STRING,
    wtWebGraphAnalogIn57642AlarmHysteresis		OCTET STRING,
    wtWebGraphAnalogIn57642AlarmDelay			OCTET STRING,
    wtWebGraphAnalogIn57642AlarmInterval		OCTET STRING,
    wtWebGraphAnalogIn57642AlarmEnable			OCTET STRING,
    wtWebGraphAnalogIn57642AlarmEMailAddr		OCTET STRING,
    wtWebGraphAnalogIn57642AlarmMailSubject		OCTET STRING,
    wtWebGraphAnalogIn57642AlarmMailText		OCTET STRING,
    wtWebGraphAnalogIn57642AlarmManagerIP		OCTET STRING,
    wtWebGraphAnalogIn57642AlarmTrapText		OCTET STRING,
    wtWebGraphAnalogIn57642AlarmMailOptions		OCTET STRING,
    wtWebGraphAnalogIn57642AlarmTcpIpAddr		OCTET STRING,
    wtWebGraphAnalogIn57642AlarmTcpPort			INTEGER,
    wtWebGraphAnalogIn57642AlarmTcpText			OCTET STRING,
    wtWebGraphAnalogIn57642AlarmClearMailSubject	OCTET STRING,
    wtWebGraphAnalogIn57642AlarmClearMailText		OCTET STRING,
    wtWebGraphAnalogIn57642AlarmClearTrapText		OCTET STRING,
    wtWebGraphAnalogIn57642AlarmClearTcpText		OCTET STRING,
    wtWebGraphAnalogIn57642Alarm2Min			OCTET STRING,
    wtWebGraphAnalogIn57642Alarm2Max			OCTET STRING,
    wtWebGraphAnalogIn57642Alarm2Hysteresis		OCTET STRING,
    wtWebGraphAnalogIn57642AlarmSyslogIpAddr		OCTET STRING,
    wtWebGraphAnalogIn57642AlarmSyslogPort		INTEGER,
    wtWebGraphAnalogIn57642AlarmSyslogText		OCTET STRING,
    wtWebGraphAnalogIn57642AlarmSyslogClearText		OCTET STRING,
    wtWebGraphAnalogIn57642AlarmFtpDataPort		OCTET STRING,
    wtWebGraphAnalogIn57642AlarmFtpFileName		OCTET STRING,
    wtWebGraphAnalogIn57642AlarmFtpText			OCTET STRING,
    wtWebGraphAnalogIn57642AlarmFtpClearText		OCTET STRING,
    wtWebGraphAnalogIn57642AlarmFtpOption		OCTET STRING,
    wtWebGraphAnalogIn57642AlarmTimerCron		OCTET STRING

}

wtWebGraphAnalogIn57642AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2-7: unused"
    ::= { wtWebGraphAnalogIn57642AlarmEntry 1 }

wtWebGraphAnalogIn57642AlarmMin OBJECT-TYPE
    SYNTAX OCTET STRING 
    ACCESS read-write
    STATUS mandatory
    DESCRIPTION
        "Minimum temperature in degrees with maximum 2 decimal places."
    ::= { wtWebGraphAnalogIn57642AlarmEntry 2 }

wtWebGraphAnalogIn57642AlarmMax OBJECT-TYPE
    SYNTAX OCTET STRING 
    ACCESS read-write
    STATUS mandatory
    DESCRIPTION
        "Maximum temperature in degrees with maximum 2 decimal places."
    ::= { wtWebGraphAnalogIn57642AlarmEntry 3 }
    
wtWebGraphAnalogIn57642AlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebGraphAnalogIn57642AlarmEntry 4 }

wtWebGraphAnalogIn57642AlarmDelay OBJECT-TYPE
    SYNTAX OCTET STRING 
    ACCESS read-write
    STATUS mandatory
    DESCRIPTION
        "Alarm will be delayed by setting this time while stable alarm 
        condition occur (time in minutes)."
    ::= { wtWebGraphAnalogIn57642AlarmEntry 5 }
        

wtWebGraphAnalogIn57642AlarmInterval OBJECT-TYPE
    SYNTAX OCTET STRING 
    ACCESS read-write
    STATUS mandatory
    DESCRIPTION
        "Send interval for alarm messages."
    ::= { wtWebGraphAnalogIn57642AlarmEntry 6 }

wtWebGraphAnalogIn57642AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphAnalogIn57642AlarmEntry 7 }

wtWebGraphAnalogIn57642AlarmEMailAddr OBJECT-TYPE
    SYNTAX OCTET STRING 
    ACCESS read-write
    STATUS mandatory
    DESCRIPTION
        "E-Mail address for sending the alarm mail to."
    ::= { wtWebGraphAnalogIn57642AlarmEntry 8 }

wtWebGraphAnalogIn57642AlarmMailSubject OBJECT-TYPE
    SYNTAX OCTET STRING 
    ACCESS read-write
    STATUS mandatory
    DESCRIPTION
        "Subject line for alarm mail."
    ::= { wtWebGraphAnalogIn57642AlarmEntry 9 }

wtWebGraphAnalogIn57642AlarmMailText OBJECT-TYPE
    SYNTAX OCTET STRING 
    ACCESS read-write
    STATUS mandatory
    DESCRIPTION
        "Alarm mail text: <Tn> provides the current temperature; n = 1..8.
        <Z> provides the current time."
    ::= { wtWebGraphAnalogIn57642AlarmEntry 10 }

wtWebGraphAnalogIn57642AlarmManagerIP OBJECT-TYPE
    SYNTAX OCTET STRING 
    ACCESS read-write
    STATUS mandatory
    DESCRIPTION
        "Name or IP address of the SNMP Manager which accepts the trap."
    ::= { wtWebGraphAnalogIn57642AlarmEntry 11 }

wtWebGraphAnalogIn57642AlarmTrapText OBJECT-TYPE
    SYNTAX OCTET STRING 
    ACCESS read-write
    STATUS mandatory
    DESCRIPTION
        "This text is sent in the trap body."
    ::= { wtWebGraphAnalogIn57642AlarmEntry 12 }
    
wtWebGraphAnalogIn57642AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAnalogIn57642AlarmEntry 13 }    
    
wtWebGraphAnalogIn57642AlarmTcpIpAddr OBJECT-TYPE
    SYNTAX OCTET STRING 
    ACCESS read-write
    STATUS mandatory
    DESCRIPTION
        "Name or IP address of the TCP server which accepts the trap."
    ::= { wtWebGraphAnalogIn57642AlarmEntry 14 }    

wtWebGraphAnalogIn57642AlarmTcpPort OBJECT-TYPE
    SYNTAX INTEGER (1..65535) 
    ACCESS read-write
    STATUS mandatory
    DESCRIPTION
        "Port number of the TCP server which accepts the trap."
    ::= { wtWebGraphAnalogIn57642AlarmEntry 15 }    

wtWebGraphAnalogIn57642AlarmTcpText OBJECT-TYPE
    SYNTAX OCTET STRING 
    ACCESS read-write
    STATUS mandatory
    DESCRIPTION
        "This text is sent in the TCP trap body."
    ::= { wtWebGraphAnalogIn57642AlarmEntry 16 }

wtWebGraphAnalogIn57642AlarmClearMailSubject OBJECT-TYPE
    SYNTAX OCTET STRING 
    ACCESS read-write
    STATUS mandatory
    DESCRIPTION
        "Subject line for alarm clear mail."
    ::= { wtWebGraphAnalogIn57642AlarmEntry 17 }

wtWebGraphAnalogIn57642AlarmClearMailText OBJECT-TYPE
    SYNTAX OCTET STRING 
    ACCESS read-write
    STATUS mandatory
    DESCRIPTION
        "Alarm clear mail text: <Tn> provides the current temperature; n = 1..8.
        <Z> provides the current time."
    ::= { wtWebGraphAnalogIn57642AlarmEntry 18 }

wtWebGraphAnalogIn57642AlarmClearTrapText OBJECT-TYPE
    SYNTAX OCTET STRING 
    ACCESS read-write
    STATUS mandatory
    DESCRIPTION
        "This text is sent in the trap body."
    ::= { wtWebGraphAnalogIn57642AlarmEntry 19 }

wtWebGraphAnalogIn57642AlarmClearTcpText OBJECT-TYPE
    SYNTAX OCTET STRING 
    ACCESS read-write
    STATUS mandatory
    DESCRIPTION
        "This text is sent in the TCP trap body."
    ::= { wtWebGraphAnalogIn57642AlarmEntry 20 }
    
wtWebGraphAnalogIn57642Alarm2Min OBJECT-TYPE
    SYNTAX OCTET STRING 
    ACCESS read-write
    STATUS mandatory
    DESCRIPTION
        "Minimum rel. Humidity in percent with maximum 2 decimal places."
    ::= { wtWebGraphAnalogIn57642AlarmEntry 21 }

wtWebGraphAnalogIn57642Alarm2Max OBJECT-TYPE
    SYNTAX OCTET STRING 
    ACCESS read-write
    STATUS mandatory
    DESCRIPTION
        "Maximum rel.Humidity in percent with maximum 2 decimal places."
    ::= { wtWebGraphAnalogIn57642AlarmEntry 22 }

wtWebGraphAnalogIn57642Alarm2Hysteresis OBJECT-TYPE
    SYNTAX OCTET STRING 
    ACCESS read-write
    STATUS mandatory
    DESCRIPTION
        "Hysterese rel. Humidity in percent with maximum 2 decimal places."
    ::= { wtWebGraphAnalogIn57642AlarmEntry 23 }

wtWebGraphAnalogIn57642AlarmSyslogIpAddr OBJECT-TYPE
    SYNTAX OCTET STRING 
    ACCESS read-write
    STATUS mandatory
    DESCRIPTION
        "IP address of the syslog server to which the Webio device should send syslog messages."
    ::= { wtWebGraphAnalogIn57642AlarmEntry 24 }    

wtWebGraphAnalogIn57642AlarmSyslogPort OBJECT-TYPE
    SYNTAX INTEGER (1..65535) 
    ACCESS read-write
    STATUS mandatory
    DESCRIPTION
        "Port number of the syslog server to which the Webio device should send syslog messages."
    ::= { wtWebGraphAnalogIn57642AlarmEntry 25 }    

wtWebGraphAnalogIn57642AlarmSyslogText OBJECT-TYPE
    SYNTAX OCTET STRING 
    ACCESS read-write
    STATUS mandatory
    DESCRIPTION
        "Every message starts with the priority key, a time stamp and the host ip address, according RFC3164.
        This text appears in the following syslog message body."
    ::= { wtWebGraphAnalogIn57642AlarmEntry 26 }
    
wtWebGraphAnalogIn57642AlarmSyslogClearText OBJECT-TYPE
    SYNTAX OCTET STRING 
    ACCESS read-write
    STATUS mandatory
    DESCRIPTION
        "Every message starts with the priority key, a time stamp and the host ip address, according RFC3164.
        This text appears in the following syslog message body of a alarm clear message."
    ::= { wtWebGraphAnalogIn57642AlarmEntry 27 }
    
wtWebGraphAnalogIn57642AlarmFtpDataPort OBJECT-TYPE
    SYNTAX OCTET STRING 
    ACCESS read-write
    STATUS mandatory
    DESCRIPTION
        "Local data port: 1..65535 or AUTO: the next free port will be assigned."
    ::= { wtWebGraphAnalogIn57642AlarmEntry 28 }
    
wtWebGraphAnalogIn57642AlarmFtpFileName OBJECT-TYPE
    SYNTAX OCTET STRING 
    ACCESS read-write
    STATUS mandatory
    DESCRIPTION
        "Name of the file including path informations."
    ::= { wtWebGraphAnalogIn57642AlarmEntry 29 }
    
wtWebGraphAnalogIn57642AlarmFtpText OBJECT-TYPE
    SYNTAX OCTET STRING 
    ACCESS read-write
    STATUS mandatory
    DESCRIPTION
        "Message text to store on the FTP server."
    ::= { wtWebGraphAnalogIn57642AlarmEntry 30 }

wtWebGraphAnalogIn57642AlarmFtpClearText OBJECT-TYPE
    SYNTAX OCTET STRING 
    ACCESS read-write
    STATUS mandatory
    DESCRIPTION
        "Alarm clear message to store on the FTP server."
    ::= { wtWebGraphAnalogIn57642AlarmEntry 31 }
    
wtWebGraphAnalogIn57642AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphAnalogIn57642AlarmEntry 32 }      
    
wtWebGraphAnalogIn57642AlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebGraphAnalogIn57642AlarmEntry 33 }      

-- wtWebGraphAnalogIn57642GraphicsBase Group
----------------------------

wtWebGraphAnalogIn57642GraphicsBaseEnable OBJECT-TYPE
    SYNTAX OCTET STRING 
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalogIn57642GraphicsBase 1 }

wtWebGraphAnalogIn57642GraphicsBaseWidth OBJECT-TYPE
    SYNTAX INTEGER 
    ACCESS read-write
    STATUS mandatory
    DESCRIPTION
        "Defines the width of the graphic in pixels."
    ::= { wtWebGraphAnalogIn57642GraphicsBase 2 }
    
wtWebGraphAnalogIn57642GraphicsBaseHeight OBJECT-TYPE
        SYNTAX INTEGER 
        ACCESS read-write
        STATUS mandatory
        DESCRIPTION
            "Defines the height of the graphic in pixels."
        ::= { wtWebGraphAnalogIn57642GraphicsBase 3 }

wtWebGraphAnalogIn57642GraphicsBaseFrameColor OBJECT-TYPE
    SYNTAX OCTET STRING (SIZE(3))
    ACCESS read-write
    STATUS mandatory
    DESCRIPTION
        "Frame color definition in RGB."
    ::= { wtWebGraphAnalogIn57642GraphicsBase 4 }

wtWebGraphAnalogIn57642GraphicsBaseBackgroundColor OBJECT-TYPE
    SYNTAX OCTET STRING (SIZE(3))
    ACCESS read-write
    STATUS mandatory
    DESCRIPTION
        "Background color definition in RGB."
    ::= { wtWebGraphAnalogIn57642GraphicsBase 5 }
    
wtWebGraphAnalogIn57642GraphicsBasePollingrate OBJECT-TYPE
        SYNTAX INTEGER 
        ACCESS read-write
        STATUS mandatory
        DESCRIPTION
            "Defines the pollingrate in seconds, 
            which defines the refreshing intervall of the graphic."
        ::= { wtWebGraphAnalogIn57642GraphicsBase 6 }
   
-- wtWebGraphAnalogIn57642GraphicsSelect Group
----------------------------

wtWebGraphAnalogIn57642GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebGraphAnalogIn57642GraphicsSelect 1 }   
    
wtWebGraphAnalogIn57642GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
     ::= { wtWebGraphAnalogIn57642GraphicsSelect 2 }   

-- Graph Sensor Color Table

wtWebGraphAnalogIn57642SensorColor2Table OBJECT-TYPE
    SYNTAX SEQUENCE OF WtWebGraphAnalogIn57642SensorColor2Entry
    ACCESS not-accessible
    STATUS mandatory
    DESCRIPTION
        "List of sensor colors for the praphical presentation."
    ::= { wtWebGraphAnalogIn57642GraphicsSelect 3 }

wtWebGraphAnalogIn57642SensorColor2Entry OBJECT-TYPE
    SYNTAX WtWebGraphAnalogIn57642SensorColor2Entry
    ACCESS not-accessible
    STATUS mandatory
    DESCRIPTION
        "Numbers of the sensors."
    INDEX  { wtWebGraphAnalogIn57642SensorNo }
    ::= { wtWebGraphAnalogIn57642SensorColor2Table 1 }

WtWebGraphAnalogIn57642SensorColor2Entry ::= SEQUENCE {
    wtWebGraphAnalogIn57642GraphicsSensorColor OCTET STRING,
    wtWebGraphAnalogIn57642GraphicsSelectScale OCTET STRING
}

wtWebGraphAnalogIn57642GraphicsSensorColor OBJECT-TYPE
    SYNTAX OCTET STRING (SIZE(3))
    ACCESS read-write
    STATUS mandatory
    DESCRIPTION
        "Color of the sensors at the praphical presention."
    ::= { wtWebGraphAnalogIn57642SensorColor2Entry 1 }
    
wtWebGraphAnalogIn57642GraphicsSelectScale OBJECT-TYPE
    SYNTAX OCTET STRING 
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3  : Use Scale 4
                Bit 4-7: unused"
    ::= { wtWebGraphAnalogIn57642SensorColor2Entry 2 }
   
-- wtWebGraphAnalogIn57642GraphicsScale Group
----------------------------

wtWebGraphAnalogIn57642GraphicsScaleAutoScaleEnable OBJECT-TYPE
    SYNTAX OCTET STRING 
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3  : Scale 4 Auto scale enable
                Bit 4-7: unused"
    ::= { wtWebGraphAnalogIn57642GraphicsScale 1 }


wtWebGraphAnalogIn57642GraphicsScaleAutoFitEnable OBJECT-TYPE
    SYNTAX OCTET STRING 
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3  : Scale 4 Auto fit enable
                Bit 4-7: unused"
    ::= { wtWebGraphAnalogIn57642GraphicsScale 2 }

wtWebGraphAnalogIn57642GraphicsScale1Min OBJECT-TYPE
    SYNTAX INTEGER
    ACCESS read-only
    STATUS mandatory
    DESCRIPTION
        "Scale 1: Minimum."
    ::= { wtWebGraphAnalogIn57642GraphicsScale 3 }
   
wtWebGraphAnalogIn57642GraphicsScale2Min OBJECT-TYPE
    SYNTAX INTEGER
    ACCESS read-only
    STATUS mandatory
    DESCRIPTION
        "Scale 2: Minimum."
    ::= { wtWebGraphAnalogIn57642GraphicsScale 4 }

wtWebGraphAnalogIn57642GraphicsScale3Min OBJECT-TYPE
    SYNTAX INTEGER
    ACCESS read-only
    STATUS mandatory
    DESCRIPTION
        "Scale 3: Minimum."
    ::= { wtWebGraphAnalogIn57642GraphicsScale 5 }

wtWebGraphAnalogIn57642GraphicsScale4Min OBJECT-TYPE
    SYNTAX INTEGER
    ACCESS read-only
    STATUS mandatory
    DESCRIPTION
        "Scale 4: Minimum."
    ::= { wtWebGraphAnalogIn57642GraphicsScale 6 }

wtWebGraphAnalogIn57642GraphicsScale1Max OBJECT-TYPE
    SYNTAX INTEGER
    ACCESS read-only
    STATUS mandatory
    DESCRIPTION
        "Scale 1: Maximum."
    ::= { wtWebGraphAnalogIn57642GraphicsScale 7 }

wtWebGraphAnalogIn57642GraphicsScale2Max OBJECT-TYPE
    SYNTAX INTEGER
    ACCESS read-only
    STATUS mandatory
    DESCRIPTION
        "Scale 2: Maximum."
    ::= { wtWebGraphAnalogIn57642GraphicsScale 8 }

wtWebGraphAnalogIn57642GraphicsScale3Max OBJECT-TYPE
    SYNTAX INTEGER
    ACCESS read-only
    STATUS mandatory
    DESCRIPTION
        "Scale 3: Maximum."
    ::= { wtWebGraphAnalogIn57642GraphicsScale 9 }

wtWebGraphAnalogIn57642GraphicsScale4Max OBJECT-TYPE
    SYNTAX INTEGER
    ACCESS read-only
    STATUS mandatory
    DESCRIPTION
        "Scale 4: Maximum."
    ::= { wtWebGraphAnalogIn57642GraphicsScale 10 }

wtWebGraphAnalogIn57642GraphicsScale1Unit OBJECT-TYPE
    SYNTAX OCTET STRING
    ACCESS read-only
    STATUS mandatory
    DESCRIPTION
        "Scale 1: Unit."
    ::= { wtWebGraphAnalogIn57642GraphicsScale 11 }

wtWebGraphAnalogIn57642GraphicsScale2Unit OBJECT-TYPE
    SYNTAX OCTET STRING
    ACCESS read-only
    STATUS mandatory
    DESCRIPTION
        "Scale 2: Unit."
    ::= { wtWebGraphAnalogIn57642GraphicsScale 12 }

wtWebGraphAnalogIn57642GraphicsScale3Unit OBJECT-TYPE
    SYNTAX OCTET STRING
    ACCESS read-only
    STATUS mandatory
    DESCRIPTION
        "Scale 3: Unit."
    ::= { wtWebGraphAnalogIn57642GraphicsScale 13 }

wtWebGraphAnalogIn57642GraphicsScale4Unit OBJECT-TYPE
    SYNTAX OCTET STRING
    ACCESS read-only
    STATUS mandatory
    DESCRIPTION
        "Scale 4: Unit."
    ::= { wtWebGraphAnalogIn57642GraphicsScale 14 }    
    
-- wtWebGraphAnalogIn57642Ports Group
----------------------------

-- Table

wtWebGraphAnalogIn57642PortTable OBJECT-TYPE
    SYNTAX SEQUENCE OF WtWebGraphAnalogIn57642PortEntry
    ACCESS not-accessible
    STATUS mandatory
    DESCRIPTION
        "List of settings depending on the sensor number."
    ::= { wtWebGraphAnalogIn57642Ports 1 }

wtWebGraphAnalogIn57642PortEntry OBJECT-TYPE
    SYNTAX WtWebGraphAnalogIn57642PortEntry
    ACCESS not-accessible
    STATUS mandatory
    DESCRIPTION
        "Sensor parameters for the individual sensors."
    INDEX  { wtWebGraphAnalogIn57642SensorNo }
    ::= { wtWebGraphAnalogIn57642PortTable 1 }

WtWebGraphAnalogIn57642PortEntry ::= SEQUENCE {
    wtWebGraphAnalogIn57642PortName		OCTET STRING,
    wtWebGraphAnalogIn57642PortText		OCTET STRING,
    wtWebGraphAnalogIn57642PortOffset1		OCTET STRING,
    wtWebGraphAnalogIn57642SetPoint1		OCTET STRING,
    wtWebGraphAnalogIn57642PortOffset2		OCTET STRING,
    wtWebGraphAnalogIn57642SetPoint2		OCTET STRING,
    wtWebGraphAnalogIn57642PortComment		OCTET STRING,
    wtWebGraphAnalogIn57642PortSensorSelect	OCTET STRING,
    wtWebGraphAnalogIn57642PortUnit		OCTET STRING,
    wtWebGraphAnalogIn57642PortScale0		OCTET STRING,
    wtWebGraphAnalogIn57642PortScale100		OCTET STRING
}

wtWebGraphAnalogIn57642PortName OBJECT-TYPE
    SYNTAX OCTET STRING 
    ACCESS read-write
    STATUS mandatory
    DESCRIPTION
        "Name of the sensor."
    ::= { wtWebGraphAnalogIn57642PortEntry 1 }

wtWebGraphAnalogIn57642PortText OBJECT-TYPE
    SYNTAX OCTET STRING 
    ACCESS read-write
    STATUS mandatory
    DESCRIPTION
        "Description of the sensor."
    ::= { wtWebGraphAnalogIn57642PortEntry 2 }

wtWebGraphAnalogIn57642PortOffset1 OBJECT-TYPE
    SYNTAX OCTET STRING 
    ACCESS read-write
    STATUS mandatory
    DESCRIPTION
        "Offset calibration: Offset in degrees with maximum 2 decimal places at set point 1."
    ::= { wtWebGraphAnalogIn57642PortEntry 3 }

wtWebGraphAnalogIn57642SetPoint1 OBJECT-TYPE
    SYNTAX OCTET STRING 
    ACCESS read-write
    STATUS mandatory
    DESCRIPTION
        "Offset calibration: set point 1 in degrees with maximum 2 decimal places."
    ::= { wtWebGraphAnalogIn57642PortEntry 4 }

wtWebGraphAnalogIn57642PortOffset2 OBJECT-TYPE
    SYNTAX OCTET STRING 
    ACCESS read-write
    STATUS mandatory
    DESCRIPTION
        "Offset calibration: Offset in degrees with maximum 2 decimal places at set point 2."
    ::= { wtWebGraphAnalogIn57642PortEntry 5 }

wtWebGraphAnalogIn57642SetPoint2 OBJECT-TYPE
    SYNTAX OCTET STRING 
    ACCESS read-write
    STATUS mandatory
    DESCRIPTION
        "Offset calibration: set point 2 in degrees with maximum 2 decimal places."
    ::= { wtWebGraphAnalogIn57642PortEntry 6 }

wtWebGraphAnalogIn57642PortComment OBJECT-TYPE
    SYNTAX OCTET STRING 
    ACCESS read-write
    STATUS mandatory
    DESCRIPTION
        "Offset calibration: informations of date, name of operator, reference devices."
    ::= { wtWebGraphAnalogIn57642PortEntry 7 }   

wtWebGraphAnalogIn57642PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-20mA (default)
		Bit 1  :	4-20mA
		Bit 2  :	Disconnect
        	Bit 3-7:	unused
        
        Binary coded options for sensor 2:
	Octet 1: unused
	Octet 2: unused
	Octet 3: unused
	Octet 4:
		Bit 0  :	0-20mA (default)
		Bit 1  :	4-20mA
		Bit 2  :	Disconnect
        	Bit 3-7:	unused"
    ::= { wtWebGraphAnalogIn57642PortEntry 8 }    
    
wtWebGraphAnalogIn57642PortUnit OBJECT-TYPE
    SYNTAX OCTET STRING 
    ACCESS read-write
    STATUS mandatory
    DESCRIPTION
        "User scale: displayed unit."
    ::= { wtWebGraphAnalogIn57642PortEntry 9 }   
    
wtWebGraphAnalogIn57642PortScale0 OBJECT-TYPE
    SYNTAX OCTET STRING 
    ACCESS read-write
    STATUS mandatory
    DESCRIPTION
        "User scale: displayed value in 1/1000 at 0% full scale range.
        Range: -999999.999 to 999999.999"
    ::= { wtWebGraphAnalogIn57642PortEntry 10 }   

wtWebGraphAnalogIn57642PortScale100 OBJECT-TYPE
    SYNTAX OCTET STRING 
    ACCESS read-write
    STATUS mandatory
    DESCRIPTION
        "User scale: displayed value in 1/1000 at 100% full scale range.
        Range: -999999.999 to 999999.999"
    ::= { wtWebGraphAnalogIn57642PortEntry 11 }   

-- wtWebGraphAnalogIn57642Manufact Group
----------------------------

wtWebGraphAnalogIn57642MfName OBJECT-TYPE
    SYNTAX OCTET STRING 
    ACCESS read-write
    STATUS mandatory
    DESCRIPTION
        "Manufacturer company name"
    ::= { wtWebGraphAnalogIn57642Manufact 1 }

wtWebGraphAnalogIn57642MfAddr OBJECT-TYPE
    SYNTAX OCTET STRING 
    ACCESS read-write
    STATUS mandatory
    DESCRIPTION
        "Manufacturer address."
    ::= { wtWebGraphAnalogIn57642Manufact 2 }

wtWebGraphAnalogIn57642MfHotline OBJECT-TYPE
    SYNTAX OCTET STRING 
    ACCESS read-write
    STATUS mandatory
    DESCRIPTION
        "Manufacturer hotline."
    ::= { wtWebGraphAnalogIn57642Manufact 3 }

wtWebGraphAnalogIn57642MfInternet OBJECT-TYPE
    SYNTAX OCTET STRING 
    ACCESS read-write
    STATUS mandatory
    DESCRIPTION
        "Manufacturer Internet address."
    ::= { wtWebGraphAnalogIn57642Manufact 4 }

wtWebGraphAnalogIn57642MfDeviceTyp OBJECT-TYPE
    SYNTAX OCTET STRING 
    ACCESS read-write
    STATUS mandatory
    DESCRIPTION
        "Manufacturer device name (model number)."
    ::= { wtWebGraphAnalogIn57642Manufact 5 }

wtWebGraphAnalogIn57642MfOrderNo OBJECT-TYPE
    SYNTAX OCTET STRING 
    ACCESS read-write
    STATUS mandatory
    DESCRIPTION
        "Manufacturer part number."
    ::= { wtWebGraphAnalogIn57642Manufact 6 }

-- wtWebGraphAnalogIn57642Diag Group
----------------------------

wtWebGraphAnalogIn57642DiagErrorCount OBJECT-TYPE
    SYNTAX INTEGER
    ACCESS read-only
    STATUS mandatory
    DESCRIPTION
        "Number of entries in the error memory."
    ::= { wtWebGraphAnalogIn57642Diag 1 }

wtWebGraphAnalogIn57642DiagBinaryError OBJECT-TYPE
    SYNTAX OCTET STRING 
    ACCESS read-only
    STATUS mandatory
    DESCRIPTION
        "Error causes coded bit-by-bit."
    ::= { wtWebGraphAnalogIn57642Diag 2 }

wtWebGraphAnalogIn57642DiagErrorIndex OBJECT-TYPE
    SYNTAX INTEGER
    ACCESS read-write
    STATUS mandatory
    DESCRIPTION
        "The value of this variable is used as an index to read 
        an error massege from wtWebGraphAnalogIn57642DiagErrorMessage.
        Errors are numbered from 1 to wtWebGraphAnalogIn57642DiagErrorCount.
        Writing a valid value into this variable, making the appropriate 
        message readable from wtWebGraphAnalogIn57642DiagErrorMessage."
    ::= { wtWebGraphAnalogIn57642Diag 3 }

wtWebGraphAnalogIn57642DiagErrorMessage OBJECT-TYPE
    SYNTAX OCTET STRING 
    ACCESS read-only
    STATUS mandatory
    DESCRIPTION
        "Using wtWebGraphAnalogIn57642DiagErrorIndex as an index, the appropriate message is available."
    ::= { wtWebGraphAnalogIn57642Diag 4 }
    
wtWebGraphAnalogIn57642DiagErrorClear OBJECT-TYPE
    SYNTAX INTEGER
    ACCESS write-only
    STATUS mandatory
    DESCRIPTION
        "Writing 1 into this variable clears all diagnosis messages."
    ::= { wtWebGraphAnalogIn57642Diag 5 }

-- TRAP DEFINITIONS

-- Diese SNMP-Traps werden gesendet, wenn die Alarmtriggerbedingungen zutreffen 

wtWebGraphAnalogIn57642Alert1 TRAP-TYPE
    ENTERPRISE  wtWebGraphAnalogIn57642
    VARIABLES   { wtWebGraphAnalogIn57642AlarmTrapText }
    DESCRIPTION
        "This SNMP trap is generated when Alarm 1 was triggered,
        SNMP trap enable is set and
        SNMP is enabled."
    -- NMS trap annotation
    --#TYPE "Thermo-Hygrometer Alarm 1"
    --#SUMMARY "Alarm 1: %s"
    --#ARGUMENTS {0}
    --#SEVERITY INFORMATIONAL
    --#TIMEINDEX 99
    --#STATE OPERATIONAL    
    ::= 31

wtWebGraphAnalogIn57642Alert2 TRAP-TYPE
    ENTERPRISE  wtWebGraphAnalogIn57642
    VARIABLES   { wtWebGraphAnalogIn57642AlarmTrapText }
    DESCRIPTION
        "This SNMP trap is generated when Alarm 2 was triggered,
        SNMP trap enable is set and
        SNMP is enabled."
    -- NMS trap annotation
    --#TYPE "Thermo-Hygrometer Alarm 2"
    --#SUMMARY "Alarm 2: %s"
    --#ARGUMENTS {0}
    --#SEVERITY INFORMATIONAL
    --#TIMEINDEX 99
    --#STATE OPERATIONAL    
    ::= 32

wtWebGraphAnalogIn57642Alert3 TRAP-TYPE
    ENTERPRISE  wtWebGraphAnalogIn57642
    VARIABLES   { wtWebGraphAnalogIn57642AlarmTrapText }
    DESCRIPTION
        "This SNMP trap is generated when Alarm 3 was triggered,
        SNMP trap enable is set and
        SNMP is enabled."
    -- NMS trap annotation
    --#TYPE "Thermo-Hygrometer Alarm 3"
    --#SUMMARY "Alarm 3: %s"
    --#ARGUMENTS {0}
    --#SEVERITY INFORMATIONAL
    --#TIMEINDEX 99
    --#STATE OPERATIONAL    
    ::= 33

wtWebGraphAnalogIn57642Alert4 TRAP-TYPE
    ENTERPRISE  wtWebGraphAnalogIn57642
    VARIABLES   { wtWebGraphAnalogIn57642AlarmTrapText }
    DESCRIPTION
        "This SNMP trap is generated when Alarm 4 was triggered,
        SNMP trap enable is set and
        SNMP is enabled."
    -- NMS trap annotation
    --#TYPE "Thermo-Hygrometer Alarm 4"
    --#SUMMARY "Alarm 4: %s"
    --#ARGUMENTS {0}
    --#SEVERITY INFORMATIONAL
    --#TIMEINDEX 99
    --#STATE OPERATIONAL    
    ::= 34

wtWebGraphAnalogIn57642Alert5 TRAP-TYPE
    ENTERPRISE  wtWebGraphAnalogIn57642
    VARIABLES   { wtWebGraphAnalogIn57642AlarmTrapText }
    DESCRIPTION
        "This SNMP trap is generated when Alarm 5 was triggered,
        SNMP trap enable is set and
        SNMP is enabled."
    -- NMS trap annotation
    --#TYPE "Thermo-Hygrometer Alarm 5"
    --#SUMMARY "Alarm 5: %s"
    --#ARGUMENTS {0}
    --#SEVERITY INFORMATIONAL
    --#TIMEINDEX 99
    --#STATE OPERATIONAL    
    ::= 35

wtWebGraphAnalogIn57642Alert6 TRAP-TYPE
    ENTERPRISE  wtWebGraphAnalogIn57642
    VARIABLES   { wtWebGraphAnalogIn57642AlarmTrapText }
    DESCRIPTION
        "This SNMP trap is generated when Alarm 6 was triggered,
        SNMP trap enable is set and
        SNMP is enabled."
    -- NMS trap annotation
    --#TYPE "Thermo-Hygrometer Alarm 6"
    --#SUMMARY "Alarm 6: %s"
    --#ARGUMENTS {0}
    --#SEVERITY INFORMATIONAL
    --#TIMEINDEX 99
    --#STATE OPERATIONAL    
    ::= 36

wtWebGraphAnalogIn57642Alert7 TRAP-TYPE
    ENTERPRISE  wtWebGraphAnalogIn57642
    VARIABLES   { wtWebGraphAnalogIn57642AlarmTrapText }
    DESCRIPTION
        "This SNMP trap is generated when Alarm 7 was triggered,
        SNMP trap enable is set and
        SNMP is enabled."
    -- NMS trap annotation
    --#TYPE "Thermo-Hygrometer Alarm 7"
    --#SUMMARY "Alarm 7: %s"
    --#ARGUMENTS {0}
    --#SEVERITY INFORMATIONAL
    --#TIMEINDEX 99
    --#STATE OPERATIONAL    
    ::= 37

wtWebGraphAnalogIn57642Alert8 TRAP-TYPE
    ENTERPRISE  wtWebGraphAnalogIn57642
    VARIABLES   { wtWebGraphAnalogIn57642AlarmTrapText }
    DESCRIPTION
        "This SNMP trap is generated when Alarm 8 was triggered,
        SNMP trap enable is set and
        SNMP is enabled."
    -- NMS trap annotation
    --#TYPE "Thermo-Hygrometer Alarm 8"
    --#SUMMARY "Alarm 8: %s"
    --#ARGUMENTS {0}
    --#SEVERITY INFORMATIONAL
    --#TIMEINDEX 99
    --#STATE OPERATIONAL    
    ::= 38

    
wtWebGraphAnalogIn57642Alert9 TRAP-TYPE
    ENTERPRISE  wtWebGraphAnalogIn57642
    VARIABLES   { wtWebGraphAnalogIn57642AlarmClearTrapText }
    DESCRIPTION
        "This SNMP trap is generated when Alarm 1 was cleared,
        SNMP trap enable is set and
        SNMP is enabled."
    -- NMS trap annotation
    --#TYPE "Thermo-Hygrometer Release Alarm 1"
    --#SUMMARY "Release Alarm 1: %s"
    --#ARGUMENTS {0}
    --#SEVERITY INFORMATIONAL
    --#TIMEINDEX 99
    --#STATE OPERATIONAL    
    ::= 91

wtWebGraphAnalogIn57642Alert10 TRAP-TYPE
    ENTERPRISE  wtWebGraphAnalogIn57642
    VARIABLES   { wtWebGraphAnalogIn57642AlarmClearTrapText }
    DESCRIPTION
        "This SNMP trap is generated when Alarm 2 was cleared,
        SNMP trap enable is set and
        SNMP is enabled."
    -- NMS trap annotation
    --#TYPE "Thermo-Hygrometer Release Alarm 2"
    --#SUMMARY "Release Alarm 2: %s"
    --#ARGUMENTS {0}
    --#SEVERITY INFORMATIONAL
    --#TIMEINDEX 99
    --#STATE OPERATIONAL    
    ::= 92

wtWebGraphAnalogIn57642Alert11 TRAP-TYPE
    ENTERPRISE  wtWebGraphAnalogIn57642
    VARIABLES   { wtWebGraphAnalogIn57642AlarmClearTrapText }
    DESCRIPTION
        "This SNMP trap is generated when Alarm 3 was cleared,
        SNMP trap enable is set and
        SNMP is enabled."
    -- NMS trap annotation
    --#TYPE "Thermo-Hygrometer Release Alarm 3"
    --#SUMMARY "Release Alarm 3: %s"
    --#ARGUMENTS {0}
    --#SEVERITY INFORMATIONAL
    --#TIMEINDEX 99
    --#STATE OPERATIONAL    
    ::= 93

wtWebGraphAnalogIn57642Alert12 TRAP-TYPE
    ENTERPRISE  wtWebGraphAnalogIn57642
    VARIABLES   { wtWebGraphAnalogIn57642AlarmClearTrapText }
    DESCRIPTION
        "This SNMP trap is generated when Alarm 4 was cleared,
        SNMP trap enable is set and
        SNMP is enabled."
    -- NMS trap annotation
    --#TYPE "Thermo-Hygrometer Release Alarm 4"
    --#SUMMARY "Release Alarm 4: %s"
    --#ARGUMENTS {0}
    --#SEVERITY INFORMATIONAL
    --#TIMEINDEX 99
    --#STATE OPERATIONAL    
    ::= 94

wtWebGraphAnalogIn57642Alert13 TRAP-TYPE
    ENTERPRISE  wtWebGraphAnalogIn57642
    VARIABLES   { wtWebGraphAnalogIn57642AlarmClearTrapText }
    DESCRIPTION
        "This SNMP trap is generated when Alarm 5 was cleared,
        SNMP trap enable is set and
        SNMP is enabled."
    -- NMS trap annotation
    --#TYPE "Thermo-Hygrometer Release Alarm 5"
    --#SUMMARY "Release Alarm 5: %s"
    --#ARGUMENTS {0}
    --#SEVERITY INFORMATIONAL
    --#TIMEINDEX 99
    --#STATE OPERATIONAL    
    ::= 95

wtWebGraphAnalogIn57642Alert14 TRAP-TYPE
    ENTERPRISE  wtWebGraphAnalogIn57642
    VARIABLES   { wtWebGraphAnalogIn57642AlarmClearTrapText }
    DESCRIPTION
        "This SNMP trap is generated when Alarm 6 was cleared,
        SNMP trap enable is set and
        SNMP is enabled."
    -- NMS trap annotation
    --#TYPE "Thermo-Hygrometer Release Alarm 6"
    --#SUMMARY "Release Alarm 6: %s"
    --#ARGUMENTS {0}
    --#SEVERITY INFORMATIONAL
    --#TIMEINDEX 99
    --#STATE OPERATIONAL    
    ::= 96

wtWebGraphAnalogIn57642Alert15 TRAP-TYPE
    ENTERPRISE  wtWebGraphAnalogIn57642
    VARIABLES   { wtWebGraphAnalogIn57642AlarmClearTrapText }
    DESCRIPTION
        "This SNMP trap is generated when Alarm 7 was cleared,
        SNMP trap enable is set and
        SNMP is enabled."
    -- NMS trap annotation
    --#TYPE "Thermo-Hygrometer Release Alarm 7"
    --#SUMMARY "Release Alarm 7: %s"
    --#ARGUMENTS {0}
    --#SEVERITY INFORMATIONAL
    --#TIMEINDEX 99
    --#STATE OPERATIONAL    
    ::= 97

wtWebGraphAnalogIn57642Alert16 TRAP-TYPE
    ENTERPRISE  wtWebGraphAnalogIn57642
    VARIABLES   { wtWebGraphAnalogIn57642AlarmClearTrapText }
    DESCRIPTION
        "This SNMP trap is generated when Alarm 8 was cleared,
        SNMP trap enable is set and
        SNMP is enabled."
    -- NMS trap annotation
    --#TYPE "Thermo-Hygrometer Release Alarm 8"
    --#SUMMARY "Release Alarm 8: %s"
    --#ARGUMENTS {0}
    --#SEVERITY INFORMATIONAL
    --#TIMEINDEX 99
    --#STATE OPERATIONAL    
    ::= 98

wtWebGraphAnalogIn57642AlertDiag TRAP-TYPE
    ENTERPRISE  wtWebGraphAnalogIn57642
    VARIABLES   { 	
    		wtWebGraphAnalogIn57642DiagErrorIndex,
    	  	wtWebGraphAnalogIn57642DiagErrorMessage
    		}
    DESCRIPTION
        "This SNMP trap is generated when a diagnosis/error message was triggered,
        SNMP trap enable is set and
        SNMP is enabled."
    -- NMS trap annotation
    --#TYPE "Thermo-Hygrometer Diagnose Error"
    --#SUMMARY "Diagnose error index: %d, Message: %s."
    --#ARGUMENTS {0,1}
    --#SEVERITY MAJOR
    --#TIMEINDEX 99
    --#STATE DEGRADED    
    ::= 110 
 
END
