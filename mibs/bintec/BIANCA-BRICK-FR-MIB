-- This file is corresponding to Release 9.1.10.101 from 2014/08/11 00:00:00


-- (C)opyright 1991-2014 bintec elmeg GmbH, All Rights Reserved
--  $RCSfile: mibfr,v $ 
-- $Revision: 1.15 $ 

BIANCA-BRICK-FR-MIB DEFINITIONS ::= BEGIN

        IMPORTS
            Counter, enterprises
                FROM RFC1155-SMI
 
            OBJECT-TYPE
                FROM RFC-1212;

    bintec      OBJECT IDENTIFIER ::= { enterprises 272 }
    bibo        OBJECT IDENTIFIER ::= { bintec 4 }
    fr          OBJECT IDENTIFIER
        ::= { bibo 13 }


	frMprTable OBJECT-TYPE
	    SYNTAX  SEQUENCE OF FrMprEntry
	    ACCESS  not-accessible
	    STATUS  mandatory
	    DESCRIPTION
		"This table contains an entry for each frame relay DCE
		 virtual interface. This interface is called virtual
		 because it does not necessarily reflect to a single
		 hardware interface; it is possible to either narrow
		 (many hardware interfaces looking as a single virtual)
		 or widen (a single hardware interface with several VCs
		 is mapped to several virtual interfaces) the interface.

		 Entries in this table are created manually and will result
		 to the creation of a multiprotocol routing interface in
		 the ifTable. This interface can than be used by higher
		 level protocols like ip, ipx and bridging.

		 The object frMprIfIndex shall be set to 0 for creation
		 of new entries. The BRICK will allocate the next free
		 interface index and assign it to frMprIfIndex.

		 Rows of this table can be deleted by setting the object
		 frMprEncapsulation to the value delete.
		 "
	::= { fr 1 }

	frMprEntry OBJECT-TYPE
	    SYNTAX  FrMprEntry
	    ACCESS  not-accessible
	    STATUS  mandatory
	    DESCRIPTION
		""
	    INDEX   { frMprIfIndex }
	::= { frMprTable 1 }

	FrMprEntry ::=
	    SEQUENCE {
		frMprIfIndex				INTEGER,
		frMprMtu				INTEGER,
		frMprEncapsulation			INTEGER,
		frMprIfcType				INTEGER,
		frMprInverseArp				INTEGER
	    }

	frMprIfIndex OBJECT-TYPE
	    SYNTAX  INTEGER 
	    ACCESS  read-write
	    STATUS  mandatory

	    DESCRIPTION
		"This object contains an interface index and assigns the
		 row to an entry in ifTable. When creating new entries
		 in the table, the value of this object shall be set to 0.
		 The next free ifIndex value is than allocated
		 by the BRICK and assigned to the object. At the same
		 time a new interface is created in the IfTable."
	    DEFVAL { 0 }
	::= { frMprEntry 1 }

	frMprMtu OBJECT-TYPE
	    SYNTAX  INTEGER (576..8180) 
	    ACCESS  read-write
	    STATUS  mandatory

	    DESCRIPTION
		"The Maximum transfer unit to be used with the interface
		 (see also ifMtu)."
	    DEFVAL { 1500 }
	::= { frMprEntry 2 }

	frMprEncapsulation OBJECT-TYPE
	    SYNTAX  INTEGER { 
		mpr(1), delete(7)
	    } 
	    ACCESS  read-write
	    STATUS  mandatory

	    DESCRIPTION
		"This object specifies the encapsulation method to be used.

		 If this object is set to mpr, the encapsulation method
		 described in Q933a is used for the protocols IP, IPX
		 and transparent bridging. This encapsulation is also
		 explained in RFC 1490.
		"
	    DEFVAL { mpr }
	::= { frMprEntry 3 }

	frMprIfcType OBJECT-TYPE
	    SYNTAX  INTEGER {
		multipoint(1), point-to-point(2)
	    }
	    ACCESS  read-write
	    STATUS  mandatory

	    DESCRIPTION
		"This object specifies wether the interface is a 
		 multipoint(1) or a point-to-point(2) interface."
	    DEFVAL { point-to-point }
	::= { frMprEntry 4 }

	frMprInverseArp OBJECT-TYPE
	    SYNTAX  INTEGER {
		enabled(1), disabled(2)
	    }
	    ACCESS  read-write
	    STATUS  mandatory

	    DESCRIPTION
		"This object specifies the use of Inverse Arp (as
		 described in RFC 1490) to automatically detect
		 upper layer network addresses."
	    DEFVAL { disabled }
	::= { frMprEntry 5 }


END

-- public MIB

     RFC1315-MIB DEFINITIONS ::= BEGIN

     IMPORTS
             OBJECT-TYPE
                     FROM RFC-1212
             transmission
                     FROM RFC1213-MIB
             Counter, TimeTicks
                     FROM RFC1155-SMI
             TRAP-TYPE
                     FROM RFC-1215;

     --  Frame Relay DTE MIB


     frpublic     OBJECT IDENTIFIER
	::= { transmission 32 }

     --  Data Link Connection Management Interface

     --      The variables that configure the DLC Management Interface.

     frDlcmiTable OBJECT-TYPE
         SYNTAX   SEQUENCE OF FrDlcmiEntry
         ACCESS   not-accessible
         STATUS   mandatory
         DESCRIPTION
            "The Parameters for the Data Link Connection Management
            Interface for the frame relay service on this
            interface."
         REFERENCE
            "Draft American National Standard T1.617-1991, Annex D"
         ::= { frpublic 1 }

         frDlcmiEntry OBJECT-TYPE
             SYNTAX   FrDlcmiEntry
             ACCESS   not-accessible
             STATUS   mandatory
             DESCRIPTION
                "The Parameters for a particular Data Link Con-
                nection Management Interface."
            INDEX { frDlcmiIfIndex }
            ::= { frDlcmiTable 1 }

         FrDlcmiEntry ::=
             SEQUENCE {
                 frDlcmiIfIndex
                     INTEGER,
                 frDlcmiState
                     INTEGER,
                 frDlcmiAddress
                     INTEGER,
                 frDlcmiAddressLen
                     INTEGER,
                 frDlcmiPollingInterval
                     INTEGER,
                 frDlcmiFullEnquiryInterval
                     INTEGER,
                 frDlcmiErrorThreshold
                     INTEGER,
                 frDlcmiMonitoredEvents
                     INTEGER,
                 frDlcmiMaxSupportedVCs
                     INTEGER,
                 frDlcmiMulticast
                     INTEGER,
		 frDlcmiDceIdleInterval
                     INTEGER,
		 frDlcmiDceErrorThreshold
                     INTEGER,
		 frDlcmiDceMonitoredEvents
                     INTEGER,
		 frDlcmiMode
		     INTEGER,
		 frDlcmiDefaultRouteIfIndex
		     INTEGER
         }



         frDlcmiIfIndex OBJECT-TYPE
             SYNTAX   INTEGER
             ACCESS   read-only
             STATUS   mandatory
             DESCRIPTION
                "The ifIndex value of the  corresponding  ifEn-
                try."
            ::= { frDlcmiEntry 1 }

         frDlcmiState OBJECT-TYPE
             SYNTAX INTEGER {
                 noLmiConfigured (1),
                 lmiRev1         (2),
                 ansiT1-617-D    (3),
                 ansiT1-617-B    (4),
                 q933a           (5),
                 original-lmi    (6)
             }
             ACCESS   read-write
             STATUS   mandatory
             DESCRIPTION
                "This variable states which Data  Link  Connec-
                tion Management scheme is active (and by impli-
                cation, what DLCI it uses) on the  Frame  Relay
                interface."
             REFERENCE
               "Draft American National Standard T1.617-1991"
             DEFVAL { noLmiConfigured }
           ::= { frDlcmiEntry 2 }



         frDlcmiAddress OBJECT-TYPE
             SYNTAX      INTEGER {
                         q921           (1),  -- 13 bit DLCI
                         q922March90    (2),  -- 11 bit DLCI
                         q922November90 (3),  -- 10 bit DLCI
                         q922           (4)   -- Final Standard
             }
             ACCESS  read-write
             STATUS  mandatory
             DESCRIPTION
                "This variable states which address  format  is
                in use on the Frame Relay interface."
             DEFVAL { q922 }
            ::= { frDlcmiEntry 3 }


         frDlcmiAddressLen OBJECT-TYPE
             SYNTAX  INTEGER {
                     two-octets (2),
                     three-octets (3),
                     four-octets (4)
             }
             ACCESS  read-write
             STATUS  mandatory
             DESCRIPTION
                "This variable states which address  length  in
                octets.  In the case of Q922 format, the length
                indicates the entire length of the address  in-
                cluding the control portion."
             DEFVAL { 2 }
            ::= { frDlcmiEntry 4 }


         frDlcmiPollingInterval OBJECT-TYPE
             SYNTAX   INTEGER (5..30)
             ACCESS   read-write
             STATUS   mandatory
             DESCRIPTION
                "This is the number of seconds between  succes-
                sive status enquiry messages."
            REFERENCE
               "Draft American National  Standard  T1.617-1991,
               Section D.7 Timer T391."
           DEFVAL { 10 }
           ::= { frDlcmiEntry 5 }


         frDlcmiFullEnquiryInterval OBJECT-TYPE
             SYNTAX   INTEGER (1..255)
             ACCESS   read-write
             STATUS   mandatory
             DESCRIPTION
                "Number of status enquiry intervals  that  pass
                before  issuance  of a full status enquiry mes-
                sage."
            REFERENCE
               "Draft American National  Standard  T1.617-1991,
               Section D.7 Counter N391."
           DEFVAL { 6 }
           ::= { frDlcmiEntry 6 }



         frDlcmiErrorThreshold OBJECT-TYPE
             SYNTAX   INTEGER (1..10)
             ACCESS   read-write
             STATUS   mandatory
             DESCRIPTION
                "This  is  the  maximum  number  of  unanswered
                Status Enquiries the equipment shall accept be-
                fore declaring the interface down."
            REFERENCE
               "Draft American National  Standard  T1.617-1991,
               Section D.5.1 Counter N392."
           DEFVAL { 3 }
           ::= { frDlcmiEntry 7 }



         frDlcmiMonitoredEvents OBJECT-TYPE
             SYNTAX   INTEGER (1..10)
             ACCESS   read-write
             STATUS   mandatory
             DESCRIPTION
                "This is the number of status polling intervals
                over which the error threshold is counted.  For
                example, if within 'MonitoredEvents' number  of
                events  the  station  receives 'ErrorThreshold'
                number of errors, the interface  is  marked  as
                down."
            REFERENCE
               "Draft American National  Standard  T1.617-1991,
               Section D.5.2 Counter N393."
           DEFVAL { 4 }
           ::= { frDlcmiEntry 8 }



         frDlcmiMaxSupportedVCs OBJECT-TYPE
             SYNTAX   INTEGER (0..1023)
             ACCESS   read-write
             STATUS   mandatory
             DESCRIPTION
                "The maximum number of Virtual Circuits allowed
                for  this  interface.   Usually dictated by the
                Frame Relay network.

                In response to a SET, if a value less than zero
                or  higher  than the agent's maximal capability
                is configured, the agent  should  respond  bad-
                Value"
            ::= { frDlcmiEntry 9 }


         frDlcmiMulticast OBJECT-TYPE
             SYNTAX   INTEGER {
                         nonBroadcast (1),
                         broadcast (2)
                         }
             ACCESS   read-write
             STATUS   mandatory
             DESCRIPTION
                "This indicates whether the Frame Relay  inter-
                face is using a multicast service."
             DEFVAL { nonBroadcast }
            ::= { frDlcmiEntry 10 }


         frDlcmiDceIdleInterval OBJECT-TYPE
             SYNTAX   INTEGER (10..60)
             ACCESS   read-write
             STATUS   mandatory
             DESCRIPTION
                "This is the number of seconds within a
                status enquiry messages should be received."
            REFERENCE
               "Draft American National  Standard  T1.617-1991,
               Section D.7 Timer T392."
           DEFVAL { 15 }
           ::= { frDlcmiEntry 42 }



         frDlcmiDceErrorThreshold OBJECT-TYPE
             SYNTAX   INTEGER (1..10)
             ACCESS   read-write
             STATUS   mandatory
             DESCRIPTION
                "This  is  the  maximum  number  of  unsent
                Status Enquiries the equipment shall accept be-
                fore declaring the interface down."
            REFERENCE
               "Draft American National  Standard  T1.617-1991,
               Section D.5.1 Counter N392."
           DEFVAL { 3 }
           ::= { frDlcmiEntry 43 }



         frDlcmiDceMonitoredEvents OBJECT-TYPE
             SYNTAX   INTEGER (1..10)
             ACCESS   read-write
             STATUS   mandatory
             DESCRIPTION
                "This is the number of status polling intervals
                over which the error threshold is counted.  For
                example, if within 'MonitoredEvents' number  of
                events  the  station  receives 'ErrorThreshold'
                number of errors, the interface  is  marked  as
                down."
            REFERENCE
               "Draft American National  Standard  T1.617-1991,
               Section D.5.2 Counter N393."
           DEFVAL { 4 }
           ::= { frDlcmiEntry 44 }



         frDlcmiMode OBJECT-TYPE
             SYNTAX   INTEGER {
                         dte (1),
                         dce (2),
			 nni (3)
                         }
             ACCESS   read-write
             STATUS   mandatory
             DESCRIPTION
                "This indicates the mode of the interface. dte(1) does
		 status enquiry polling, dce(2) does status answering.
		 nni(3) is bidirectional use of both dte and dce."
             DEFVAL { dte }
            ::= { frDlcmiEntry 45 }



         frDlcmiDefaultRouteIfIndex OBJECT-TYPE
             SYNTAX   INTEGER
             ACCESS   read-write
             STATUS   mandatory
             DESCRIPTION
                "This is the default route interface index when a new
                 PVC is established by means of line management."
             DEFVAL { 0 }
           ::= { frDlcmiEntry 46 }



     -- A Frame Relay service is a multiplexing service.  Data
     -- Link Connection Identifiers enumerate virtual circuits
     -- (permanent or dynamic) which are layered onto the underlying
     -- circuit, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.

     --   Circuit Table

     -- The table describing the use of the DLCIs attached to
     -- each Frame Relay Interface.

     frCircuitTable OBJECT-TYPE
         SYNTAX   SEQUENCE OF FrCircuitEntry
         ACCESS   not-accessible
         STATUS   mandatory
         DESCRIPTION
            "A table containing information about specific Data
            Link Connection Identifiers and corresponding virtual
            circuits."
         ::= { frpublic 2 }

         frCircuitEntry OBJECT-TYPE
             SYNTAX   FrCircuitEntry
             ACCESS   not-accessible
             STATUS   mandatory
             DESCRIPTION
                "The information regarding a single  Data  Link
                Connection Identifier."
            INDEX { frCircuitIfIndex, frCircuitDlci }
            ::= { frCircuitTable 1 }


         FrCircuitEntry ::=
             SEQUENCE {
                 frCircuitIfIndex
                     INTEGER,
                 frCircuitDlci
                     INTEGER,
                 frCircuitState
                     INTEGER,
                 frCircuitReceivedFECNs
                     Counter,
                 frCircuitReceivedBECNs
                     Counter,
                 frCircuitSentFrames
                     Counter,
                 frCircuitSentOctets
                     Counter,
                 frCircuitReceivedFrames
                     Counter,
                 frCircuitReceivedOctets
                     Counter,
                 frCircuitCreationTime
                     TimeTicks,
                 frCircuitLastTimeChange
                     TimeTicks,
                 frCircuitCommittedBurst
                     INTEGER,
                 frCircuitExcessBurst
                     INTEGER,
                 frCircuitThroughput
                     INTEGER,
		 frCircuitRouteType
		     INTEGER,
		 frCircuitRouteIfIndex
		     INTEGER,
		 frCircuitRouteDlci
		     INTEGER
         }


         frCircuitIfIndex OBJECT-TYPE
             SYNTAX   INTEGER
             ACCESS   read-write
             STATUS   mandatory
             DESCRIPTION
                "The ifIndex Value of the ifEntry this  virtual
                circuit is layered onto."
            ::= { frCircuitEntry 1 }


         frCircuitDlci OBJECT-TYPE
             SYNTAX   INTEGER
             ACCESS   read-write
             STATUS   mandatory
             DESCRIPTION
                "The Data Link Connection Identifier  for  this
                virtual circuit."
            REFERENCE
               "Draft American National  Standard  T1.618-1991,
               Section 3.3.6"
           ::= { frCircuitEntry 2 }


         frCircuitState OBJECT-TYPE
             SYNTAX   INTEGER {
                         invalid (1),
                         active (2),
                         inactive (3)
                      }
             ACCESS   read-write
             STATUS   mandatory
             DESCRIPTION
                "Indicates whether the particular virtual  cir-
                cuit  is operational.  In the absence of a Data
                Link Connection Management  Interface,  virtual
                circuit  entries  (rows) may be created by set-
                ting virtual  circuit  state  to  'active',  or
                deleted by changing Circuit state to 'invalid'.
                Whether or not the row actually  disappears  is
                left  to the implementation, so this object may
                actually read as 'invalid' for  some  arbitrary
                length  of  time.   It is also legal to set the
                state of a virtual  circuit  to  'inactive'  to
                temporarily disable a given circuit."
            DEFVAL { active }
            ::= { frCircuitEntry 3 }


         frCircuitReceivedFECNs OBJECT-TYPE
             SYNTAX   Counter
             ACCESS   read-only
             STATUS   mandatory
             DESCRIPTION
                "Number of frames received from the network in-
                dicating  forward  congestion since the virtual
                circuit was created."
            REFERENCE
               "Draft American National  Standard  T1.618-1991,
               Section 3.3.3"
           ::= { frCircuitEntry 4 }



         frCircuitReceivedBECNs OBJECT-TYPE
             SYNTAX   Counter
             ACCESS   read-only
             STATUS   mandatory
             DESCRIPTION
                "Number of frames received from the network in-
                dicating  backward congestion since the virtual
                circuit was created."
            REFERENCE
               "Draft American National  Standard  T1.618-1991,
               Section 3.3.4"
           ::= { frCircuitEntry 5 }



         frCircuitSentFrames OBJECT-TYPE
             SYNTAX   Counter
             ACCESS   read-only
             STATUS   mandatory
             DESCRIPTION
                "The number of frames sent  from  this  virtual
                circuit since it was created."
            ::= { frCircuitEntry 6 }



         frCircuitSentOctets OBJECT-TYPE
             SYNTAX   Counter
             ACCESS   read-only
             STATUS   mandatory
             DESCRIPTION
                "The number of octets sent  from  this  virtual
                circuit since it was created."
            ::= { frCircuitEntry 7 }



         frCircuitReceivedFrames OBJECT-TYPE
             SYNTAX   Counter
             ACCESS   read-only
             STATUS   mandatory
             DESCRIPTION
                "Number of frames received  over  this  virtual
                circuit since it was created."
            ::= { frCircuitEntry 8 }



         frCircuitReceivedOctets OBJECT-TYPE
             SYNTAX   Counter
             ACCESS   read-only
             STATUS   mandatory
             DESCRIPTION
                "Number of octets received  over  this  virtual
                circuit since it was created."
            ::= { frCircuitEntry 9 }


         frCircuitCreationTime OBJECT-TYPE
             SYNTAX   
		      TimeTicks
             ACCESS   read-only
             STATUS   mandatory
             DESCRIPTION
                "The value of sysUpTime when the  virtual  cir-
                cuit was created, whether by the Data Link Con-
                nection Management Interface  or  by  a  SetRe-
                quest."
            ::= { frCircuitEntry 10 }


         frCircuitLastTimeChange OBJECT-TYPE
             SYNTAX   
		      TimeTicks
             ACCESS   read-only
             STATUS   mandatory
             DESCRIPTION
                "The value of sysUpTime when last there  was  a
                change in the virtual circuit state"
            ::= { frCircuitEntry 11 }



         frCircuitCommittedBurst OBJECT-TYPE
             SYNTAX   INTEGER
             ACCESS   read-write
             STATUS   mandatory
             DESCRIPTION
                "This variable indicates the maximum amount  of
                data,  in  bits,  that  the  network  agrees to
                transfer under normal  conditions,  during  the
                measurement interval."
            REFERENCE
               "Draft American National  Standard  T1.617-1991,
               Section 6.5.19"
           DEFVAL   { 0 }  -- the default indicates no commitment
           ::= { frCircuitEntry 12 }



         frCircuitExcessBurst OBJECT-TYPE
             SYNTAX   INTEGER
             ACCESS   read-write
             STATUS   mandatory
             DESCRIPTION
                "This variable indicates the maximum amount  of
                uncommitted data bits that the network will at-
                tempt to deliver over the measurement interval.

                By default, if not configured when creating the
                entry, the Excess Information Burst Size is set
                to the value of ifSpeed."
            REFERENCE
               "Draft American National  Standard  T1.617-1991,
               Section 6.5.19"
                   ::= { frCircuitEntry 13 }



         frCircuitThroughput OBJECT-TYPE
             SYNTAX   INTEGER
             ACCESS   read-write
             STATUS   mandatory
             DESCRIPTION
                "Throughput is the average number of 'Frame Re-
                lay  Information  Field'  bits  transferred per
                second across a user network interface  in  one
                direction, measured over the measurement inter-
                val.

                If the  configured  committed  burst  rate  and
                throughput  are  both non-zero, the measurement
                interval
                T=frCircuitCommittedBurst/frCircuitThroughput.

                If the  configured  committed  burst  rate  and
                throughput  are  both zero, the measurement in-
                terval
                       T=frCircuitExcessBurst/ifSpeed."
            REFERENCE
               "Draft American National  Standard  T1.617-1991,
               Section 6.5.19"
           DEFVAL {0}  -- the default value of Throughput is
                       -- "no commitment".
           ::= { frCircuitEntry 14 }



         frCircuitRouteType OBJECT-TYPE
             SYNTAX   INTEGER {
		local(1), switch(2)
	     }
             ACCESS   read-only
             STATUS   mandatory
             DESCRIPTION
                "Type of routing entry. This field is intended for
		 informational purpose only."
           DEFVAL { local }
           ::= { frCircuitEntry 42 }



         frCircuitRouteIfIndex OBJECT-TYPE
             SYNTAX   INTEGER
             ACCESS   read-write
             STATUS   mandatory
             DESCRIPTION
                "The destination IfIndex is a pointer to either a
		 second frame relay interface (frame relay switching)
		 or to a frame relay virtual interface (multiprotocol
		 routing)."
           DEFVAL { 0 }
           ::= { frCircuitEntry 43 }



         frCircuitRouteDlci OBJECT-TYPE
             SYNTAX   INTEGER
             ACCESS   read-write
             STATUS   mandatory
             DESCRIPTION
                "The destination DLCI. When the circuit is used for
		 switching, all packets are sent using this DLCI.
		 This field is void for multiprotocol routing."
           DEFVAL { 0 }
           ::= { frCircuitEntry 44 }


     --  Error Table

     -- The table describing errors encountered on each Frame
     -- Relay Interface.

     frErrTable OBJECT-TYPE
         SYNTAX   SEQUENCE OF FrErrEntry
         ACCESS   not-accessible
         STATUS   mandatory
         DESCRIPTION
            "A table containing information about Errors on the
            Frame Relay interface."
         ::= { frpublic 3 }

         frErrEntry OBJECT-TYPE
             SYNTAX   FrErrEntry
             ACCESS   not-accessible
             STATUS   mandatory
             DESCRIPTION
                "The error information for a single frame relay
                interface."
            INDEX { frErrIfIndex }
            ::= { frErrTable 1 }



         FrErrEntry ::=
             SEQUENCE {
                 frErrIfIndex
                     INTEGER,
                 frErrType
                     INTEGER,
                 frErrData
                     OCTET STRING,
                 frErrTime
                     TimeTicks
         }



         frErrIfIndex OBJECT-TYPE
             SYNTAX   INTEGER
             ACCESS   read-only
             STATUS   mandatory
             DESCRIPTION
                "The ifIndex Value of the  corresponding  ifEn-
                try."
            ::= { frErrEntry 1 }



         frErrType OBJECT-TYPE
             SYNTAX   INTEGER {
                         unknownError(1),
                         receiveShort(2),
                         receiveLong(3),
                         illegalDLCI(4),
                         unknownDLCI(5),
                         dlcmiProtoErr(6),
                         dlcmiUnknownIE(7),
                         dlcmiSequenceErr(8),
                         dlcmiUnknownRpt(9),
                         noErrorSinceReset(10)
                      }
             ACCESS   read-only
             STATUS   mandatory
             DESCRIPTION
                "The type of error that was last seen  on  this
                interface."
            ::= { frErrEntry 2 }



         frErrData OBJECT-TYPE
             SYNTAX   OCTET STRING
             ACCESS   read-only
             STATUS   mandatory
             DESCRIPTION
                "An octet string containing as much of the  er-
                ror  packet as possible.  As a minimum, it must
                contain the Q.922 Address or  as  much  as  was
                delivered.   It is desirable to include all in-
                formation up to the PDU."
            ::= { frErrEntry 3 }



         frErrTime OBJECT-TYPE
             SYNTAX   
		      TimeTicks
             ACCESS   read-only
             STATUS   mandatory
             DESCRIPTION
                "The value of sysUpTime at which the error  was
                detected."
            ::= { frErrEntry 4 }


         -- Frame Relay Globals

         -- fr-globals OBJECT IDENTIFIER ::= { frpublic 4 }
         frGlobals OBJECT IDENTIFIER
		::= { frpublic 4 }

         frTrapState OBJECT-TYPE
             SYNTAX  INTEGER { enabled(1), disabled(2) }
             ACCESS   read-write
             STATUS   mandatory
             DESCRIPTION
                "This variable  indicates  whether  the  system
                produces the frDLCIStatusChange trap."
            DEFVAL { disabled }
            ::= { frGlobals 1 }


         --  Data Link Connection Management Interface Related Traps

--         frDLCIStatusChange TRAP-TYPE
--             ENTERPRISE fr
--             VARIABLES  { frCircuitIfIndex, frCircuitDlci, frCircuitState }
--             DESCRIPTION
--                "This trap indicates that the indicated Virtual
--                Circuit  has changed state.  It has either been
--                created or invalidated, or has toggled  between
--                the active and inactive states."
--             ::= 1


     END
