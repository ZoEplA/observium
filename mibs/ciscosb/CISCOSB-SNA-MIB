CISCOSB-SNA-MIB DEFINITIONS ::= BEGIN

-- Title:                CISCOSB
--                       SNA MIB
-- Version:              800
-- Date:                 12-May-2015

IMPORTS
    switch001                                                     FROM CISCOSB-MIB
    OBJECT-TYPE, MODULE-IDENTITY                            FROM SNMPv2-SMI
    TestAndIncr                                             FROM SNMPv2-TC;


rlSna MODULE-IDENTITY
                LAST-UPDATED "201101050000Z"
      ORGANIZATION "Cisco Systems, Inc."

      CONTACT-INFO
      "Postal: 170 West Tasman Drive
      San Jose , CA 95134-1706
      USA

      
      Website:  Cisco Small Business Support Community <http://www.cisco.com/go/smallbizsupport>"

                DESCRIPTION
                      "This private MIB module is used for communication between 
                      SNA client and SNA server."
                REVISION "201505120000Z"
                DESCRIPTION
                      "Initial revision."
        ::= { switch001 229 }
	
	
rlSnaNextFreeSessionId  OBJECT-TYPE
    SYNTAX       TestAndIncr
    MAX-ACCESS   read-write
    STATUS       current
    DESCRIPTION "The MIB allows several SNA clients operating at the same time to 
	             receive different session ids. Get operation on this MIB will return 
				 the next free session id number. An SNA client should then issue SET 
				 operation with the value it received. The response will be one of the 
                 following:
                 - noError.
                 - inconsistentValue in case another client has already used this session id.
				 - resourceUnavailable in case the number of active sessions has already 
				   reached the maximum. 
				 In case of success, a new session events database is allocated for the session id."
    ::= { rlSna 1 } 
	

END
