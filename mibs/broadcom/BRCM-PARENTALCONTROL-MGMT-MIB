--**************************************************************************
--                                                                          
--    Copyright 2003 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-parentalcontrol-mgmt.mib
--    Author:   Kevin O'Neal
--    Creation Date: 4-april-2003
--
--**************************************************************************
--    Description:
--
--		private MIB for runtime (not factory) parental control
--		
--**************************************************************************
--    Revision History:
--
--**************************************************************************

BRCM-PARENTALCONTROL-MGMT-MIB DEFINITIONS ::= BEGIN

IMPORTS
    MODULE-IDENTITY,
    OBJECT-TYPE
        FROM SNMPv2-SMI
    TruthValue,
    DisplayString,
    DateAndTime
        FROM SNMPv2-TC 
    cableDataMgmtMIBObjects
        FROM BRCM-CABLEDATA-MGMT-MIB;
                
parentalControlMgmt MODULE-IDENTITY
    LAST-UPDATED "0307300000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom parental control management MIB"
    REVISION      "0304040000Z"
    DESCRIPTION
         "Initial version of this MIB module."
    REVISION      "0304170000Z"
    DESCRIPTION
         "Added new objects to invoke subscription and check status."
    REVISION      "0307300000Z"
    DESCRIPTION
         "Added pctlCategoryList object."
    ::= { cableDataMgmtMIBObjects 8 }
    
pctlService OBJECT IDENTIFIER ::= { parentalControlMgmt 1 }

pctlSubscriptionURL OBJECT-TYPE
    SYNTAX      DisplayString
    MAX-ACCESS  read-write
    STATUS      current
    DESCRIPTION
        "Identifies an internet URL which the subscriber will be directed when
         he chooses to subscribe to the parental control service."
    ::= { pctlService 1 }

pctlServiceModel OBJECT-TYPE
    SYNTAX      INTEGER {
                none(0),
                cerberianCMR(1),
                cerberianADR(2),
                rulespace(3)
    }
    MAX-ACCESS  read-write
    STATUS      current
    DESCRIPTION
        "Identifies the service model used for parental control.  If set to
         none(0), parental control will be disabled."
    ::= { pctlService 2 }
    
pctlServicePrimaryURL OBJECT-TYPE
    SYNTAX      DisplayString
    MAX-ACCESS  read-write
    STATUS      current
    DESCRIPTION
        "Identifies an internet URL which will be used as the primary parental
         control server."
    ::= { pctlService 3 }
    
pctlServiceSecondaryURL OBJECT-TYPE
    SYNTAX      DisplayString
    MAX-ACCESS  read-write
    STATUS      current
    DESCRIPTION
        "Identifies an internet URL which will be used as the primary parental
         control server.  For service providers which do not provide a 
         secondary server, this object will be empty."
    ::= { pctlService 4 }
    
pctlLicenseKey OBJECT-TYPE
    SYNTAX      OCTET STRING
    MAX-ACCESS  read-write
    STATUS      current
    DESCRIPTION
        "The parental control license key for this subscriber."
    ::= { pctlService 5 }
    
pctlLicenseExpiration OBJECT-TYPE
    SYNTAX      DateAndTime
    MAX-ACCESS  read-write
    STATUS      current
    DESCRIPTION
        "The date at which the current license key will expire.  If the key has
         no expiration, then a value of 1-1-1970 will be used."
    ::= { pctlService 6 }
    
pctlServiceSubscribeNow OBJECT-TYPE
    SYNTAX      TruthValue
    MAX-ACCESS  read-write
    STATUS      current
    DESCRIPTION
        "If set to true(1), the device will attempt to subscribe to parental
         control service based on the paramters in pctlServiceModel, 
         pctlServicePrimaryURL, pctlServiceSecondaryURL, and pctlLicenseKey.
         Results of this attempt may be retrieved from 
         pctlServiceSubscriptionStatus.
         
         If set to false(2), the device will un-subscribe from parental control
         service."
    ::= { pctlService 7 }
    
pctlServiceSubscriptionStatus OBJECT-TYPE
    SYNTAX      INTEGER {
                notAttempted(0),
				readyToSubscribe(1),
                subscribedServiceNotStarted(2),
                subscribedEstablishingService(3),
                subscribedServiceRunning(4),
				subscribedServiceError(5),
				subscriptionFailed(6),
				subscriptionExpired(7)
    }
    MAX-ACCESS  read-only
    STATUS      current
    DESCRIPTION
        "Indicates the status of the last parental control subscription attempt.
         If no attempt has been made, this object will return notAttempted(0).
         If a subscription exchange is currently in progress, inProgress(1) will
         be returned.  A successful subscription attempt will result in a value
         of successful(2), and a failed subscription attempt will result in a
         value of failure(3)."
    ::= { pctlService 8 }
    
pctlCategoryList OBJECT-TYPE
    SYNTAX      OCTET STRING (SIZE(0..1024))
    MAX-ACCESS  read-write
    STATUS      current
    DESCRIPTION
        "Identifies the list of currently available parental control 
         categories."
    ::= { pctlService 9 }
    
END
