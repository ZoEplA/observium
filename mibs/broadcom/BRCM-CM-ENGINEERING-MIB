--**************************************************************************
--                                                                          
--    Copyright 2002 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-cm-engineering.mib
--    Author:   Kevin O'Neal
--    Creation Date: 22-october-2002
--
--**************************************************************************
--    Description:
--
--		private MIB for cablemodem factory
--		
--**************************************************************************
--    Revision History:
--
--**************************************************************************

BRCM-CM-ENGINEERING-MIB DEFINITIONS ::= BEGIN

IMPORTS
    MODULE-IDENTITY,
    OBJECT-TYPE,
    Integer32,
    Unsigned32
        FROM SNMPv2-SMI
    TruthValue, RowPointer
        FROM SNMPv2-TC
    cableDataEngineering
        FROM BRCM-CABLEDATA-ENGINEERING-MIB
    cmDsCalOffsetIndex
        FROM BRCM-CM-FACTORY-MIB;
                
cablemodemEngineering MODULE-IDENTITY
    LAST-UPDATED "0306230000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata private MIB"
    REVISION     "0210220000Z"
    DESCRIPTION
            "Initial version of this MIB module."
    REVISION     "0211110000Z"
    DESCRIPTION
            "Added objects for 33xx hardware control in cmEngrBase and
             populated cmEngrUpstreamCalibration."
    REVISION     "0212110000Z"
    DESCRIPTION
            "Added more DS cal objects to control and report the results of the
             CM DS characterization routine."
    REVISION     "0212230000Z"
    DESCRIPTION
            "Added AGC control objects.  Ho, Ho, Ho."
    REVISION     "0301030000Z"
    DESCRIPTION
            "Added cmHwSTABW2 object."
    REVISION     "0304240000Z"
    DESCRIPTION
            "Added cmDsCalFrequencyError object."
    REVISION     "0306230000Z"
    DESCRIPTION
            "Added objects to allow dynamic population and de-population of
             the downstream and upstream calibration tables in order to provide
             more efficient RAM management when performing downstream and 
             upstream CM characterization."
    ::= { cableDataEngineering 2 }

-- cmEngrBase: miscellaneous control/state objects for engineering mode    
cmEngrBase OBJECT IDENTIFIER ::= { cablemodemEngineering 1 }

cmEngr33xxOpcode OBJECT-TYPE
    SYNTAX      Unsigned32
    MAX-ACCESS  read-write
    STATUS      current
    DESCRIPTION
        "The hardware address or multibyte opcode to access in a 33xx family
         device when executing a cmEngr33xxCommand operation."
    ::= { cmEngrBase 1 }
    
cmEngr33xxData OBJECT-TYPE
    SYNTAX      Unsigned32
    MAX-ACCESS  read-write
    STATUS      current
    DESCRIPTION
        "The data read from or to be written to a 33xx family device when 
         executing a cmEngr33xxCommand operation."
    ::= { cmEngrBase 2 }
    
cmEngr33xxCommand OBJECT-TYPE
    SYNTAX      INTEGER {
                read(0),
                write(1)
    }
    MAX-ACCESS  read-write
    STATUS      current
    DESCRIPTION
        "Setting this value to read(0) will cause a read operation to be
         executed on the multibyte opcode specified in cmEngr33xxOpcode.  The 
         data read back from the operation will be presented in cmEngr33xxData.  
         Setting this value to write(1) will cause the data in cmEngr33xxData 
         to be written via the multibyte opcode specified in cmEngr33xxOpcode."
    ::= { cmEngrBase 3 }

-- cmEngrDownstreamCalibration: used to characterize a family of devices,
-- typically not necessary for manufacturing of individual units.
cmEngrDownstreamCalibration OBJECT IDENTIFIER ::= { cablemodemEngineering 2 }

--
-- Tuner Coeficient objects
--

cmDsCalZeroTunerCoefs OBJECT-TYPE
    SYNTAX      TruthValue
    MAX-ACCESS  read-write
    STATUS      current
    DESCRIPTION
        "Setting this object to true(1) will result in all writable objects in
         the cmDsCalTunerCoefTable being set to zero.  Sets to false(2) will be
         accepted, but will not result in any action being taken.  Reading
         this object always returns false(2)."
    ::= { cmEngrDownstreamCalibration 1 }

cmDsCalNumTunerCoefs OBJECT-TYPE
    SYNTAX      Unsigned32 (1..255)
    MAX-ACCESS  read-write
    STATUS      current
    DESCRIPTION
        "Controls and reflects the number of tuner coefficients per downstream
         frequency in the cmDsCalTunerCoefTable.  Note that the total number
         of entries in this table will be the value of cmDsCalNumOffsets
         (from the BRCM-CM-FACTORY-MIB) multiplied by this value. If this value
         is changed, then the cmDsCalTunerCoefTable will be destroyed and 
         rebuilt with the new number of coefficients, but all coefficient values
         will be set to zero."
    ::= { cmEngrDownstreamCalibration 2 }

cmDsCalTunerCoefTable  OBJECT-TYPE
    SYNTAX      SEQUENCE OF CmDsCalTunerCoefEntry
    MAX-ACCESS  not-accessible
    STATUS      current
    DESCRIPTION
        "A list of tuner coeffiencents to be used when calculating downstream 
         power for this device."
    ::= { cmEngrDownstreamCalibration 3 }
    
cmDsCalTunerCoefEntry OBJECT-TYPE
    SYNTAX      CmDsCalTunerCoefEntry
    MAX-ACCESS  not-accessible
    STATUS      current
    DESCRIPTION
        "An entry defining a tuner coefficient for a given frequency at the
         given index for this device."
    INDEX   { cmDsCalOffsetIndex, cmDsCalTunerCoefIndex }
    ::= { cmDsCalTunerCoefTable 1 }
    
CmDsCalTunerCoefEntry ::= 
    SEQUENCE    {
                cmDsCalTunerCoefIndex         Integer32,
                cmDsCalTunerCoefFrequency     Integer32,
                cmDsCalTunerCoefValue         Unsigned32,
                cmDsCalTunerCoefCopyFrom      Integer32
    }
    
cmDsCalTunerCoefIndex OBJECT-TYPE
    SYNTAX      Integer32
    MAX-ACCESS  not-accessible
    STATUS      current
    DESCRIPTION
        "Identifies the instance of this tuner coefficient."
    ::= { cmDsCalTunerCoefEntry 1 }
    
cmDsCalTunerCoefFrequency OBJECT-TYPE
    SYNTAX      Integer32
    UNITS       "hertz"
    MAX-ACCESS  read-only
    STATUS      current
    DESCRIPTION
        "The downstream frequency at which this instance of 
         cmDsCalTunerCoefValue applies.  This read-only object is provided here
         for convenience.  Value is identical to the value of the read-write
         object cmDsCalOffsetFrequency which may be changed in engineering
         mode if necessary.  Changes made to cmDsCalOffsetFrequency will be
         reflected here immediately."
    REFERENCE 
         "docsIfDownChannelFrequency from DOCS-IF-MIB" 
    ::= { cmDsCalTunerCoefEntry 2 }
    
cmDsCalTunerCoefValue OBJECT-TYPE
    SYNTAX      Unsigned32 (0..1000000)
    UNITS       "millionth" 
    MAX-ACCESS  read-write
    STATUS      current
    DESCRIPTION
        "The value of this tuner coefficient multiplied by one million.
         For example, a tuner coefficient value of 0.218369 would be
         represented as 218369.  This gives a Since tuner coefficients must 
         range in value between zero and one, this object will always have a 
         value of between zero (0.000000) and one million (1.000000).  
         Precision is 1e-6."
    ::= { cmDsCalTunerCoefEntry 3 }
    
cmDsCalTunerCoefCopyFrom OBJECT-TYPE
    SYNTAX      Integer32
    MAX-ACCESS  read-write
    STATUS      current
    DESCRIPTION
        "Setting this object to the value of the first element of an index of
         a row in this table will cause all coefficients for this frequency to 
         be copied from the corresponding location in the frequency pointed to
         by the index specified.  For example, if cmDsCalTunerCoefCopyFrom.1.1
         is set to 2, then cmDsCalTunerCoefValue.1.1 through 
         cmDsCalTunerCoefCopyFrom.1.n will be copied from 
         cmDsCalTunerCoefCopyFrom.2.1 through cmDsCalTunerCoefCopyFrom.2.n. 
         Reading this object will always return 0."
    ::= { cmDsCalTunerCoefEntry 4 }
    
--
-- IF (Intermediate Frequency) Coeficient objects
--

cmDsCalZeroIFCoefs OBJECT-TYPE
    SYNTAX      TruthValue
    MAX-ACCESS  read-write
    STATUS      current
    DESCRIPTION
        "Setting this object to true(1) will result in all writable objects in
         the cmDsCalIFCoefTable being set to zero.  Sets to false(2) will be
         accepted, but will not result in any action being taken.  Reading
         this object always returns false(2)."
    ::= { cmEngrDownstreamCalibration 4 }

cmDsCalNumIFCoefs OBJECT-TYPE
    SYNTAX      Unsigned32 (1..255)
    MAX-ACCESS  read-write
    STATUS      current
    DESCRIPTION
        "Controls and reflects the number of IF coefficients per downstream
         frequency in the cmDsCalIFCoefTable.  Note that the total number
         of entries in this table will be the value of cmDsCalNumOffsets
         (from the BRCM-CM-FACTORY-MIB) multiplied by this value. If this value
         is changed, then the cmDsCalIFCoefTable will be destroyed and 
         rebuilt with the new number of coefficients, but all coefficient values
         will be set to zero."
    ::= { cmEngrDownstreamCalibration 5 }
    
cmDsCalIFCoefTable  OBJECT-TYPE
    SYNTAX      SEQUENCE OF CmDsCalIFCoefEntry
    MAX-ACCESS  not-accessible
    STATUS      current
    DESCRIPTION
        "A list of intermediate frequency coeffiencents to be used when 
         calculating downstream power for this device."
    ::= { cmEngrDownstreamCalibration 6 }
    
cmDsCalIFCoefEntry OBJECT-TYPE
    SYNTAX      CmDsCalIFCoefEntry
    MAX-ACCESS  not-accessible
    STATUS      current
    DESCRIPTION
        "An entry defining an IF coefficient for a given frequency at the
         given index for this device."
    INDEX   { cmDsCalOffsetIndex, cmDsCalIFCoefIndex }
    ::= { cmDsCalIFCoefTable 1 }
    
CmDsCalIFCoefEntry ::= 
    SEQUENCE    {
                cmDsCalIFCoefIndex         Integer32,
                cmDsCalIFCoefFrequency     Integer32,
                cmDsCalIFCoefValue         Integer32,
                cmDsCalIFCoefCopyFrom      Integer32
    }
    
cmDsCalIFCoefIndex OBJECT-TYPE
    SYNTAX      Integer32
    MAX-ACCESS  not-accessible
    STATUS      current
    DESCRIPTION
        "Identifies the instance of this IF coefficient."
    ::= { cmDsCalIFCoefEntry 1 }
    
cmDsCalIFCoefFrequency OBJECT-TYPE
    SYNTAX      Integer32
    UNITS       "hertz"
    MAX-ACCESS  read-only
    STATUS      current
    DESCRIPTION
        "The downstream frequency at which this instance of 
         cmDsCalIFCoefValue applies.  This read-only object is provided here
         for convenience.  Value is identical to the value of the read-write
         object cmDsCalOffsetFrequency which may be changed in engineering
         mode if necessary.  Changes made to cmDsCalOffsetFrequency will be
         reflected here immediately."
    REFERENCE 
         "docsIfDownChannelFrequency from DOCS-IF-MIB" 
    ::= { cmDsCalIFCoefEntry 2 }
    
cmDsCalIFCoefValue OBJECT-TYPE
    SYNTAX      Integer32
    UNITS       "hundred-thousandth" 
    MAX-ACCESS  read-write
    STATUS      current
    DESCRIPTION
        "The value of this IF coefficient multiplied by one hundred thousand.
         For example, an IF coefficent value of -2662.94 would be represented
         as -266294000.  This gives an effective range of IF coefficent values
         ranging from -21474.83647 to 21474.83647 and a precision of 1e-5"
    ::= { cmDsCalIFCoefEntry 3 }
    
cmDsCalIFCoefCopyFrom OBJECT-TYPE
    SYNTAX      Integer32
    MAX-ACCESS  read-write
    STATUS      current
    DESCRIPTION
        "Setting this object to the value of the first element of an index of
         a row in this table will cause all coefficients for this frequency to 
         be copied from the corresponding location in the frequency pointed to
         by the index specified.  For example, if cmDsCalIFCoefCopyFrom.1.1
         is set to 2, then cmDsCalIFCoefValue.1.1 through 
         cmDsCalIFCoefCopyFrom.1.n will be copied from 
         cmDsCalIFCoefCopyFrom.2.1 through cmDsCalIFCoefCopyFrom.2.n. 
         Reading this object will always return 0."
    ::= { cmDsCalIFCoefEntry 4 }
    
--
-- Fine Coeficient objects
--

cmDsCalZeroFineCoefs OBJECT-TYPE
    SYNTAX      TruthValue
    MAX-ACCESS  read-write
    STATUS      current
    DESCRIPTION
        "Setting this object to true(1) will result in all writable objects in
         the cmDsCalFineCoefTable being set to zero.  Sets to false(2) will be
         accepted, but will not result in any action being taken.  Reading
         this object always returns false(2)."
    ::= { cmEngrDownstreamCalibration 7 }

cmDsCalNumFineCoefs OBJECT-TYPE
    SYNTAX      Unsigned32 (1..255)
    MAX-ACCESS  read-write
    STATUS      current
    DESCRIPTION
        "Controls and reflects the number of Fine coefficients per downstream
         frequency in the cmDsCalFineCoefTable.  Note that the total number
         of entries in this table will be the value of cmDsCalNumOffsets
         (from the BRCM-CM-FACTORY-MIB) multiplied by this value. If this value
         is changed, then the cmDsCalFineCoefTable will be destroyed and 
         rebuilt with the new number of coefficients, but all coefficient values
         will be set to zero."
    ::= { cmEngrDownstreamCalibration 8 }

cmDsCalFineCoefTable  OBJECT-TYPE
    SYNTAX      SEQUENCE OF CmDsCalFineCoefEntry
    MAX-ACCESS  not-accessible
    STATUS      current
    DESCRIPTION
        "A list of Fine coeffiencents to be used when calculating downstream 
         power for this device."
    ::= { cmEngrDownstreamCalibration 9 }
    
cmDsCalFineCoefEntry OBJECT-TYPE
    SYNTAX      CmDsCalFineCoefEntry
    MAX-ACCESS  not-accessible
    STATUS      current
    DESCRIPTION
        "An entry defining a Fine coefficient for a given frequency at the
         given index for this device."
    INDEX   { cmDsCalOffsetIndex, cmDsCalFineCoefIndex }
    ::= { cmDsCalFineCoefTable 1 }
    
CmDsCalFineCoefEntry ::= 
    SEQUENCE    {
                cmDsCalFineCoefIndex         Integer32,
                cmDsCalFineCoefFrequency     Integer32,
                cmDsCalFineCoefValue         Integer32,
                cmDsCalFineCoefCopyFrom      Integer32
    }
    
cmDsCalFineCoefIndex OBJECT-TYPE
    SYNTAX      Integer32
    MAX-ACCESS  not-accessible
    STATUS      current
    DESCRIPTION
        "Identifies the instance of this Fine coefficient."
    ::= { cmDsCalFineCoefEntry 1 }
    
cmDsCalFineCoefFrequency OBJECT-TYPE
    SYNTAX      Integer32
    UNITS       "hertz"
    MAX-ACCESS  read-only
    STATUS      current
    DESCRIPTION
        "The downstream frequency at which this instance of 
         cmDsCalFineCoefValue applies.  This read-only object is provided here
         for convenience.  Value is identical to the value of the read-write
         object cmDsCalOffsetFrequency which may be changed in engineering
         mode if necessary.  Changes made to cmDsCalOffsetFrequency will be
         reflected here immediately."
    REFERENCE 
         "docsIfDownChannelFrequency from DOCS-IF-MIB" 
    ::= { cmDsCalFineCoefEntry 2 }
    
cmDsCalFineCoefValue OBJECT-TYPE
    SYNTAX      Integer32
    UNITS       "millionth" 
    MAX-ACCESS  read-write
    STATUS      current
    DESCRIPTION
        "The value of this fine coefficient multiplied by one million.
         For example, a fine coefficent value of 36.5494 would be represented
         as 36549400.  This gives an effective range of fine coefficent values
         ranging from -2147.483647 to 2147.483647 and a precision of 1e-6."
    ::= { cmDsCalFineCoefEntry 3 }
    
cmDsCalFineCoefCopyFrom OBJECT-TYPE
    SYNTAX      Integer32
    MAX-ACCESS  read-write
    STATUS      current
    DESCRIPTION
        "Setting this object to the value of the first element of an index of
         a row in this table will cause all coefficients for this frequency to 
         be copied from the corresponding location in the frequency pointed to
         by the index specified.  For example, if cmDsCalFineCoefCopyFrom.1.1
         is set to 2, then cmDsCalFineCoefValue.1.1 through 
         cmDsCalFineCoefCopyFrom.1.n will be copied from 
         cmDsCalFineCoefCopyFrom.2.1 through cmDsCalFineCoefCopyFrom.2.n. 
         Reading this object will always return 0."
    ::= { cmDsCalFineCoefEntry 4 }
    
--
-- Equalizer Coeficient objects
--

cmDsCalZeroEqCoefs OBJECT-TYPE
    SYNTAX      TruthValue
    MAX-ACCESS  read-write
    STATUS      current
    DESCRIPTION
        "Setting this object to true(1) will result in all writable objects in
         the cmDsCalEqualizerCoefTable being set to zero.  Sets to false(2) will be
         accepted, but will not result in any action being taken.  Reading
         this object always returns false(2)."
    ::= { cmEngrDownstreamCalibration 10 }

cmDsCalNumEqCoefs OBJECT-TYPE
    SYNTAX      Unsigned32 (1..255)
    MAX-ACCESS  read-write
    STATUS      current
    DESCRIPTION
        "Controls and reflects the number of equalizer coefficients per downstream
         frequency in the cmDsCalEqualizerCoefTable.  Note that the total number
         of entries in this table will be the value of cmDsCalNumOffsets
         (from the BRCM-CM-FACTORY-MIB) multiplied by this value. If this value
         is changed, then the cmDsCalEqualizerCoefTable will be destroyed and 
         rebuilt with the new number of coefficients, but all coefficient values
         will be set to zero."
    ::= { cmEngrDownstreamCalibration 11 }

cmDsCalEqCoefTable  OBJECT-TYPE
    SYNTAX      SEQUENCE OF CmDsCalEqCoefEntry
    MAX-ACCESS  not-accessible
    STATUS      current
    DESCRIPTION
        "A list of equalizer coeffiencents to be used when calculating downstream 
         power for this device."
    ::= { cmEngrDownstreamCalibration 12 }
    
cmDsCalEqCoefEntry OBJECT-TYPE
    SYNTAX      CmDsCalEqCoefEntry
    MAX-ACCESS  not-accessible
    STATUS      current
    DESCRIPTION
        "An entry defining a equalizer coefficient for a given frequency at the
         given index for this device."
    INDEX   { cmDsCalOffsetIndex, cmDsCalEqCoefIndex }
    ::= { cmDsCalEqCoefTable 1 }
    
CmDsCalEqCoefEntry ::= 
    SEQUENCE    {
                cmDsCalEqCoefIndex         Integer32,
                cmDsCalEqCoefFrequency     Integer32,
                cmDsCalEqCoefValue         Integer32,
                cmDsCalEqCoefCopyFrom      Integer32
    }
    
cmDsCalEqCoefIndex OBJECT-TYPE
    SYNTAX      Integer32
    MAX-ACCESS  not-accessible
    STATUS      current
    DESCRIPTION
        "Identifies the instance of this equalizer coefficient."
    ::= { cmDsCalEqCoefEntry 1 }
    
cmDsCalEqCoefFrequency OBJECT-TYPE
    SYNTAX      Integer32
    UNITS       "hertz"
    MAX-ACCESS  read-only
    STATUS      current
    DESCRIPTION
        "The downstream frequency at which this instance of 
         cmDsCalEqCoefValue applies.  This read-only object is provided here
         for convenience.  Value is identical to the value of the read-write
         object cmDsCalOffsetFrequency which may be changed in engineering
         mode if necessary.  Changes made to cmDsCalOffsetFrequency will be
         reflected here immediately."
    REFERENCE 
         "docsIfDownChannelFrequency from DOCS-IF-MIB" 
    ::= { cmDsCalEqCoefEntry 2 }
    
cmDsCalEqCoefValue OBJECT-TYPE
    SYNTAX      Integer32
    UNITS       "hundred-thousandth" 
    MAX-ACCESS  read-write
    STATUS      current
    DESCRIPTION
        "The value of this equalizer coefficient multiplied by one hundred 
         thousand. For example, an equalizer coefficent value of 4287.95 would 
         be represented as 428795000.  This gives an effective range of 
         equalizer coefficent values ranging from -21474.83647 to 21474.83647 
         and a precision of 1e-5."
    ::= { cmDsCalEqCoefEntry 3 }
    
cmDsCalEqCoefCopyFrom OBJECT-TYPE
    SYNTAX      Integer32
    MAX-ACCESS  read-write
    STATUS      current
    DESCRIPTION
        "Setting this object to the value of the first element of an index of
         a row in this table will cause all coefficients for this frequency to 
         be copied from the corresponding location in the frequency pointed to
         by the index specified.  For example, if cmDsCalEqCoefCopyFrom.1.1 is 
         set to 2, then cmDsCalEqCoefValue.1.1 through cmDsCalEqCoefCopyFrom.1.n 
         will be copied from cmDsCalEqCoefCopyFrom.2.1 through 
         cmDsCalEqCoefCopyFrom.2.n. Reading this object will always return 0."
    ::= { cmDsCalEqCoefEntry 4 }
    
cmDsCalNumLDAIxReads OBJECT-TYPE
    SYNTAX      Unsigned32 (0..255)
    MAX-ACCESS  read-write
    STATUS      current
    DESCRIPTION
        "Sets the number of times the LDAIx registers will be read before doing 
         the power calculations.  It will average the register values."
    ::= { cmEngrDownstreamCalibration 13 }
    
cmDsCalLDAIxReadInterval OBJECT-TYPE
    SYNTAX      Unsigned32 (0..255)
    UNITS       "milliseconds"
    MAX-ACCESS  read-write
    STATUS      current
    DESCRIPTION
        "Sets the time (in milliseconds) between each read of the LDAIx 
         registers."
    ::= { cmEngrDownstreamCalibration 14 }
    
cmDsCalTunerStep OBJECT-TYPE
    SYNTAX      Unsigned32 (0..800)
    UNITS       "hundredth dBmV"
    MAX-ACCESS  read-write
    STATUS      current
    DESCRIPTION
        "Sets the step size (in dBmV) that was used when sampling the tuner 
         table.  This influences how the data is interpolated when calculating 
         the tuner gain part of actual power level."
    ::= { cmEngrDownstreamCalibration 15 }
    
cmDsCalMasterPowerOffset OBJECT-TYPE
    SYNTAX      Integer32 (-32700..32700)
    UNITS       "hundredth dBmV"
    MAX-ACCESS  read-write
    STATUS      current
    DESCRIPTION
        "Sets the master offset power value (in dBmV) for the modem.  Each 
         frequency band in the table has an offset power adjustment that is 
         applied to this value when calculating the actual power level."
    ::= { cmEngrDownstreamCalibration 16 }
    
cmDsCalCharacterizeNow OBJECT-TYPE
    SYNTAX      TruthValue
    MAX-ACCESS  read-write
    STATUS      current
    DESCRIPTION
        "When set to true(1), the CM will execute its DS characterization 
         routine using the frequency specified by cmDsCalFrequency, and the 
         modulation type specified by cmDsCalModulation.  Prior to executing the 
         DS characterization routine, cmDsCalLockNow must have been set to 
         true(1) and the lock must have been successful, as indicated by 
         cmDsCalQamLocked and cmDsCalFecLocked both being true(1). The SET 
         operation will not return until the routine is complete, so the SNMP 
         manager's timeout value may need to be increased to several seconds.  
         Once the DS characterization is complete, the resulting data may be 
         read from the objects cmDsCalNormalLDAIT, cmDsCalNormalLDAIF, 
         cmDsCalNormalLDAII, cmDsCalFrozenLDAIT, cmDsCalFrozenLDAIF, 
         cmDsCalFrozenLDAII, cmDsCalFGain, cmDsCalTGain, and cmDsCalIGain.  
         Always returns false(2) when read."
    ::= { cmEngrDownstreamCalibration 17 }
    
cmDsCalNormalLDAIT OBJECT-TYPE
    SYNTAX      Unsigned32
    MAX-ACCESS  read-only
    STATUS      current
    DESCRIPTION
        "Shows the contents of the LDAIT register after executing the 'normal' 
         portion of the CM DS characterization routine."
    ::= { cmEngrDownstreamCalibration 18 }
    
cmDsCalNormalLDAIF OBJECT-TYPE
    SYNTAX      Unsigned32
    MAX-ACCESS  read-only
    STATUS      current
    DESCRIPTION
        "Shows the contents of the LDAIF register after executing the 'normal' 
         portion of the CM DS characterization routine."
    ::= { cmEngrDownstreamCalibration 19 }
    
cmDsCalNormalLDAII OBJECT-TYPE
    SYNTAX      Unsigned32
    MAX-ACCESS  read-only
    STATUS      current
    DESCRIPTION
        "Shows the contents of the LDAII register after executing the 'normal' 
         portion of the CM DS characterization routine."
    ::= { cmEngrDownstreamCalibration 20 }
    
cmDsCalFrozenLDAIT OBJECT-TYPE
    SYNTAX      Unsigned32
    MAX-ACCESS  read-only
    STATUS      current
    DESCRIPTION
        "Shows the contents of the LDAIT register after executing the 'frozen' 
         portion of the CM DS characterization routine."
    ::= { cmEngrDownstreamCalibration 21 }
    
cmDsCalFrozenLDAIF OBJECT-TYPE
    SYNTAX      Unsigned32
    MAX-ACCESS  read-only
    STATUS      current
    DESCRIPTION
        "Shows the contents of the LDAIF register after executing the 'frozen' 
         portion of the CM DS characterization routine."
    ::= { cmEngrDownstreamCalibration 22 }
    
cmDsCalFrozenLDAII OBJECT-TYPE
    SYNTAX      Unsigned32
    MAX-ACCESS  read-only
    STATUS      current
    DESCRIPTION
        "Shows the contents of the LDAII register after executing the 'frozen' 
         portion of the CM DS characterization routine."
    ::= { cmEngrDownstreamCalibration 23 }
    
cmDsCalFGainTap OBJECT-TYPE
    SYNTAX      Unsigned32
    MAX-ACCESS  read-only
    STATUS      current
    DESCRIPTION
        "Shows the value of the equalizer main tap after executing the F-Gain 
         portion of the CM DS characterization routine."
    ::= { cmEngrDownstreamCalibration 24 }
    
cmDsCalTGainTap OBJECT-TYPE
    SYNTAX      Unsigned32
    MAX-ACCESS  read-only
    STATUS      current
    DESCRIPTION
        "Shows the value of the equalizer main tap after executing the T-Gain 
         portion of the CM DS characterization routine."
    ::= { cmEngrDownstreamCalibration 25 }
    
cmDsCalIGainTap OBJECT-TYPE
    SYNTAX      Unsigned32
    MAX-ACCESS  read-only
    STATUS      current
    DESCRIPTION
        "Shows the value of the equalizer main tap after executing the I-Gain 
         portion of the CM DS characterization routine."
    ::= { cmEngrDownstreamCalibration 26 }
    
cmDsCalFrequencyError OBJECT-TYPE
    SYNTAX      Integer32
    UNITS       "hertz"
    MAX-ACCESS  read-only
    STATUS      current
    DESCRIPTION
        "Reports the amount of frequency error in the downstream signal."
    ::= { cmEngrDownstreamCalibration 27 }
    
cmDsCalTunerCoefTablePopulate  OBJECT-TYPE
    SYNTAX      TruthValue
    MAX-ACCESS  read-write
    STATUS      current
    DESCRIPTION
        "When set to true(1), the downstream tuner coefficient data will be 
         loaded into the cmDsCalTunerCoefTable.  If the table is already 
         populated, it will be flushed and re-populated.  If the amount of RAM
         available on the device becomes low while populating the table, an 
         error code of RESOURCE UNAVAILABLE will be returned, and the table
         population will be incomplete.  Setting this object to false(2) will 
         flush the cmDsCalTunerCoefTable.
         
         When read, this object indicates the current state of the 
         cmDsCalTunerCoefTable.  A value of true(1) indicates that the table was
         successfully populated.  A value of false(2) indicates that the table
         is either unpopulated, or that insufficient RAM was available to 
         complete the population and that the table is incomplete."
    ::= { cmEngrDownstreamCalibration 28 }
    
cmDsCalIFCoefTablePopulate  OBJECT-TYPE
    SYNTAX      TruthValue
    MAX-ACCESS  read-write
    STATUS      current
    DESCRIPTION
        "When set to true(1), the downstream intermediate frequency coefficient 
         data will be loaded into the cmDsCalIFCoefTable.  If the table is 
         already populated, it will be flushed and re-populated.  If the amount 
         of RAM available on the device becomes low while populating the table, 
         an error code of RESOURCE UNAVAILABLE will be returned, and the table
         population will be incomplete.  Setting this object to false(2) will 
         flush the cmDsCalIFCoefTable.
         
         When read, this object indicates the current state of the 
         cmDsCalIFCoefTable.  A value of true(1) indicates that the table was
         successfully populated.  A value of false(2) indicates that the table
         is either unpopulated, or that insufficient RAM was available to 
         complete the population and that the table is incomplete."
    ::= { cmEngrDownstreamCalibration 29 }
    
cmDsCalFineCoefTablePopulate  OBJECT-TYPE
    SYNTAX      TruthValue
    MAX-ACCESS  read-write
    STATUS      current
    DESCRIPTION
        "When set to true(1), the downstream fine coefficient data will be 
         loaded into the cmDsCalFineCoefTable.  If the table is already 
         populated, it will be flushed and re-populated.  If the amount of RAM
         available on the device becomes low while populating the table, an 
         error code of RESOURCE UNAVAILABLE will be returned, and the table
         population will be incomplete.  Setting this object to false(2) will 
         flush the cmDsCalFineCoefTable.
         
         When read, this object indicates the current state of the 
         cmDsCalFineCoefTable.  A value of true(1) indicates that the table was
         successfully populated.  A value of false(2) indicates that the table
         is either unpopulated, or that insufficient RAM was available to 
         complete the population and that the table is incomplete."
    ::= { cmEngrDownstreamCalibration 30 }
    
cmDsCalEqCoefTablePopulate  OBJECT-TYPE
    SYNTAX      TruthValue
    MAX-ACCESS  read-write
    STATUS      current
    DESCRIPTION
        "When set to true(1), the downstream equalizer coefficient data will be 
         loaded into the cmDsCalEqCoefTable.  If the table is already 
         populated, it will be flushed and re-populated.  If the amount of RAM
         available on the device becomes low while populating the table, an 
         error code of RESOURCE UNAVAILABLE will be returned, and the table
         population will be incomplete.  Setting this object to false(2) will 
         flush the cmDsCalEqCoefTable.
         
         When read, this object indicates the current state of the 
         cmDsCalEqCoefTable.  A value of true(1) indicates that the table was
         successfully populated.  A value of false(2) indicates that the table
         is either unpopulated, or that insufficient RAM was available to 
         complete the population and that the table is incomplete."
    ::= { cmEngrDownstreamCalibration 31 }
    
    
---
--- Upstream Calibration engineering objects
---

cmEngrUpstreamCalibration OBJECT IDENTIFIER ::= { cablemodemEngineering 3 }

cmUsCalControlStartPower  OBJECT-TYPE
    SYNTAX      Integer32 (0..255)
    UNITS       "dBmV"
    MAX-ACCESS  read-write
    STATUS      current
    DESCRIPTION
        "Controls and reflects the starting power used in the 
         cmUsCalControlTable.  Changing this value will result in the size of
         the cmUsCalControlTable being altered."
    ::= { cmEngrUpstreamCalibration 1 }
    
cmUsCalControlEndPower  OBJECT-TYPE
    SYNTAX      Integer32 (0..255)
    UNITS       "dBmV"
    MAX-ACCESS  read-write
    STATUS      current
    DESCRIPTION
        "Controls and reflects the ending power used in the 
         cmUsCalControlTable.  Changing this value will result in the size of
         the cmUsCalControlTable being altered."
    ::= { cmEngrUpstreamCalibration 2 }

cmUsCalControlResolution  OBJECT-TYPE
    SYNTAX      Integer32 (0..255)
    UNITS       "hundredth dBmV"
    MAX-ACCESS  read-write
    STATUS      current
    DESCRIPTION
        "Controls and reflects the resolution used in the 
         cmUsCalControlTable.  Changing this value will result in the size of
         the cmUsCalControlTable being altered."
    ::= { cmEngrUpstreamCalibration 3 }

cmUsCalZeroControl  OBJECT-TYPE
    SYNTAX      TruthValue
    MAX-ACCESS  read-write
    STATUS      current
    DESCRIPTION
        "If set to true(1), all instances of cmUsCalControlAmpGain and
         cmUsCalControlDacAtten in the cmUsCalControlTable will be set to
         a value of zero.  When read, always returns false."
    ::= { cmEngrUpstreamCalibration 4 }

cmUsCalControlTable  OBJECT-TYPE
    SYNTAX      SEQUENCE OF CmUsCalControlEntry
    MAX-ACCESS  not-accessible
    STATUS      current
    DESCRIPTION
        "A list of control values to be used when calculating upstream 
         power for this device."
    ::= { cmEngrUpstreamCalibration 5 }
    
cmUsCalControlEntry OBJECT-TYPE
    SYNTAX      CmUsCalControlEntry
    MAX-ACCESS  not-accessible
    STATUS      current
    DESCRIPTION
        "An entry defining the control values for a given power at the given
         index for this device."
    INDEX   { cmUsCalControlIndex }
    ::= { cmUsCalControlTable 1 }
    
CmUsCalControlEntry ::= 
    SEQUENCE    {
                cmUsCalControlIndex         Integer32,
                cmUsCalControlPower         Integer32,
                cmUsCalControlAmpGain       Unsigned32,
                cmUsCalControlDacAtten      Unsigned32
    }
    
cmUsCalControlIndex OBJECT-TYPE
    SYNTAX      Integer32
    MAX-ACCESS  not-accessible
    STATUS      current
    DESCRIPTION
        "Identifies the instance of this pair of control values."
    ::= { cmUsCalControlEntry 1 }
    
cmUsCalControlPower  OBJECT-TYPE
    SYNTAX      Integer32 (0..255)
    UNITS       "hundredth dBmV"
    MAX-ACCESS  read-only
    STATUS      current
    DESCRIPTION
        "Indicates the upstream power level which is expected when the
         amp gain and DAC attenuation are programmed as indicated in this
         entry.  This value is read-only, its value depends on the values
         set in cmUsCalControlStartPower, cmUsCalControlEndPower, and
         cmUsCalControlResolution."
    ::= { cmUsCalControlEntry 2 }
    
cmUsCalControlAmpGain  OBJECT-TYPE
    SYNTAX      Unsigned32 (0..255)
    MAX-ACCESS  read-write
    STATUS      current
    DESCRIPTION
        "Controls and reflects the amplifier gain setting used to produce
         an output power equal to the value of this entry's instance of
         cmUsCalControlPower."
    ::= { cmUsCalControlEntry 3 }
    
cmUsCalControlDacAtten  OBJECT-TYPE
    SYNTAX      Unsigned32 (0..255)
    MAX-ACCESS  read-write
    STATUS      current
    DESCRIPTION
        "Controls and reflects the DAC attenuation setting used to produce
         an output power equal to the value of this entry's instance of
         cmUsCalControlPower."
    ::= { cmUsCalControlEntry 4 }

cmUsCalOffsetStartFreq  OBJECT-TYPE
    SYNTAX      Integer32 (0..255)
    UNITS       "megahertz"
    MAX-ACCESS  read-write
    STATUS      current
    DESCRIPTION
        "Controls and reflects the starting frequency used in the 
         cmUsCalOffsetTable.  Changing this value will result in the size of
         the cmUsCalOffsetTable being altered."
    ::= { cmEngrUpstreamCalibration 6 }
    
cmUsCalOffsetEndFreq  OBJECT-TYPE
    SYNTAX      Integer32 (0..255)
    UNITS       "megahertz"
    MAX-ACCESS  read-write
    STATUS      current
    DESCRIPTION
        "Controls and reflects the ending frequency used in the 
         cmUsCalOffsetTable.  Changing this value will result in the size of
         the cmUsCalOffsetTable being altered."
    ::= { cmEngrUpstreamCalibration 7 }

cmUsCalOffsetResolution  OBJECT-TYPE
    SYNTAX      Integer32 (0..255)
    UNITS       "hundredth megahertz (10 kHz)"
    MAX-ACCESS  read-write
    STATUS      current
    DESCRIPTION
        "Controls and reflects the resolution used in the 
         cmUsCalOffsetTable.  Changing this value will result in the size of
         the cmUsCalControlTable being altered."
    ::= { cmEngrUpstreamCalibration 8 }
    
cmUsCalBoardType  OBJECT-TYPE
    SYNTAX      INTEGER {
                genericUnknownDontCare(0),
                bcm93350AV2US(1),
                bcm93350AV3US(2),
                bcm93350CV0US(3),
                bcm93350iV1aUS(4),
                bcm93350iV1bUS(5),
                bcm93350VV1US(6),
                bcm93352VV0US(7),
                bcm93350AV2Euro(8),
                bcm93350AV3Euro(9),
                bcm93350CV0Euro(10),
                bcm93350iV1aEuro(11),
                bcm93350iV1bEuro(12),
                bcm93350VV1Euro(13),
                bcm93352VV0Euro(14),
                bcm93350CV2US(15),
                bcm93350CV2Euro(16),
                bcm93345I(17),
                bcm93345A(18)
    }
    MAX-ACCESS  read-write
    STATUS      current
    DESCRIPTION
        "Sets the board revision that the tables have been calibrated for; it
         helps the app warn the user about incorrect configurations (loading a 
         table that has been calibrated for a different modem).  These values 
         are the same as those found in the HAL non-vol settings."
    DEFVAL { genericUnknownDontCare }
    ::= { cmEngrUpstreamCalibration 9 }

cmUsCalAmpType  OBJECT-TYPE
    SYNTAX      INTEGER {
                lucentATTV4910(1),
                lucentATTV4911(2),
                celISG2000(3),
                anadigicsARA5050(4),
                adi8321(5),
                maxim3510(6),
                celISG3300(7),
                adi8322(8),
                broadcomInternal(9)
    }
    MAX-ACCESS  read-write
    STATUS      current
    DESCRIPTION
        "Sets the upstream amp that the tables have been calibrated for; it 
         helps the app warn the user about incorrect configurations.  These 
         values are the same as those found in the HAL non-vol settings."
    DEFVAL { broadcomInternal }
    ::= { cmEngrUpstreamCalibration 10 }

cmUsCalAmpGain  OBJECT-TYPE
    SYNTAX      Unsigned32 (0..255)
    MAX-ACCESS  read-write
    STATUS      current
    DESCRIPTION
        "Controls and reflects the current value of the amplifier gain, an 8
         bit hardware value."
    ::= { cmEngrUpstreamCalibration 11 }

cmUsCalDacAtten  OBJECT-TYPE
    SYNTAX      Unsigned32 (0..255)
    MAX-ACCESS  read-write
    STATUS      current
    DESCRIPTION
        "Controls and reflects the current value of the DAC attenuator, an 8
         bit hardware value."
    ::= { cmEngrUpstreamCalibration 12 }
    
cmUsCalTransmitNow  OBJECT-TYPE
    SYNTAX      INTEGER {
                cw(1),
                bits23(2)
    }
    MAX-ACCESS  read-write
    STATUS      current
    DESCRIPTION
        "When set to cw(1), the device will begin transmitting upstream in
         CW mode using the specified amp gain and DAC attenuation values.  When
         set to bits23(2), the device will begin transmitting upstream in 23 
         bit mode using the specified amp gain and DAC attenuation values."
    ::= { cmEngrUpstreamCalibration 13 }
    
cmUsCalControlTablePopulate  OBJECT-TYPE
    SYNTAX      TruthValue
    MAX-ACCESS  read-write
    STATUS      current
    DESCRIPTION
        "When set to true(1), the upstream calibration control data will be 
         loaded into the cmUsCalControlTable.  If the table is already 
         populated, it will be flushed and re-populated.  If the amount of RAM
         available on the device becomes low while populating the table, an 
         error code of RESOURCE UNAVAILABLE will be returned, and the table
         population will be incomplete.  Setting this object to false(2) will 
         flush the cmUsCalControlTable.
         
         When read, this object indicates the current state of the 
         cmUsCalControlTable.  A value of true(1) indicates that the table was
         successfully populated.  A value of false(2) indicates that the table
         is either unpopulated, or that insufficient RAM was available to 
         complete the population and that the table is incomplete."
    ::= { cmEngrUpstreamCalibration 14 }

---
--- Hardware engineering objects
---

cmEngrHardware OBJECT IDENTIFIER ::= { cablemodemEngineering 4 }    

cmHwDSAGI OBJECT-TYPE
    SYNTAX      Unsigned32 (0..255)
    MAX-ACCESS  read-write
    STATUS      current
    DESCRIPTION
        "IF AGC Control"
    ::= { cmEngrHardware 1 }
    
cmHwDSAGT OBJECT-TYPE
    SYNTAX      Unsigned32 (0..255)
    MAX-ACCESS  read-write
    STATUS      current
    DESCRIPTION
        "RF (Tuner) AGC Control"
    ::= { cmEngrHardware 2 }
    
cmHwSTPGA1 OBJECT-TYPE
    SYNTAX      Unsigned32 (0..16777215)
    MAX-ACCESS  read-write
    STATUS      current
    DESCRIPTION
        "IF PGA Control"
    ::= { cmEngrHardware 3 }
    
cmHwSTABW OBJECT-TYPE
    SYNTAX      Unsigned32 (0..65535)
    MAX-ACCESS  read-write
    STATUS      current
    DESCRIPTION
        "AGC Bandwidth Control"
    ::= { cmEngrHardware 4 }
    
cmHwSTABW2 OBJECT-TYPE
    SYNTAX      Unsigned32 (0..65535)
    MAX-ACCESS  read-write
    STATUS      current
    DESCRIPTION
        "AGC Bandwidth Control 2"
    ::= { cmEngrHardware 5 }

END
