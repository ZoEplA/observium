--**************************************************************************
--                                                                          
--    Copyright 2002 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-80211-factory.mib
--    Author:   Kevin O'Neal
--    Creation Date: 19-september-2002
--
--**************************************************************************
--    Description:
--
--		private MIB for cablemodem factory
--		
--**************************************************************************
--    Revision History:
--
--**************************************************************************

BRCM-80211-FACTORY-MIB DEFINITIONS ::= BEGIN

IMPORTS
    MODULE-IDENTITY,
    OBJECT-TYPE,
    Unsigned32
        FROM SNMPv2-SMI
    DisplayString
        FROM SNMPv2-TC
    cableDataFactory
        FROM BRCM-CABLEDATA-FACTORY-MIB;
                
ieee802dot11Factory MODULE-IDENTITY
    LAST-UPDATED "0209190000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata private MIB for 802.11 configuration and 
         diagnostics"
    REVISION      "0209190000Z"
    DESCRIPTION
            "Initial version of this MIB module."
    REVISION      "0304280000Z"
    DESCRIPTION
            "Added dot11DiagWlCmd object."
    REVISION      "0308220000Z"
    DESCRIPTION
            "Added dot11Country, dot11PAParameters, dot11IdleTSSI, and 
             dot11AntennaGain objects."
    ::= { cableDataFactory 5 }

-- dot11FactoryCfg: configure 802.11 setup objects
dot11FactoryCfg OBJECT IDENTIFIER ::= { ieee802dot11Factory 1 }

dot11RegDomain OBJECT-TYPE
    SYNTAX      INTEGER {
                fcc(16),
                doc(32),
                etsi(48),
                spain(49),
                france(50),
                mkk(64) -- Japan
    }
    MAX-ACCESS  read-write
    STATUS      deprecated
    DESCRIPTION
        "The 802.11 regulatory domain."
    ::= { dot11FactoryCfg 2 }
    
dot11BoardRev OBJECT-TYPE
    SYNTAX      Unsigned32
    MAX-ACCESS  read-write
    STATUS      current    
    DESCRIPTION
    	"The revision of 802.11 hardware interface."
    ::= { dot11FactoryCfg 3 }

dot11MaxPower OBJECT-TYPE
    SYNTAX      Unsigned32
    MAX-ACCESS  read-write
    STATUS      current
    DESCRIPTION        
        "Sets maximum TX power for power over temperature adjustment algorithm.  
         Used to prevent output overdrive."
    ::= { dot11FactoryCfg 4 }
    
dot11Country OBJECT-TYPE
    SYNTAX      INTEGER {
                worldWide(0),
                thailand(1),
                israel(2),
                jordan(3),
                china(4),
                japan(5),
                usa(6),
                europe(7),
                allChannels(8)
    }
    MAX-ACCESS  read-write
    STATUS      current
    DESCRIPTION
        "Restricts the channel set based on country requirements."
    ::= { dot11FactoryCfg 5 }

dot11PAParameters OBJECT-TYPE
    SYNTAX      OCTET STRING (SIZE (6))
    MAX-ACCESS  read-write
    STATUS      current
    DESCRIPTION
        "Sets PA parameters of the wireless hardware.  Used by output power 
         control algorithm."
    ::= { dot11FactoryCfg 6 }

dot11IdleTSSI OBJECT-TYPE
    SYNTAX      INTEGER (0..255)
    MAX-ACCESS  read-write
    STATUS      current
    DESCRIPTION
        "Sets idle TSSI target of the wireless hardware.  Used by output power 
        control algorithm."
    ::= { dot11FactoryCfg 7 }
    
dot11AntennaGain OBJECT-TYPE
    SYNTAX      INTEGER (0..255)
    MAX-ACCESS  read-write
    STATUS      current
    DESCRIPTION
        "Sets the antenna gain of the device.  Used by output power control 
         algorithm."
    ::= { dot11FactoryCfg 8 }


-- dot11FactoryDiagnostics: various objects for 802.11 diagnostics
dot11FactoryDiagnostics OBJECT IDENTIFIER ::= { ieee802dot11Factory 2 }

dot11DiagChannel OBJECT-TYPE
    SYNTAX      Unsigned32 (1..14)
    MAX-ACCESS  read-write
    STATUS      current
    DESCRIPTION
        "Sets test channel number.  Obeys regulatory domain restrictions - step 
         through regulatory domains to cover all channels."
    ::= { dot11FactoryDiagnostics 1 }
    
dot11DiagAntennaDiversity OBJECT-TYPE
    SYNTAX      INTEGER {
                diversityDisabledAntenna0(0),
                diversityDisabledAntenna1(1),
                diversityEnabledAntenna1(2),
                diversityEnabledAntenna0(3)
    }
    MAX-ACCESS  read-write
    STATUS      current
    DESCRIPTION
        "If diversity is disabled, then this value indicates the antenna used
         for transmission and reception.  If diversity is enabled, then this
         value controls the initial antenna used when written, and when read
         indicates the antenna on which the most recent packet was received."
    ::= { dot11FactoryDiagnostics 2 }
    
dot11DiagTxMode OBJECT-TYPE
    SYNTAX      INTEGER {
                cw(0),
                evm(1),
                normal(2)
    }
    MAX-ACCESS  read-write
    STATUS      current
    DESCRIPTION
        "cw(0) is used for frequency accuracy test, evm(1) is used for error 
         vector test.  When set to normal(2), 802.11 STAs will once again be 
         able to associate with the DUT. "
    ::= { dot11FactoryDiagnostics 3 }
    
dot11DiagTxPowerLevel OBJECT-TYPE
    SYNTAX      INTEGER (1..1000)
    UNITS       "milliwatts"
    MAX-ACCESS  read-write
    STATUS      current
    DESCRIPTION
        "Sets TX test power level as permitted by regulatory domain 
         restrictions."
    ::= { dot11FactoryDiagnostics 4 }
    
dot11DiagWirelessLanCmd OBJECT-TYPE
    SYNTAX      DisplayString
    MAX-ACCESS  read-write
    STATUS      current
    DESCRIPTION
        "Sends commands to the 802.11 diagnostic and manufacturing utility.
         When read, reports the last command issued."
    ::= { dot11FactoryDiagnostics 5 }
    
dot11DiagWirelessLanOutput OBJECT-TYPE
    SYNTAX      DisplayString
    MAX-ACCESS  read-only
    STATUS      current
    DESCRIPTION
        "Reports the console output (if any) generated by the last set of the 
         dot11DiagWirelessLanCmd object."
    ::= { dot11FactoryDiagnostics 6 }
    
END
