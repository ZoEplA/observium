-- *********************************************************************
-- CISCO-FIREPOWER-AP-ETHER-MIB.my
-- 
-- MIB representation of the Cisco Firepower
-- ETHER management information model package
-- 
-- Created August 2017 by Charles Bullis
-- 
-- Copyright (c) 2005-2017 Cisco Systems, Inc. All rights reserved.
-- 
-- *********************************************************************

CISCO-FIREPOWER-AP-ETHER-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApConditionRemoteInvRslt,
    CfprApEquipmentChassisConfigState,
    CfprApEquipmentXcvrType,
    CfprApEtherCIoEpIfType,
    CfprApEtherCloudType,
    CfprApEtherErrStatsHistThresholded,
    CfprApEtherErrStatsThresholded,
    CfprApEtherExternalEpAdminState,
    CfprApEtherExternalEpLocale,
    CfprApEtherExternalPcAdminState,
    CfprApEtherExternalPcLocale,
    CfprApEtherFcoeInterfaceStatsHistThresholded,
    CfprApEtherFcoeInterfaceStatsThresholded,
    CfprApEtherFtwOperMode,
    CfprApEtherFtwPortPairFsmCurrentFsm,
    CfprApEtherFtwPortPairFsmStageName,
    CfprApEtherFtwPortPairFsmTaskItem,
    CfprApEtherFtwPortPairMode,
    CfprApEtherFtwPortPairWdtState,
    CfprApEtherIntFIoEpType,
    CfprApEtherInternalPcLocale,
    CfprApEtherLossStatsHistThresholded,
    CfprApEtherLossStatsThresholded,
    CfprApEtherNiErrStatsHistThresholded,
    CfprApEtherNiErrStatsThresholded,
    CfprApEtherPIoEpIfType,
    CfprApEtherPIoFsmCurrentFsm,
    CfprApEtherPIoFsmStageName,
    CfprApEtherPauseStatsHistThresholded,
    CfprApEtherPauseStatsThresholded,
    CfprApEtherRxStatsHistThresholded,
    CfprApEtherRxStatsThresholded,
    CfprApEtherSatelliteConnectionDisc,
    CfprApEtherServerIntFIoAdminState,
    CfprApEtherServerIntFIoFsmCurrentFsm,
    CfprApEtherServerIntFIoFsmStageName,
    CfprApEtherServerIntFIoFsmTaskItem,
    CfprApEtherServerIntFIoIfRole,
    CfprApEtherServerIntFIoLocale,
    CfprApEtherServerIntFIoPcEpIfRole,
    CfprApEtherServerIntFIoPcEpPortId,
    CfprApEtherServerIntFIoPcIfRole,
    CfprApEtherServerIntFIoPcPortId,
    CfprApEtherServerIntFIoPcTransport,
    CfprApEtherServerIntFIoPcType,
    CfprApEtherServerIntFIoTransport,
    CfprApEtherServerIntFIoType,
    CfprApEtherSwitchIntFIoAck,
    CfprApEtherSwitchIntFIoIfRole,
    CfprApEtherSwitchIntFIoLocale,
    CfprApEtherSwitchIntFIoPcEpIfRole,
    CfprApEtherSwitchIntFIoPcEpPortId,
    CfprApEtherSwitchIntFIoPcIfRole,
    CfprApEtherSwitchIntFIoPcPortId,
    CfprApEtherSwitchIntFIoPcTransport,
    CfprApEtherSwitchIntFIoPcType,
    CfprApEtherSwitchIntFIoTransport,
    CfprApEtherSwitchIntFIoType,
    CfprApEtherTxStatsHistThresholded,
    CfprApEtherTxStatsThresholded,
    CfprApFabricAdminState,
    CfprApFabricMembershipStatus,
    CfprApFsmCompletion,
    CfprApFsmFlags,
    CfprApFsmFsmStageStatus,
    CfprApFsmLifecycle,
    CfprApLicenseState,
    CfprApNetworkConnectionType,
    CfprApNetworkLocale,
    CfprApNetworkPhysEpIfType,
    CfprApNetworkPortOperState,
    CfprApNetworkPortRole,
    CfprApNetworkSwitchId,
    CfprApNetworkTransport,
    CfprApPortDuplex,
    CfprApPortEncap,
    CfprApPortEthSpeed,
    CfprApPortMode
        FROM CISCO-FIREPOWER-AP-TC-MIB;

cfprApEtherObjects MODULE-IDENTITY
    LAST-UPDATED    "201708230000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        ETHER management information model package"
    ::= { ciscoFirepowerApMIBObjects 21 }

cfprApEtherErrStatsTable OBJECT-TYPE
    SYNTAX           SEQUENCE OF CfprApEtherErrStatsEntry
    MAX-ACCESS       not-accessible
    STATUS           current
    DESCRIPTION
        "Cisco Firepower ether:ErrStats managed object table"
    ::= { cfprApEtherObjects 1 }

cfprApEtherErrStatsEntry OBJECT-TYPE
    SYNTAX           CfprApEtherErrStatsEntry
    MAX-ACCESS       not-accessible
    STATUS           current
    DESCRIPTION
        "Entry for the cfprApEtherErrStatsTable table."
    INDEX { cfprApEtherErrStatsInstanceId }
    ::= { cfprApEtherErrStatsTable 1 }

CfprApEtherErrStatsEntry ::= SEQUENCE {
    cfprApEtherErrStatsInstanceId                                    CfprApManagedObjectId,
    cfprApEtherErrStatsDn                                            CfprApManagedObjectDn,
    cfprApEtherErrStatsRn                                            SnmpAdminString,
    cfprApEtherErrStatsAlign                                         Unsigned64,
    cfprApEtherErrStatsAlignDelta                                    Counter64,
    cfprApEtherErrStatsAlignDeltaAvg                                 Unsigned64,
    cfprApEtherErrStatsAlignDeltaMax                                 Unsigned64,
    cfprApEtherErrStatsAlignDeltaMin                                 Unsigned64,
    cfprApEtherErrStatsDeferredTx                                    Unsigned64,
    cfprApEtherErrStatsDeferredTxDelta                               Counter64,
    cfprApEtherErrStatsDeferredTxDeltaAvg                            Unsigned64,
    cfprApEtherErrStatsDeferredTxDeltaMax                            Unsigned64,
    cfprApEtherErrStatsDeferredTxDeltaMin                            Unsigned64,
    cfprApEtherErrStatsFcs                                           Unsigned64,
    cfprApEtherErrStatsFcsDelta                                      Counter64,
    cfprApEtherErrStatsFcsDeltaAvg                                   Unsigned64,
    cfprApEtherErrStatsFcsDeltaMax                                   Unsigned64,
    cfprApEtherErrStatsFcsDeltaMin                                   Unsigned64,
    cfprApEtherErrStatsIntMacRx                                      Unsigned64,
    cfprApEtherErrStatsIntMacRxDelta                                 Counter64,
    cfprApEtherErrStatsIntMacRxDeltaAvg                              Unsigned64,
    cfprApEtherErrStatsIntMacRxDeltaMax                              Unsigned64,
    cfprApEtherErrStatsIntMacRxDeltaMin                              Unsigned64,
    cfprApEtherErrStatsIntMacTx                                      Unsigned64,
    cfprApEtherErrStatsIntMacTxDelta                                 Counter64,
    cfprApEtherErrStatsIntMacTxDeltaAvg                              Unsigned64,
    cfprApEtherErrStatsIntMacTxDeltaMax                              Unsigned64,
    cfprApEtherErrStatsIntMacTxDeltaMin                              Unsigned64,
    cfprApEtherErrStatsIntervals                                     Gauge32,
    cfprApEtherErrStatsOutDiscard                                    Unsigned64,
    cfprApEtherErrStatsOutDiscardDelta                               Counter64,
    cfprApEtherErrStatsOutDiscardDeltaAvg                            Unsigned64,
    cfprApEtherErrStatsOutDiscardDeltaMax                            Unsigned64,
    cfprApEtherErrStatsOutDiscardDeltaMin                            Unsigned64,
    cfprApEtherErrStatsRcv                                           Unsigned64,
    cfprApEtherErrStatsRcvDelta                                      Counter64,
    cfprApEtherErrStatsRcvDeltaAvg                                   Unsigned64,
    cfprApEtherErrStatsRcvDeltaMax                                   Unsigned64,
    cfprApEtherErrStatsRcvDeltaMin                                   Unsigned64,
    cfprApEtherErrStatsSuspect                                       TruthValue,
    cfprApEtherErrStatsThresholded                                   CfprApEtherErrStatsThresholded,
    cfprApEtherErrStatsTimeCollected                                 DateAndTime,
    cfprApEtherErrStatsUnderSize                                     Unsigned64,
    cfprApEtherErrStatsUnderSizeDelta                                Counter64,
    cfprApEtherErrStatsUnderSizeDeltaAvg                             Unsigned64,
    cfprApEtherErrStatsUnderSizeDeltaMax                             Unsigned64,
    cfprApEtherErrStatsUnderSizeDeltaMin                             Unsigned64,
    cfprApEtherErrStatsUpdate                                        Gauge32,
    cfprApEtherErrStatsXmit                                          Unsigned64,
    cfprApEtherErrStatsXmitDelta                                     Counter64,
    cfprApEtherErrStatsXmitDeltaAvg                                  Unsigned64,
    cfprApEtherErrStatsXmitDeltaMax                                  Unsigned64,
    cfprApEtherErrStatsXmitDeltaMin                                  Unsigned64
}

cfprApEtherErrStatsInstanceId OBJECT-TYPE
    SYNTAX       CfprApManagedObjectId
    MAX-ACCESS   not-accessible
    STATUS       current
    DESCRIPTION
        "Instance identifier of the managed object."
    ::= { cfprApEtherErrStatsEntry 1 }

cfprApEtherErrStatsDn OBJECT-TYPE
    SYNTAX       CfprApManagedObjectDn
    MAX-ACCESS   read-only
    STATUS       current
    DESCRIPTION
        "Cisco Firepower ether:ErrStats:dn managed object property"
    ::= { cfprApEtherErrStatsEntry 2 }

cfprApEtherErrStatsRn OBJECT-TYPE
    SYNTAX       SnmpAdminString
    MAX-ACCESS   read-only
    STATUS       current
    DESCRIPTION
        "Cisco Firepower ether:ErrStats:rn managed object property"
    ::= { cfprApEtherErrStatsEntry 3 }

cfprApEtherErrStatsAlign OBJECT-TYPE
    SYNTAX       Unsigned64
    MAX-ACCESS   read-only
    STATUS       current
    DESCRIPTION
        "Cisco Firepower ether:ErrStats:align managed object property"
    ::= { cfprApEtherErrStatsEntry 4 }

cfprApEtherErrStatsAlignDelta OBJECT-TYPE
    SYNTAX       Counter64
    MAX-ACCESS   read-only
    STATUS       current
    DESCRIPTION
        "Cisco Firepower ether:ErrStats:alignDelta managed
        object property"
    ::= { cfprApEtherErrStatsEntry 5 }

cfprApEtherErrStatsAlignDeltaAvg OBJECT-TYPE
    SYNTAX       Unsigned64
    MAX-ACCESS   read-only
    STATUS       current
    DESCRIPTION
        "Cisco Firepower ether:ErrStats:alignDeltaAvg managed
        object property"
    ::= { cfprApEtherErrStatsEntry 6 }

cfprApEtherErrStatsAlignDeltaMax OBJECT-TYPE
    SYNTAX       Unsigned64
    MAX-ACCESS   read-only
    STATUS       current
    DESCRIPTION
        "Cisco Firepower ether:ErrStats:alignDeltaMax managed
        object property"
    ::= { cfprApEtherErrStatsEntry 7 }

cfprApEtherErrStatsAlignDeltaMin OBJECT-TYPE
    SYNTAX       Unsigned64
    MAX-ACCESS   read-only
    STATUS       current
    DESCRIPTION
        "Cisco Firepower ether:ErrStats:alignDeltaMin managed
        object property"
    ::= { cfprApEtherErrStatsEntry 8 }

cfprApEtherErrStatsDeferredTx OBJECT-TYPE
    SYNTAX       Unsigned64
    MAX-ACCESS   read-only
    STATUS       current
    DESCRIPTION
        "Cisco Firepower ether:ErrStats:deferredTx managed
        object property"
    ::= { cfprApEtherErrStatsEntry 9 }

cfprApEtherErrStatsDeferredTxDelta OBJECT-TYPE
    SYNTAX       Counter64
    MAX-ACCESS   read-only
    STATUS       current
    DESCRIPTION
        "Cisco Firepower ether:ErrStats:deferredTxDelta
        managed object property"
    ::= { cfprApEtherErrStatsEntry 10 }

cfprApEtherErrStatsDeferredTxDeltaAvg OBJECT-TYPE
    SYNTAX       Unsigned64
    MAX-ACCESS   read-only
    STATUS       current
    DESCRIPTION
        "Cisco Firepower ether:ErrStats:deferredTxDeltaAvg
        managed object property"
    ::= { cfprApEtherErrStatsEntry 11 }

cfprApEtherErrStatsDeferredTxDeltaMax OBJECT-TYPE
    SYNTAX       Unsigned64
    MAX-ACCESS   read-only
    STATUS       current
    DESCRIPTION
        "Cisco Firepower ether:ErrStats:deferredTxDeltaMax
        managed object property"
    ::= { cfprApEtherErrStatsEntry 12 }

cfprApEtherErrStatsDeferredTxDeltaMin OBJECT-TYPE
    SYNTAX       Unsigned64
    MAX-ACCESS   read-only
    STATUS       current
    DESCRIPTION
        "Cisco Firepower ether:ErrStats:deferredTxDeltaMin
        managed object property"
    ::= { cfprApEtherErrStatsEntry 13 }

cfprApEtherErrStatsFcs OBJECT-TYPE
    SYNTAX       Unsigned64
    MAX-ACCESS   read-only
    STATUS       current
    DESCRIPTION
        "Cisco Firepower ether:ErrStats:fcs managed object property"
    ::= { cfprApEtherErrStatsEntry 14 }

cfprApEtherErrStatsFcsDelta OBJECT-TYPE
    SYNTAX       Counter64
    MAX-ACCESS   read-only
    STATUS       current
    DESCRIPTION
        "Cisco Firepower ether:ErrStats:fcsDelta managed object property"
    ::= { cfprApEtherErrStatsEntry 15 }

cfprApEtherErrStatsFcsDeltaAvg OBJECT-TYPE
    SYNTAX       Unsigned64
    MAX-ACCESS   read-only
    STATUS       current
    DESCRIPTION
        "Cisco Firepower ether:ErrStats:fcsDeltaAvg managed
        object property"
    ::= { cfprApEtherErrStatsEntry 16 }

cfprApEtherErrStatsFcsDeltaMax OBJECT-TYPE
    SYNTAX       Unsigned64
    MAX-ACCESS   read-only
    STATUS       current
    DESCRIPTION
        "Cisco Firepower ether:ErrStats:fcsDeltaMax managed
        object property"
    ::= { cfprApEtherErrStatsEntry 17 }

cfprApEtherErrStatsFcsDeltaMin OBJECT-TYPE
    SYNTAX       Unsigned64
    MAX-ACCESS   read-only
    STATUS       current
    DESCRIPTION
        "Cisco Firepower ether:ErrStats:fcsDeltaMin managed
        object property"
    ::= { cfprApEtherErrStatsEntry 18 }

cfprApEtherErrStatsIntMacRx OBJECT-TYPE
    SYNTAX       Unsigned64
    MAX-ACCESS   read-only
    STATUS       current
    DESCRIPTION
        "Cisco Firepower ether:ErrStats:intMacRx managed object property"
    ::= { cfprApEtherErrStatsEntry 19 }

cfprApEtherErrStatsIntMacRxDelta OBJECT-TYPE
    SYNTAX       Counter64
    MAX-ACCESS   read-only
    STATUS       current
    DESCRIPTION
        "Cisco Firepower ether:ErrStats:intMacRxDelta managed
        object property"
    ::= { cfprApEtherErrStatsEntry 20 }

cfprApEtherErrStatsIntMacRxDeltaAvg OBJECT-TYPE
    SYNTAX       Unsigned64
    MAX-ACCESS   read-only
    STATUS       current
    DESCRIPTION
        "Cisco Firepower ether:ErrStats:intMacRxDeltaAvg
        managed object property"
    ::= { cfprApEtherErrStatsEntry 21 }

cfprApEtherErrStatsIntMacRxDeltaMax OBJECT-TYPE
    SYNTAX       Unsigned64
    MAX-ACCESS   read-only
    STATUS       current
    DESCRIPTION
        "Cisco Firepower ether:ErrStats:intMacRxDeltaMax
        managed object property"
    ::= { cfprApEtherErrStatsEntry 22 }

cfprApEtherErrStatsIntMacRxDeltaMin OBJECT-TYPE
    SYNTAX       Unsigned64
    MAX-ACCESS   read-only
    STATUS       current
    DESCRIPTION
        "Cisco Firepower ether:ErrStats:intMacRxDeltaMin
        managed object property"
    ::= { cfprApEtherErrStatsEntry 23 }

cfprApEtherErrStatsIntMacTx OBJECT-TYPE
    SYNTAX       Unsigned64
    MAX-ACCESS   read-only
    STATUS       current
    DESCRIPTION
        "Cisco Firepower ether:ErrStats:intMacTx managed object property"
    ::= { cfprApEtherErrStatsEntry 24 }

cfprApEtherErrStatsIntMacTxDelta OBJECT-TYPE
    SYNTAX       Counter64
    MAX-ACCESS   read-only
    STATUS       current
    DESCRIPTION
        "Cisco Firepower ether:ErrStats:intMacTxDelta managed
        object property"
    ::= { cfprApEtherErrStatsEntry 25 }

cfprApEtherErrStatsIntMacTxDeltaAvg OBJECT-TYPE
    SYNTAX       Unsigned64
    MAX-ACCESS   read-only
    STATUS       current
    DESCRIPTION
        "Cisco Firepower ether:ErrStats:intMacTxDeltaAvg
        managed object property"
    ::= { cfprApEtherErrStatsEntry 26 }

cfprApEtherErrStatsIntMacTxDeltaMax OBJECT-TYPE
    SYNTAX       Unsigned64
    MAX-ACCESS   read-only
    STATUS       current
    DESCRIPTION
        "Cisco Firepower ether:ErrStats:intMacTxDeltaMax
        managed object property"
    ::= { cfprApEtherErrStatsEntry 27 }

cfprApEtherErrStatsIntMacTxDeltaMin OBJECT-TYPE
    SYNTAX       Unsigned64
    MAX-ACCESS   read-only
    STATUS       current
    DESCRIPTION
        "Cisco Firepower ether:ErrStats:intMacTxDeltaMin
        managed object property"
    ::= { cfprApEtherErrStatsEntry 28 }

cfprApEtherErrStatsIntervals OBJECT-TYPE
    SYNTAX       Gauge32
    MAX-ACCESS   read-only
    STATUS       current
    DESCRIPTION
        "Cisco Firepower ether:ErrStats:intervals managed object property"
    ::= { cfprApEtherErrStatsEntry 29 }

cfprApEtherErrStatsOutDiscard OBJECT-TYPE
    SYNTAX       Unsigned64
    MAX-ACCESS   read-only
    STATUS       current
    DESCRIPTION
        "Cisco Firepower ether:ErrStats:outDiscard managed
        object property"
    ::= { cfprApEtherErrStatsEntry 30 }

cfprApEtherErrStatsOutDiscardDelta OBJECT-TYPE
    SYNTAX       Counter64
    MAX-ACCESS   read-only
    STATUS       current
    DESCRIPTION
        "Cisco Firepower ether:ErrStats:outDiscardDelta
        managed object property"
    ::= { cfprApEtherErrStatsEntry 31 }

cfprApEtherErrStatsOutDiscardDeltaAvg OBJECT-TYPE
    SYNTAX       Unsigned64
    MAX-ACCESS   read-only
    STATUS       current
    DESCRIPTION
        "Cisco Firepower ether:ErrStats:outDiscardDeltaAvg
        managed object property"
    ::= { cfprApEtherErrStatsEntry 32 }

cfprApEtherErrStatsOutDiscardDeltaMax OBJECT-TYPE
    SYNTAX       Unsigned64
    MAX-ACCESS   read-only
    STATUS       current
    DESCRIPTION
        "Cisco Firepower ether:ErrStats:outDiscardDeltaMax
        managed object property"
    ::= { cfprApEtherErrStatsEntry 33 }

cfprApEtherErrStatsOutDiscardDeltaMin OBJECT-TYPE
    SYNTAX       Unsigned64
    MAX-ACCESS   read-only
    STATUS       current
    DESCRIPTION
        "Cisco Firepower ether:ErrStats:outDiscardDeltaMin
        managed object property"
    ::= { cfprApEtherErrStatsEntry 34 }

cfprApEtherErrStatsRcv OBJECT-TYPE
    SYNTAX       Unsigned64
    MAX-ACCESS   read-only
    STATUS       current
    DESCRIPTION
        "Cisco Firepower ether:ErrStats:rcv managed object property"
    ::= { cfprApEtherErrStatsEntry 35 }

cfprApEtherErrStatsRcvDelta OBJECT-TYPE
    SYNTAX       Counter64
    MAX-ACCESS   read-only
    STATUS       current
    DESCRIPTION
        "Cisco Firepower ether:ErrStats:rcvDelta managed object property"
    ::= { cfprApEtherErrStatsEntry 36 }

cfprApEtherErrStatsRcvDeltaAvg OBJECT-TYPE
    SYNTAX       Unsigned64
    MAX-ACCESS   read-only
    STATUS       current
    DESCRIPTION
        "Cisco Firepower ether:ErrStats:rcvDeltaAvg managed
        object property"
    ::= { cfprApEtherErrStatsEntry 37 }

cfprApEtherErrStatsRcvDeltaMax OBJECT-TYPE
    SYNTAX       Unsigned64
    MAX-ACCESS   read-only
    STATUS       current
    DESCRIPTION
        "Cisco Firepower ether:ErrStats:rcvDeltaMax managed
        object property"
    ::= { cfprApEtherErrStatsEntry 38 }

cfprApEtherErrStatsRcvDeltaMin OBJECT-TYPE
    SYNTAX       Unsigned64
    MAX-ACCESS   read-only
    STATUS       current
    DESCRIPTION
        "Cisco Firepower ether:ErrStats:rcvDeltaMin managed
        object property"
    ::= { cfprApEtherErrStatsEntry 39 }

cfprApEtherErrStatsSuspect OBJECT-TYPE
    SYNTAX       TruthValue
    MAX-ACCESS   read-only
    STATUS       current
    DESCRIPTION
        "Cisco Firepower ether:ErrStats:suspect managed object property"
    ::= { cfprApEtherErrStatsEntry 40 }

cfprApEtherErrStatsThresholded OBJECT-TYPE
    SYNTAX       CfprApEtherErrStatsThresholded
    MAX-ACCESS   read-only
    STATUS       current
    DESCRIPTION
        "Cisco Firepower ether:ErrStats:thresholded managed
        object property"
    ::= { cfprApEtherErrStatsEntry 41 }

cfprApEtherErrStatsTimeCollected OBJECT-TYPE
    SYNTAX       DateAndTime
    MAX-ACCESS   read-only
    STATUS       current
    DESCRIPTION
        "Cisco Firepower ether:ErrStats:timeCollected managed
        object property"
    ::= { cfprApEtherErrStatsEntry 42 }

cfprApEtherErrStatsUnderSize OBJECT-TYPE
    SYNTAX       Unsigned64
    MAX-ACCESS   read-only
    STATUS       current
    DESCRIPTION
        "Cisco Firepower ether:ErrStats:underSize managed object property"
    ::= { cfprApEtherErrStatsEntry 43 }

cfprApEtherErrStatsUnderSizeDelta OBJECT-TYPE
    SYNTAX       Counter64
    MAX-ACCESS   read-only
    STATUS       current
    DESCRIPTION
        "Cisco Firepower ether:ErrStats:underSizeDelta
        managed object property"
    ::= { cfprApEtherErrStatsEntry 44 }

cfprApEtherErrStatsUnderSizeDeltaAvg OBJECT-TYPE
    SYNTAX       Unsigned64
    MAX-ACCESS   read-only
    STATUS       current
    DESCRIPTION
        "Cisco Firepower ether:ErrStats:underSizeDeltaAvg
        managed object property"
    ::= { cfprApEtherErrStatsEntry 45 }

cfprApEtherErrStatsUnderSizeDeltaMax OBJECT-TYPE
    SYNTAX       Unsigned64
    MAX-ACCESS   read-only
    STATUS       current
    DESCRIPTION
        "Cisco Firepower ether:ErrStats:underSizeDeltaMax
        managed object property"
    ::= { cfprApEtherErrStatsEntry 46 }

cfprApEtherErrStatsUnderSizeDeltaMin OBJECT-TYPE
    SYNTAX       Unsigned64
    MAX-ACCESS   read-only
    STATUS       current
    DESCRIPTION
        "Cisco Firepower ether:ErrStats:underSizeDeltaMin
        managed object property"
    ::= { cfprApEtherErrStatsEntry 47 }

cfprApEtherErrStatsUpdate OBJECT-TYPE
    SYNTAX       Gauge32
    MAX-ACCESS   read-only
    STATUS       current
    DESCRIPTION
        "Cisco Firepower ether:ErrStats:update managed object property"
    ::= { cfprApEtherErrStatsEntry 48 }

cfprApEtherErrStatsXmit OBJECT-TYPE
    SYNTAX       Unsigned64
    MAX-ACCESS   read-only
    STATUS       current
    DESCRIPTION
        "Cisco Firepower ether:ErrStats:xmit managed object property"
    ::= { cfprApEtherErrStatsEntry 49 }

cfprApEtherErrStatsXmitDelta OBJECT-TYPE
    SYNTAX       Counter64
    MAX-ACCESS   read-only
    STATUS       current
    DESCRIPTION
        "Cisco Firepower ether:ErrStats:xmitDelta managed object property"
    ::= { cfprApEtherErrStatsEntry 50 }

cfprApEtherErrStatsXmitDeltaAvg OBJECT-TYPE
    SYNTAX       Unsigned64
    MAX-ACCESS   read-only
    STATUS       current
    DESCRIPTION
        "Cisco Firepower ether:ErrStats:xmitDeltaAvg managed
        object property"
    ::= { cfprApEtherErrStatsEntry 51 }

cfprApEtherErrStatsXmitDeltaMax OBJECT-TYPE
    SYNTAX       Unsigned64
    MAX-ACCESS   read-only
    STATUS       current
    DESCRIPTION
        "Cisco Firepower ether:ErrStats:xmitDeltaMax managed
        object property"
    ::= { cfprApEtherErrStatsEntry 52 }

cfprApEtherErrStatsXmitDeltaMin OBJECT-TYPE
    SYNTAX       Unsigned64
    MAX-ACCESS   read-only
    STATUS       current
    DESCRIPTION
        "Cisco Firepower ether:ErrStats:xmitDeltaMin managed
        object property"
    ::= { cfprApEtherErrStatsEntry 53 }

cfprApEtherErrStatsHistTable OBJECT-TYPE
    SYNTAX           SEQUENCE OF CfprApEtherErrStatsHistEntry
    MAX-ACCESS       not-accessible
    STATUS           current
    DESCRIPTION
        "Cisco Firepower ether:ErrStatsHist managed object table"
    ::= { cfprApEtherObjects 2 }

cfprApEtherErrStatsHistEntry OBJECT-TYPE
    SYNTAX           CfprApEtherErrStatsHistEntry
    MAX-ACCESS       not-accessible
    STATUS           current
    DESCRIPTION
        "Entry for the cfprApEtherErrStatsHistTable table."
    INDEX { cfprApEtherErrStatsHistInstanceId }
    ::= { cfprApEtherErrStatsHistTable 1 }

CfprApEtherErrStatsHistEntry ::= SEQUENCE {
    cfprApEtherErrStatsHistInstanceId                                CfprApManagedObjectId,
    cfprApEtherErrStatsHistDn                                        CfprApManagedObjectDn,
    cfprApEtherErrStatsHistRn                                        SnmpAdminString,
    cfprApEtherErrStatsHistAlign                                     Unsigned64,
    cfprApEtherErrStatsHistAlignDelta                                Unsigned64,
    cfprApEtherErrStatsHistAlignDeltaAvg                             Unsigned64,
    cfprApEtherErrStatsHistAlignDeltaMax                             Unsigned64,
    cfprApEtherErrStatsHistAlignDeltaMin                             Unsigned64,
    cfprApEtherErrStatsHistDeferredTx                                Unsigned64,
    cfprApEtherErrStatsHistDeferredTxDelta                           Unsigned64,
    cfprApEtherErrStatsHistDeferredTxDeltaAvg                        Unsigned64,
    cfprApEtherErrStatsHistDeferredTxDeltaMax                        Unsigned64,
    cfprApEtherErrStatsHistDeferredTxDeltaMin                        Unsigned64,
    cfprApEtherErrStatsHistFcs                                       Unsigned64,
    cfprApEtherErrStatsHistFcsDelta                                  Unsigned64,
    cfprApEtherErrStatsHistFcsDeltaAvg                               Unsigned64,
    cfprApEtherErrStatsHistFcsDeltaMax                               Unsigned64,
    cfprApEtherErrStatsHistFcsDeltaMin                               Unsigned64,
    cfprApEtherErrStatsHistId                                        Unsigned64,
    cfprApEtherErrStatsHistIntMacRx                                  Unsigned64,
    cfprApEtherErrStatsHistIntMacRxDelta                             Unsigned64,
    cfprApEtherErrStatsHistIntMacRxDeltaAvg                          Unsigned64,
    cfprApEtherErrStatsHistIntMacRxDeltaMax                          Unsigned64,
    cfprApEtherErrStatsHistIntMacRxDeltaMin                          Unsigned64,
    cfprApEtherErrStatsHistIntMacTx                                  Unsigned64,
    cfprApEtherErrStatsHistIntMacTxDelta                             Unsigned64,
    cfprApEtherErrStatsHistIntMacTxDeltaAvg                          Unsigned64,
    cfprApEtherErrStatsHistIntMacTxDeltaMax                          Unsigned64,
    cfprApEtherErrStatsHistIntMacTxDeltaMin                          Unsigned64,
    cfprApEtherErrStatsHistMostRecent                                TruthValue,
    cfprApEtherErrStatsHistOutDiscard                                Unsigned64,
    cfprApEtherErrStatsHistOutDiscardDelta                           Unsigned64,
    cfprApEtherErrStatsHistOutDiscardDeltaAvg                        Unsigned64,
    cfprApEtherErrStatsHistOutDiscardDeltaMax                        Unsigned64,
    cfprApEtherErrStatsHistOutDiscardDeltaMin                        Unsigned64,
    cfprApEtherErrStatsHistRcv                                       Unsigned64,
    cfprApEtherErrStatsHistRcvDelta                                  Unsigned64,
    cfprApEtherErrStatsHistRcvDeltaAvg                               Unsigned64,
    cfprApEtherErrStatsHistRcvDeltaMax                               Unsigned64,
    cfprApEtherErrStatsHistRcvDeltaMin                               Unsigned64,
    cfprApEtherErrStatsHistSuspect                                   TruthValue,
    cfprApEtherErrStatsHistThresholded                               CfprApEtherErrStatsHistThresholded,
    cfprApEtherErrStatsHistTimeCollected                             DateAndTime,
    cfprApEtherErrStatsHistUnderSize                                 Unsigned64,
    cfprApEtherErrStatsHistUnderSizeDelta                            Unsigned64,
    cfprApEtherErrStatsHistUnderSizeDeltaAvg                         Unsigned64,
    cfprApEtherErrStatsHistUnderSizeDeltaMax                         Unsigned64,
    cfprApEtherErrStatsHistUnderSizeDeltaMin                         Unsigned64,
    cfprApEtherErrStatsHistXmit                                      Unsigned64,
    cfprApEtherErrStatsHistXmitDelta                                 Unsigned64,
    cfprApEtherErrStatsHistXmitDeltaAvg                              Unsigned64,
    cfprApEtherErrStatsHistXmitDeltaMax                              Unsigned64,
    cfprApEtherErrStatsHistXmitDeltaMin                              Unsigned64
}

cfprApEtherErrStatsHistInstanceId OBJECT-TYPE
    SYNTAX       CfprApManagedObjectId
    MAX-ACCESS   not-accessible
    STATUS       current
    DESCRIPTION
        "Instance identifier of the managed object."
    ::= { cfprApEtherErrStatsHistEntry 1 }

cfprApEtherErrStatsHistDn OBJECT-TYPE
    SYNTAX       CfprApManagedObjectDn
    MAX-ACCESS   read-only
    STATUS       current
    DESCRIPTION
        "Cisco Firepower ether:ErrStatsHist:dn managed object property"
    ::= { cfprApEtherErrStatsHistEntry 2 }

cfprApEtherErrStatsHistRn OBJECT-TYPE
    SYNTAX       SnmpAdminString
    MAX-ACCESS   read-only
    STATUS       current
    DESCRIPTION
        "Cisco Firepower ether:ErrStatsHist:rn managed object property"
    ::= { cfprApEtherErrStatsHistEntry 3 }

cfprApEtherErrStatsHistAlign OBJECT-TYPE
    SYNTAX       Unsigned64
    MAX-ACCESS   read-only
    STATUS       current
    DESCRIPTION
        "Cisco Firepower ether:ErrStatsHist:align managed object property"
    ::= { cfprApEtherErrStatsHistEntry 4 }

cfprApEtherErrStatsHistAlignDelta OBJECT-TYPE
    SYNTAX       Unsigned64
    MAX-ACCESS   read-only
    STATUS       current
    DESCRIPTION
        "Cisco Firepower ether:ErrStatsHist:alignDelta
        managed object property"
    ::= { cfprApEtherErrStatsHistEntry 5 }

cfprApEtherErrStatsHistAlignDeltaAvg OBJECT-TYPE
    SYNTAX       Unsigned64
    MAX-ACCESS   read-only
    STATUS       current
    DESCRIPTION
        "Cisco Firepower ether:ErrStatsHist:alignDeltaAvg
        managed object property"
    ::= { cfprApEtherErrStatsHistEntry 6 }

cfprApEtherErrStatsHistAlignDeltaMax OBJECT-TYPE
    SYNTAX       Unsigned64
    MAX-ACCESS   read-only
    STATUS       current
    DESCRIPTION
        "Cisco Firepower ether:ErrStatsHist:alignDeltaMax
        managed object property"
    ::= { cfprApEtherErrStatsHistEntry 7 }

cfprApEtherErrStatsHistAlignDeltaMin OBJECT-TYPE
    SYNTAX       Unsigned64
    MAX-ACCESS   read-only
    STATUS       current
    DESCRIPTION
        "Cisco Firepower ether:ErrStatsHist:alignDeltaMin
        managed object property"
    ::= { cfprApEtherErrStatsHistEntry 8 }

cfprApEtherErrStatsHistDeferredTx OBJECT-TYPE
    SYNTAX       Unsigned64
    MAX-ACCESS   read-only
    STATUS       current
    DESCRIPTION
        "Cisco Firepower ether:ErrStatsHist:deferredTx
        managed object property"
    ::= { cfprApEtherErrStatsHistEntry 9 }

cfprApEtherErrStatsHistDeferredTxDelta OBJECT-TYPE
    SYNTAX       Unsigned64
    MAX-ACCESS   read-only
    STATUS       current
    DESCRIPTION
        "Cisco Firepower ether:ErrStatsHist:deferredTxDelta
        managed object property"
    ::= { cfprApEtherErrStatsHistEntry 10 }

cfprApEtherErrStatsHistDeferredTxDeltaAvg OBJECT-TYPE
    SYNTAX       Unsigned64
    MAX-ACCESS   read-only
    STATUS       current
    DESCRIPTION
        "Cisco Firepower ether:ErrStatsHist:deferredTxDeltaAvg
        managed object property"
    ::= { cfprApEtherErrStatsHistEntry 11 }

cfprApEtherErrStatsHistDeferredTxDeltaMax OBJECT-TYPE
    SYNTAX       Unsigned64
    MAX-ACCESS   read-only
    STATUS       current
    DESCRIPTION
        "Cisco Firepower ether:ErrStatsHist:deferredTxDeltaMax
        managed object property"
    ::= { cfprApEtherErrStatsHistEntry 12 }

cfprApEtherErrStatsHistDeferredTxDeltaMin OBJECT-TYPE
    SYNTAX       Unsigned64
    MAX-ACCESS   read-only
    STATUS       current
    DESCRIPTION
        "Cisco Firepower ether:ErrStatsHist:deferredTxDeltaMin
        managed object property"
    ::= { cfprApEtherErrStatsHistEntry 13 }

cfprApEtherErrStatsHistFcs OBJECT-TYPE
    SYNTAX       Unsigned64
    MAX-ACCESS   read-only
    STATUS       current
    DESCRIPTION
        "Cisco Firepower ether:ErrStatsHist:fcs managed object property"
    ::= { cfprApEtherErrStatsHistEntry 14 }

cfprApEtherErrStatsHistFcsDelta OBJECT-TYPE
    SYNTAX       Unsigned64
    MAX-ACCESS   read-only
    STATUS       current
    DESCRIPTION
        "Cisco Firepower ether:ErrStatsHist:fcsDelta managed
        object property"
    ::= { cfprApEtherErrStatsHistEntry 15 }

cfprApEtherErrStatsHistFcsDeltaAvg OBJECT-TYPE
    SYNTAX       Unsigned64
    MAX-ACCESS   read-only
    STATUS       current
    DESCRIPTION
        "Cisco Firepower ether:ErrStatsHist:fcsDeltaAvg
        managed object property"
    ::= { cfprApEtherErrStatsHistEntry 16 }

cfprApEtherErrStatsHistFcsDeltaMax OBJECT-TYPE
    SYNTAX       Unsigned64
    MAX-ACCESS   read-only
    STATUS       current
    DESCRIPTION
        "Cisco Firepower ether:ErrStatsHist:fcsDeltaMax
        managed object property"
    ::= { cfprApEtherErrStatsHistEntry 17 }

cfprApEtherErrStatsHistFcsDeltaMin OBJECT-TYPE
    SYNTAX       Unsigned64
    MAX-ACCESS   read-only
    STATUS       current
    DESCRIPTION
        "Cisco Firepower ether:ErrStatsHist:fcsDeltaMin
        managed object property"
    ::= { cfprApEtherErrStatsHistEntry 18 }

cfprApEtherErrStatsHistId OBJECT-TYPE
    SYNTAX       Unsigned64
    MAX-ACCESS   read-only
    STATUS       current
    DESCRIPTION
        "Cisco Firepower ether:ErrStatsHist:id managed object property"
    ::= { cfprApEtherErrStatsHistEntry 19 }

cfprApEtherErrStatsHistIntMacRx OBJECT-TYPE
    SYNTAX       Unsigned64
    MAX-ACCESS   read-only
    STATUS       current
    DESCRIPTION
        "Cisco Firepower ether:ErrStatsHist:intMacRx managed
        object property"
    ::= { cfprApEtherErrStatsHistEntry 20 }

cfprApEtherErrStatsHistIntMacRxDelta OBJECT-TYPE
    SYNTAX       Unsigned64
    MAX-ACCESS   read-only
    STATUS       current
    DESCRIPTION
        "Cisco Firepower ether:ErrStatsHist:intMacRxDelta
        managed object property"
    ::= { cfprApEtherErrStatsHistEntry 21 }

cfprApEtherErrStatsHistIntMacRxDeltaAvg OBJECT-TYPE
    SYNTAX       Unsigned64
    MAX-ACCESS   read-only
    STATUS       current
    DESCRIPTION
        "Cisco Firepower ether:ErrStatsHist:intMacRxDeltaAvg
        managed object property"
    ::= { cfprApEtherErrStatsHistEntry 22 }

cfprApEtherErrStatsHistIntMacRxDeltaMax OBJECT-TYPE
    SYNTAX       Unsigned64
    MAX-ACCESS   read-only
    STATUS       current
    DESCRIPTION
        "Cisco Firepower ether:ErrStatsHist:intMacRxDeltaMax
        managed object property"
    ::= { cfprApEtherErrStatsHistEntry 23 }

cfprApEtherErrStatsHistIntMacRxDeltaMin OBJECT-TYPE
    SYNTAX       Unsigned64
    MAX-ACCESS   read-only
    STATUS       current
    DESCRIPTION
        "Cisco Firepower ether:ErrStatsHist:intMacRxDeltaMin
        managed object property"
    ::= { cfprApEtherErrStatsHistEntry 24 }

cfprApEtherErrStatsHistIntMacTx OBJECT-TYPE
    SYNTAX       Unsigned64
    MAX-ACCESS   read-only
    STATUS       current
    DESCRIPTION
        "Cisco Firepower ether:ErrStatsHist:intMacTx managed
        object property"
    ::= { cfprApEtherErrStatsHistEntry 25 }

cfprApEtherErrStatsHistIntMacTxDelta OBJECT-TYPE
    SYNTAX       Unsigned64
    MAX-ACCESS   read-only
    STATUS       current
    DESCRIPTION
        "Cisco Firepower ether:ErrStatsHist:intMacTxDelta
        managed object property"
    ::= { cfprApEtherErrStatsHistEntry 26 }

cfprApEtherErrStatsHistIntMacTxDeltaAvg OBJECT-TYPE
    SYNTAX       Unsigned64
    MAX-ACCESS   read-only
    STATUS       current
    DESCRIPTION
        "Cisco Firepower ether:ErrStatsHist:intMacTxDeltaAvg
        managed object property"
    ::= { cfprApEtherErrStatsHistEntry 27 }

cfprApEtherErrStatsHistIntMacTxDeltaMax OBJECT-TYPE
    SYNTAX       Unsigned64
    MAX-ACCESS   read-only
    STATUS       current
    DESCRIPTION
        "Cisco Firepower ether:ErrStatsHist:intMacTxDeltaMax
        managed object property"
    ::= { cfprApEtherErrStatsHistEntry 28 }

cfprApEtherErrStatsHistIntMacTxDeltaMin OBJECT-TYPE
    SYNTAX       Unsigned64
    MAX-ACCESS   read-only
    STATUS       current
    DESCRIPTION
        "Cisco Firepower ether:ErrStatsHist:intMacTxDeltaMin
        managed object property"
    ::= { cfprApEtherErrStatsHistEntry 29 }

cfprApEtherErrStatsHistMostRecent OBJECT-TYPE
    SYNTAX       TruthValue
    MAX-ACCESS   read-only
    STATUS       current
    DESCRIPTION
        "Cisco Firepower ether:ErrStatsHist:mostRecent
        managed object property"
    ::= { cfprApEtherErrStatsHistEntry 30 }

cfprApEtherErrStatsHistOutDiscard OBJECT-TYPE
    SYNTAX       Unsigned64
    MAX-ACCESS   read-only
    STATUS       current
    DESCRIPTION
        "Cisco Firepower ether:ErrStatsHist:outDiscard
        managed object property"
    ::= { cfprApEtherErrStatsHistEntry 31 }

cfprApEtherErrStatsHistOutDiscardDelta OBJECT-TYPE
    SYNTAX       Unsigned64
    MAX-ACCESS   read-only
    STATUS       current
    DESCRIPTION
        "Cisco Firepower ether:ErrStatsHist:outDiscardDelta
        managed object property"
    ::= { cfprApEtherErrStatsHistEntry 32 }

cfprApEtherErrStatsHistOutDiscardDeltaAvg OBJECT-TYPE
    SYNTAX       Unsigned64
    MAX-ACCESS   read-only
    STATUS       current
    DESCRIPTION
        "Cisco Firepower ether:ErrStatsHist:outDiscardDeltaAvg
        managed object property"
    ::= { cfprApEtherErrStatsHistEntry 33 }

cfprApEtherErrStatsHistOutDiscardDeltaMax OBJECT-TYPE
    SYNTAX       Unsigned64
    MAX-ACCESS   read-only
    STATUS       current
    DESCRIPTION
        "Cisco Firepower ether:ErrStatsHist:outDiscardDeltaMax
        managed object property"
    ::= { cfprApEtherErrStatsHistEntry 34 }

cfprApEtherErrStatsHistOutDiscardDeltaMin OBJECT-TYPE
    SYNTAX       Unsigned64
    MAX-ACCESS   read-only
    STATUS       current
    DESCRIPTION
        "Cisco Firepower ether:ErrStatsHist:outDiscardDeltaMin
        managed object property"
    ::= { cfprApEtherErrStatsHistEntry 35 }

cfprApEtherErrStatsHistRcv OBJECT-TYPE
    SYNTAX       Unsigned64
    MAX-ACCESS   read-only
    STATUS       current
    DESCRIPTION
        "Cisco Firepower ether:ErrStatsHist:rcv managed object property"
    ::= { cfprApEtherErrStatsHistEntry 36 }

cfprApEtherErrStatsHistRcvDelta OBJECT-TYPE
    SYNTAX       Unsigned64
    MAX-ACCESS   read-only
    STATUS       current
    DESCRIPTION
        "Cisco Firepower ether:ErrStatsHist:rcvDelta managed
        object property"
    ::= { cfprApEtherErrStatsHistEntry 37 }

cfprApEtherErrStatsHistRcvDeltaAvg OBJECT-TYPE
    SYNTAX       Unsigned64
    MAX-ACCESS   read-only
    STATUS       current
    DESCRIPTION
        "Cisco Firepower ether:ErrStatsHist:rcvDeltaAvg
        managed object property"
    ::= { cfprApEtherErrStatsHistEntry 38 }

cfprApEtherErrStatsHistRcvDeltaMax OBJECT-TYPE
    SYNTAX       Unsigned64
    MAX-ACCESS   read-only
    STATUS       current
    DESCRIPTION
        "Cisco Firepower ether:ErrStatsHist:rcvDeltaMax
        managed object property"
    ::= { cfprApEtherErrStatsHistEntry 39 }

cfprApEtherErrStatsHistRcvDeltaMin OBJECT-TYPE
    SYNTAX       Unsigned64
    MAX-ACCESS   read-only
    STATUS       current
    DESCRIPTION
        "Cisco Firepower ether:ErrStatsHist:rcvDeltaMin
        managed object property"
    ::= { cfprApEtherErrStatsHistEntry 40 }

cfprApEtherErrStatsHistSuspect OBJECT-TYPE
    SYNTAX       TruthValue
    MAX-ACCESS   read-only
    STATUS       current
    DESCRIPTION
        "Cisco Firepower ether:ErrStatsHist:suspect managed
        object property"
    ::= { cfprApEtherErrStatsHistEntry 41 }

cfprApEtherErrStatsHistThresholded OBJECT-TYPE
    SYNTAX       CfprApEtherErrStatsHistThresholded
    MAX-ACCESS   read-only
    STATUS       current
    DESCRIPTION
        "Cisco Firepower ether:ErrStatsHist:thresholded
        managed object property"
    ::= { cfprApEtherErrStatsHistEntry 42 }

cfprApEtherErrStatsHistTimeCollected OBJECT-TYPE
    SYNTAX       DateAndTime
    MAX-ACCESS   read-only
    STATUS       current
    DESCRIPTION
        "Cisco Firepower ether:ErrStatsHist:timeCollected
        managed object property"
    ::= { cfprApEtherErrStatsHistEntry 43 }

cfprApEtherErrStatsHistUnderSize OBJECT-TYPE
    SYNTAX       Unsigned64
    MAX-ACCESS   read-only
    STATUS       current
    DESCRIPTION
        "Cisco Firepower ether:ErrStatsHist:underSize managed
        object property"
    ::= { cfprApEtherErrStatsHistEntry 44 }

cfprApEtherErrStatsHistUnderSizeDelta OBJECT-TYPE
    SYNTAX       Unsigned64
    MAX-ACCESS   read-only
    STATUS       current
    DESCRIPTION
        "Cisco Firepower ether:ErrStatsHist:underSizeDelta
        managed object property"
    ::= { cfprApEtherErrStatsHistEntry 45 }

cfprApEtherErrStatsHistUnderSizeDeltaAvg OBJECT-TYPE
    SYNTAX       Unsigned64
    MAX-ACCESS   read-only
    STATUS       current
    DESCRIPTION
        "Cisco Firepower ether:ErrStatsHist:underSizeDeltaAvg
        managed object property"
    ::= { cfprApEtherErrStatsHistEntry 46 }

cfprApEtherErrStatsHistUnderSizeDeltaMax OBJECT-TYPE
    SYNTAX       Unsigned64
    MAX-ACCESS   read-only
    STATUS       current
    DESCRIPTION
        "Cisco Firepower ether:ErrStatsHist:underSizeDeltaMax
        managed object property"
    ::= { cfprApEtherErrStatsHistEntry 47 }

cfprApEtherErrStatsHistUnderSizeDeltaMin OBJECT-TYPE
    SYNTAX       Unsigned64
    MAX-ACCESS   read-only
    STATUS       current
    DESCRIPTION
        "Cisco Firepower ether:ErrStatsHist:underSizeDeltaMin
        managed object property"
    ::= { cfprApEtherErrStatsHistEntry 48 }

cfprApEtherErrStatsHistXmit OBJECT-TYPE
    SYNTAX       Unsigned64
    MAX-ACCESS   read-only
    STATUS       current
    DESCRIPTION
        "Cisco Firepower ether:ErrStatsHist:xmit managed object property"
    ::= { cfprApEtherErrStatsHistEntry 49 }

cfprApEtherErrStatsHistXmitDelta OBJECT-TYPE
    SYNTAX       Unsigned64
    MAX-ACCESS   read-only
    STATUS       current
    DESCRIPTION
        "Cisco Firepower ether:ErrStatsHist:xmitDelta managed
        object property"
    ::= { cfprApEtherErrStatsHistEntry 50 }

cfprApEtherErrStatsHistXmitDeltaAvg OBJECT-TYPE
    SYNTAX       Unsigned64
    MAX-ACCESS   read-only
    STATUS       current
    DESCRIPTION
        "Cisco Firepower ether:ErrStatsHist:xmitDeltaAvg
        managed object property"
    ::= { cfprApEtherErrStatsHistEntry 51 }

cfprApEtherErrStatsHistXmitDeltaMax OBJECT-TYPE
    SYNTAX       Unsigned64
    MAX-ACCESS   read-only
    STATUS       current
    DESCRIPTION
        "Cisco Firepower ether:ErrStatsHist:xmitDeltaMax
        managed object property"
    ::= { cfprApEtherErrStatsHistEntry 52 }

cfprApEtherErrStatsHistXmitDeltaMin OBJECT-TYPE
    SYNTAX       Unsigned64
    MAX-ACCESS   read-only
    STATUS       current
    DESCRIPTION
        "Cisco Firepower ether:ErrStatsHist:xmitDeltaMin
        managed object property"
    ::= { cfprApEtherErrStatsHistEntry 53 }

cfprApEtherFailToWireTable OBJECT-TYPE
    SYNTAX           SEQUENCE OF CfprApEtherFailToWireEntry
    MAX-ACCESS       not-accessible
    STATUS           current
    DESCRIPTION
        "Cisco Firepower ether:FailToWire managed object table"
    ::= { cfprApEtherObjects 3 }

cfprApEtherFailToWireEntry OBJECT-TYPE
    SYNTAX           CfprApEtherFailToWireEntry
    MAX-ACCESS       not-accessible
    STATUS           current
    DESCRIPTION
        "Entry for the cfprApEtherFailToWireTable table."
    INDEX { cfprApEtherFailToWireInstanceId }
    ::= { cfprApEtherFailToWireTable 1 }

CfprApEtherFailToWireEntry ::= SEQUENCE {
    cfprApEtherFailToWireInstanceId                                  CfprApManagedObjectId,
    cfprApEtherFailToWireDn                                          CfprApManagedObjectDn,
    cfprApEtherFailToWireRn                                          SnmpAdminString,
    cfprApEtherFailToWireLocale                                      CfprApNetworkLocale,
    cfprApEtherFailToWireName                                        SnmpAdminString,
    cfprApEtherFailToWireTransport                                   CfprApNetworkTransport,
    cfprApEtherFailToWireType                                        CfprApNetworkConnectionType
}

cfprApEtherFailToWireInstanceId OBJECT-TYPE
    SYNTAX       CfprApManagedObjectId
    MAX-ACCESS   not-accessible
    STATUS       current
    DESCRIPTION
        "Instance identifier of the managed object."
    ::= { cfprApEtherFailToWireEntry 1 }

cfprApEtherFailToWireDn OBJECT-TYPE
    SYNTAX       CfprApManagedObjectDn
    MAX-ACCESS   read-only
    STATUS       current
    DESCRIPTION
        "Cisco Firepower ether:FailToWire:dn managed object property"
    ::= { cfprApEtherFailToWireEntry 2 }

cfprApEtherFailToWireRn OBJECT-TYPE
    SYNTAX       SnmpAdminString
    MAX-ACCESS   read-only
    STATUS       current
    DESCRIPTION
        "Cisco Firepower ether:FailToWire:rn managed object property"
    ::= { cfprApEtherFailToWireEntry 3 }

cfprApEtherFailToWireLocale OBJECT-TYPE
    SYNTAX       CfprApNetworkLocale
    MAX-ACCESS   read-only
    STATUS       current
    DESCRIPTION
        "Cisco Firepower ether:FailToWire:locale managed object property"
    ::= { cfprApEtherFailToWireEntry 4 }

cfprApEtherFailToWireName OBJECT-TYPE
    SYNTAX       SnmpAdminString
    MAX-ACCESS   read-only
    STATUS       current
    DESCRIPTION
        "Cisco Firepower ether:FailToWire:name managed object property"
    ::= { cfprApEtherFailToWireEntry 5 }

cfprApEtherFailToWireTransport OBJECT-TYPE
    SYNTAX       CfprApNetworkTransport
    MAX-ACCESS   read-only
    STATUS       current
    DESCRIPTION
        "Cisco Firepower ether:FailToWire:transport managed
        object property"
    ::= { cfprApEtherFailToWireEntry 6 }

cfprApEtherFailToWireType OBJECT-TYPE
    SYNTAX       CfprApNetworkConnectionType
    MAX-ACCESS   read-only
    STATUS       current
    DESCRIPTION
        "Cisco Firepower ether:FailToWire:type managed object property"
    ::= { cfprApEtherFailToWireEntry 7 }

cfprApEtherFcoeInterfaceStatsTable OBJECT-TYPE
    SYNTAX           SEQUENCE OF CfprApEtherFcoeInterfaceStatsEntry
    MAX-ACCESS       not-accessible
    STATUS           current
    DESCRIPTION
        "Cisco Firepower ether:FcoeInterfaceStats managed object table"
    ::= { cfprApEtherObjects 4 }

cfprApEtherFcoeInterfaceStatsEntry OBJECT-TYPE
    SYNTAX           CfprApEtherFcoeInterfaceStatsEntry
    MAX-ACCESS       not-accessible
    STATUS           current
    DESCRIPTION
        "Entry for the cfprApEtherFcoeInterfaceStatsTable table."
    INDEX { cfprApEtherFcoeInterfaceStatsInstanceId }
    ::= { cfprApEtherFcoeInterfaceStatsTable 1 }

CfprApEtherFcoeInterfaceStatsEntry ::= SEQUENCE {
    cfprApEtherFcoeInterfaceStatsInstanceId                          CfprApManagedObjectId,
    cfprApEtherFcoeInterfaceStatsDn                                  CfprApManagedObjectDn,
    cfprApEtherFcoeInterfaceStatsRn                                  SnmpAdminString,
    cfprApEtherFcoeInterfaceStatsBytesRx                             Unsigned64,
    cfprApEtherFcoeInterfaceStatsBytesRxDelta                        Counter64,
    cfprApEtherFcoeInterfaceStatsBytesRxDeltaAvg                     Unsigned64,
    cfprApEtherFcoeInterfaceStatsBytesRxDeltaMax                     Unsigned64,
    cfprApEtherFcoeInterfaceStatsBytesRxDeltaMin                     Unsigned64,
    cfprApEtherFcoeInterfaceStatsBytesTx                             Unsigned64,
    cfprApEtherFcoeInterfaceStatsBytesTxDelta                        Counter64,
    cfprApEtherFcoeInterfaceStatsBytesTxDeltaAvg                     Unsigned64,
    cfprApEtherFcoeInterfaceStatsBytesTxDeltaMax                     Unsigned64,
    cfprApEtherFcoeInterfaceStatsBytesTxDeltaMin                     Unsigned64,
    cfprApEtherFcoeInterfaceStatsDroppedRx                           Unsigned64,
    cfprApEtherFcoeInterfaceStatsDroppedRxDelta                      Counter64,
    cfprApEtherFcoeInterfaceStatsDroppedRxDeltaAvg                   Unsigned64,
    cfprApEtherFcoeInterfaceStatsDroppedRxDeltaMax                   Unsigned64,
    cfprApEtherFcoeInterfaceStatsDroppedRxDeltaMin                   Unsigned64,
    cfprApEtherFcoeInterfaceStatsDroppedTx                           Unsigned64,
    cfprApEtherFcoeInterfaceStatsDroppedTxDelta                      Counter64,
    cfprApEtherFcoeInterfaceStatsDroppedTxDeltaAvg                   Unsigned64,
    cfprApEtherFcoeInterfaceStatsDroppedTxDeltaMax                   Unsigned64,
    cfprApEtherFcoeInterfaceStatsDroppedTxDeltaMin                   Unsigned64,
    cfprApEtherFcoeInterfaceStatsErrorsRx                            Unsigned64,
    cfprApEtherFcoeInterfaceStatsErrorsRxDelta                       Counter64,
    cfprApEtherFcoeInterfaceStatsErrorsRxDeltaAvg                    Unsigned64,
    cfprApEtherFcoeInterfaceStatsErrorsRxDeltaMax                    Unsigned64,
    cfprApEtherFcoeInterfaceStatsErrorsRxDeltaMin                    Unsigned64,
    cfprApEtherFcoeInterfaceStatsErrorsTx                            Unsigned64,
    cfprApEtherFcoeInterfaceStatsErrorsTxDelta                       Counter64,
    cfprApEtherFcoeInterfaceStatsErrorsTxDeltaAvg                    Unsigned64,
    cfprApEtherFcoeInterfaceStatsErrorsTxDeltaMax                    Unsigned64,
    cfprApEtherFcoeInterfaceStatsErrorsTxDeltaMin                    Unsigned64,
    cfprApEtherFcoeInterfaceStatsIntervals                           Gauge32,
    cfprApEtherFcoeInterfaceStatsPacketsRx                           Unsigned64,
    cfprApEtherFcoeInterfaceStatsPacketsRxDelta                      Counter64,
    cfprApEtherFcoeInterfaceStatsPacketsRxDeltaAvg                   Unsigned64,
    cfprApEtherFcoeInterfaceStatsPacketsRxDeltaMax                   Unsigned64,
    cfprApEtherFcoeInterfaceStatsPacketsRxDeltaMin                   Unsigned64,
    cfprApEtherFcoeInterfaceStatsPacketsTx                           Unsigned64,
    cfprApEtherFcoeInterfaceStatsPacketsTxDelta                      Counter64,
    cfprApEtherFcoeInterfaceStatsPacketsTxDeltaAvg                   Unsigned64,
    cfprApEtherFcoeInterfaceStatsPacketsTxDeltaMax                   Unsigned64,
    cfprApEtherFcoeInterfaceStatsPacketsTxDeltaMin                   Unsigned64,
    cfprApEtherFcoeInterfaceStatsSuspect                             TruthValue,
    cfprApEtherFcoeInterfaceStatsThresholded                         CfprApEtherFcoeInterfaceStatsThresholded,
    cfprApEtherFcoeInterfaceStatsTimeCollected                       DateAndTime,
    cfprApEtherFcoeInterfaceStatsUpdate                              Gauge32
}

cfprApEtherFcoeInterfaceStatsInstanceId OBJECT-TYPE
    SYNTAX       CfprApManagedObjectId
    MAX-ACCESS   not-accessible
    STATUS       current
    DESCRIPTION
        "Instance identifier of the managed object."
    ::= { cfprApEtherFcoeInterfaceStatsEntry 1 }

cfprApEtherFcoeInterfaceStatsDn OBJECT-TYPE
    SYNTAX       CfprApManagedObjectDn
    MAX-ACCESS   read-only
    STATUS       current
    DESCRIPTION
        "Cisco Firepower ether:FcoeInterfaceStats:dn managed
        object property"
    ::= { cfprApEtherFcoeInterfaceStatsEntry 2 }

cfprApEtherFcoeInterfaceStatsRn OBJECT-TYPE
    SYNTAX       SnmpAdminString
    MAX-ACCESS   read-only
    STATUS       current
    DESCRIPTION
        "Cisco Firepower ether:FcoeInterfaceStats:rn managed
        object property"
    ::= { cfprApEtherFcoeInterfaceStatsEntry 3 }

cfprApEtherFcoeInterfaceStatsBytesRx OBJECT-TYPE
    SYNTAX       Unsigned64
    MAX-ACCESS   read-only
    STATUS       current
    DESCRIPTION
        "Cisco Firepower ether:FcoeInterfaceStats:bytesRx
        managed object property"
    ::= { cfprApEtherFcoeInterfaceStatsEntry 4 }

cfprApEtherFcoeInterfaceStatsBytesRxDelta OBJECT-TYPE
    SYNTAX       Counter64
    MAX-ACCESS   read-only
    STATUS       current
    DESCRIPTION
        "Cisco Firepower ether:FcoeInterfaceStats:bytesRxDelta
        managed object property"
    ::= { cfprApEtherFcoeInterfaceStatsEntry 5 }

cfprApEtherFcoeInterfaceStatsBytesRxDeltaAvg OBJECT-TYPE
    SYNTAX       Unsigned64
    MAX-ACCESS   read-only
    STATUS       current
    DESCRIPTION
        "Cisco Firepower ether:FcoeInterfaceStats:bytesRxDeltaAvg
        managed object property"
    ::= { cfprApEtherFcoeInterfaceStatsEntry 6 }

cfprApEtherFcoeInterfaceStatsBytesRxDeltaMax OBJECT-TYPE
    SYNTAX       Unsigned64
    MAX-ACCESS   read-only
    STATUS       current
    DESCRIPTION
        "Cisco Firepower ether:FcoeInterfaceStats:bytesRxDeltaMax
        managed object property"
    ::= { cfprApEtherFcoeInterfaceStatsEntry 7 }

cfprApEtherFcoeInterfaceStatsBytesRxDeltaMin OBJECT-TYPE
    SYNTAX       Unsigned64
    MAX-ACCESS   read-only
    STATUS       current
    DESCRIPTION
        "Cisco Firepower ether:FcoeInterfaceStats:bytesRxDeltaMin
        managed object property"
    ::= { cfprApEtherFcoeInterfaceStatsEntry 8 }

cfprApEtherFcoeInterfaceStatsBytesTx OBJECT-TYPE
    SYNTAX       Unsigned64
    MAX-ACCESS   read-only
    STATUS       current
    DESCRIPTION
        "Cisco Firepower ether:FcoeInterfaceStats:bytesTx
        managed object property"
    ::= { cfprApEtherFcoeInterfaceStatsEntry 9 }

cfprApEtherFcoeInterfaceStatsBytesTxDelta OBJECT-TYPE
    SYNTAX       Counter64
    MAX-ACCESS   read-only
    STATUS       current
    DESCRIPTION
        "Cisco Firepower ether:FcoeInterfaceStats:bytesTxDelta
        managed object property"
    ::= { cfprApEtherFcoeInterfaceStatsEntry 10 }

cfprApEtherFcoeInterfaceStatsBytesTxDeltaAvg OBJECT-TYPE
    SYNTAX       Unsigned64
    MAX-ACCESS   read-only
    STATUS       current
    DESCRIPTION
        "Cisco Firepower ether:FcoeInterfaceStats:bytesTxDeltaAvg
        managed object property"
    ::= { cfprApEtherFcoeInterfaceStatsEntry 11 }

cfprApEtherFcoeInterfaceStatsBytesTxDeltaMax OBJECT-TYPE
    SYNTAX       Unsigned64
    MAX-ACCESS   read-only
    STATUS       current
    DESCRIPTION
        "Cisco Firepower ether:FcoeInterfaceStats:bytesTxDeltaMax
        managed object property"
    ::= { cfprApEtherFcoeInterfaceStatsEntry 12 }

cfprApEtherFcoeInterfaceStatsBytesTxDeltaMin OBJECT-TYPE
    SYNTAX       Unsigned64
    MAX-ACCESS   read-only
    STATUS       current
    DESCRIPTION
        "Cisco Firepower ether:FcoeInterfaceStats:bytesTxDeltaMin
        managed object property"
    ::= { cfprApEtherFcoeInterfaceStatsEntry 13 }

cfprApEtherFcoeInterfaceStatsDroppedRx OBJECT-TYPE
    SYNTAX       Unsigned64
    MAX-ACCESS   read-only
    STATUS       current
    DESCRIPTION
        "Cisco Firepower ether:FcoeInterfaceStats:droppedRx
        managed object property"
    ::= { cfprApEtherFcoeInterfaceStatsEntry 14 }

cfprApEtherFcoeInterfaceStatsDroppedRxDelta OBJECT-TYPE
    SYNTAX       Counter64
    MAX-ACCESS   read-only
    STATUS       current
    DESCRIPTION
        "Cisco Firepower ether:FcoeInterfaceStats:droppedRxDelta
        managed object property"
    ::= { cfprApEtherFcoeInterfaceStatsEntry 15 }

cfprApEtherFcoeInterfaceStatsDroppedRxDeltaAvg OBJECT-TYPE
    SYNTAX       Unsigned64
    MAX-ACCESS   read-only
    STATUS       current
    DESCRIPTION
        "Cisco Firepower ether:FcoeInterfaceStats:droppedRxDeltaAvg
        managed object property"
    ::= { cfprApEtherFcoeInterfaceStatsEntry 16 }

cfprApEtherFcoeInterfaceStatsDroppedRxDeltaMax OBJECT-TYPE
    SYNTAX       Unsigned64
    MAX-ACCESS   read-only
    STATUS       current
    DESCRIPTION
        "Cisco Firepower ether:FcoeInterfaceStats:droppedRxDeltaMax
        managed object property"
    ::= { cfprApEtherFcoeInterfaceStatsEntry 17 }

cfprApEtherFcoeInterfaceStatsDroppedRxDeltaMin OBJECT-TYPE
    SYNTAX       Unsigned64
    MAX-ACCESS   read-only
    STATUS       current
    DESCRIPTION
        "Cisco Firepower ether:FcoeInterfaceStats:droppedRxDeltaMin
        managed object property"
    ::= { cfprApEtherFcoeInterfaceStatsEntry 18 }

cfprApEtherFcoeInterfaceStatsDroppedTx OBJECT-TYPE
    SYNTAX       Unsigned64
    MAX-ACCESS   read-only
    STATUS       current
    DESCRIPTION
        "Cisco Firepower ether:FcoeInterfaceStats:droppedTx
        managed object property"
    ::= { cfprApEtherFcoeInterfaceStatsEntry 19 }

cfprApEtherFcoeInterfaceStatsDroppedTxDelta OBJECT-TYPE
    SYNTAX       Counter64
    MAX-ACCESS   read-only
    STATUS       current
    DESCRIPTION
        "Cisco Firepower ether:FcoeInterfaceStats:droppedTxDelta
        managed object property"
    ::= { cfprApEtherFcoeInterfaceStatsEntry 20 }

cfprApEtherFcoeInterfaceStatsDroppedTxDeltaAvg OBJECT-TYPE
    SYNTAX       Unsigned64
    MAX-ACCESS   read-only
    STATUS       current
    DESCRIPTION
        "Cisco Firepower ether:FcoeInterfaceStats:droppedTxDeltaAvg
        managed object property"
    ::= { cfprApEtherFcoeInterfaceStatsEntry 21 }

cfprApEtherFcoeInterfaceStatsDroppedTxDeltaMax OBJECT-TYPE
    SYNTAX       Unsigned64
    MAX-ACCESS   read-only
    STATUS       current
    DESCRIPTION
        "Cisco Firepower ether:FcoeInterfaceStats:droppedTxDeltaMax
        managed object property"
    ::= { cfprApEtherFcoeInterfaceStatsEntry 22 }

cfprApEtherFcoeInterfaceStatsDroppedTxDeltaMin OBJECT-TYPE
    SYNTAX       Unsigned64
    MAX-ACCESS   read-only
    STATUS       current
    DESCRIPTION
        "Cisco Firepower ether:FcoeInterfaceStats:droppedTxDeltaMin
        managed object property"
    ::= { cfprApEtherFcoeInterfaceStatsEntry 23 }

cfprApEtherFcoeInterfaceStatsErrorsRx OBJECT-TYPE
    SYNTAX       Unsigned64
    MAX-ACCESS   read-only
    STATUS       current
    DESCRIPTION
        "Cisco Firepower ether:FcoeInterfaceStats:errorsRx
        managed object property"
    ::= { cfprApEtherFcoeInterfaceStatsEntry 24 }

cfprApEtherFcoeInterfaceStatsErrorsRxDelta OBJECT-TYPE
    SYNTAX       Counter64
    MAX-ACCESS   read-only
    STATUS       current
    DESCRIPTION
        "Cisco Firepower ether:FcoeInterfaceStats:errorsRxDelta
        managed object property"
    ::= { cfprApEtherFcoeInterfaceStatsEntry 25 }

cfprApEtherFcoeInterfaceStatsErrorsRxDeltaAvg OBJECT-TYPE
    SYNTAX       Unsigned64
    MAX-ACCESS   read-only
    STATUS       current
    DESCRIPTION
        "Cisco Firepower ether:FcoeInterfaceStats:errorsRxDeltaAvg
        managed object property"
    ::= { cfprApEtherFcoeInterfaceStatsEntry 26 }

cfprApEtherFcoeInterfaceStatsErrorsRxDeltaMax OBJECT-TYPE
    SYNTAX       Unsigned64
    MAX-ACCESS   read-only
    STATUS       current
    DESCRIPTION
        "Cisco Firepower ether:FcoeInterfaceStats:errorsRxDeltaMax
        managed object property"
    ::= { cfprApEtherFcoeInterfaceStatsEntry 27 }

cfprApEtherFcoeInterfaceStatsErrorsRxDeltaMin OBJECT-TYPE
    SYNTAX       Unsigned64
    MAX-ACCESS   read-only
    STATUS       current
    DESCRIPTION
        "Cisco Firepower ether:FcoeInterfaceStats:errorsRxDeltaMin
        managed object property"
    ::= { cfprApEtherFcoeInterfaceStatsEntry 28 }

cfprApEtherFcoeInterfaceStatsErrorsTx OBJECT-TYPE
    SYNTAX       Unsigned64
    MAX-ACCESS   read-only
    STATUS       current
    DESCRIPTION
        "Cisco Firepower ether:FcoeInterfaceStats:errorsTx
        managed object property"
    ::= { cfprApEtherFcoeInterfaceStatsEntry 29 }

cfprApEtherFcoeInterfaceStatsErrorsTxDelta OBJECT-TYPE
    SYNTAX       Counter64
    MAX-ACCESS   read-only
    STATUS       current
    DESCRIPTION
        "Cisco Firepower ether:FcoeInterfaceStats:errorsTxDelta
        managed object property"
    ::= { cfprApEtherFcoeInterfaceStatsEntry 30 }

cfprApEtherFcoeInterfaceStatsErrorsTxDeltaAvg OBJECT-TYPE
    SYNTAX       Unsigned64
    MAX-ACCESS   read-only
    STATUS       current
    DESCRIPTION
        "Cisco Firepower ether:FcoeInterfaceStats:errorsTxDeltaAvg
        managed object property"
    ::= { cfprApEtherFcoeInterfaceStatsEntry 31 }

cfprApEtherFcoeInterfaceStatsErrorsTxDeltaMax OBJECT-TYPE
    SYNTAX       Unsigned64
    MAX-ACCESS   read-only
    STATUS       current
    DESCRIPTION
        "Cisco Firepower ether:FcoeInterfaceStats:errorsTxDeltaMax
        managed object property"
    ::= { cfprApEtherFcoeInterfaceStatsEntry 32 }

cfprApEtherFcoeInterfaceStatsErrorsTxDeltaMin OBJECT-TYPE
    SYNTAX       Unsigned64
    MAX-ACCESS   read-only
    STATUS       current
    DESCRIPTION
        "Cisco Firepower ether:FcoeInterfaceStats:errorsTxDeltaMin
        managed object property"
    ::= { cfprApEtherFcoeInterfaceStatsEntry 33 }

cfprApEtherFcoeInterfaceStatsIntervals OBJECT-TYPE
    SYNTAX       Gauge32
    MAX-ACCESS   read-only
    STATUS       current
    DESCRIPTION
        "Cisco Firepower ether:FcoeInterfaceStats:intervals
        managed object property"
    ::= { cfprApEtherFcoeInterfaceStatsEntry 34 }

cfprApEtherFcoeInterfaceStatsPacketsRx OBJECT-TYPE
    SYNTAX       Unsigned64
    MAX-ACCESS   read-only
    STATUS       current
    DESCRIPTION
        "Cisco Firepower ether:FcoeInterfaceStats:packetsRx
        managed object property"
    ::= { cfprApEtherFcoeInterfaceStatsEntry 35 }

cfprApEtherFcoeInterfaceStatsPacketsRxDelta OBJECT-TYPE
    SYNTAX       Counter64
    MAX-ACCESS   read-only
    STATUS       current
    DESCRIPTION
        "Cisco Firepower ether:FcoeInterfaceStats:packetsRxDelta
        managed object property"
    ::= { cfprApEtherFcoeInterfaceStatsEntry 36 }

cfprApEtherFcoeInterfaceStatsPacketsRxDeltaAvg OBJECT-TYPE
    SYNTAX       Unsigned64
    MAX-ACCESS   read-only
    STATUS       current
    DESCRIPTION
        "Cisco Firepower ether:FcoeInterfaceStats:packetsRxDeltaAvg
        managed object property"
    ::= { cfprApEtherFcoeInterfaceStatsEntry 37 }

cfprApEtherFcoeInterfaceStatsPacketsRxDeltaMax OBJECT-TYPE
    SYNTAX       Unsigned64
    MAX-ACCESS   read-only
    STATUS       current
    DESCRIPTION
        "Cisco Firepower ether:FcoeInterfaceStats:packetsRxDeltaMax
        managed object property"
    ::= { cfprApEtherFcoeInterfaceStatsEntry 38 }

cfprApEtherFcoeInterfaceStatsPacketsRxDeltaMin OBJECT-TYPE
    SYNTAX       Unsigned64
    MAX-ACCESS   read-only
    STATUS       current
    DESCRIPTION
        "Cisco Firepower ether:FcoeInterfaceStats:packetsRxDeltaMin
        managed object property"
    ::= { cfprApEtherFcoeInterfaceStatsEntry 39 }

cfprApEtherFcoeInterfaceStatsPacketsTx OBJECT-TYPE
    SYNTAX       Unsigned64
    MAX-ACCESS   read-only
    STATUS       current
    DESCRIPTION
        "Cisco Firepower ether:FcoeInterfaceStats:packetsTx
        managed object property"
    ::= { cfprApEtherFcoeInterfaceStatsEntry 40 }

cfprApEtherFcoeInterfaceStatsPacketsTxDelta OBJECT-TYPE
    SYNTAX       Counter64
    MAX-ACCESS   read-only
    STATUS       current
    DESCRIPTION
        "Cisco Firepower ether:FcoeInterfaceStats:packetsTxDelta
        managed object property"
    ::= { cfprApEtherFcoeInterfaceStatsEntry 41 }

cfprApEtherFcoeInterfaceStatsPacketsTxDeltaAvg OBJECT-TYPE
    SYNTAX       Unsigned64
    MAX-ACCESS   read-only
    STATUS       current
    DESCRIPTION
        "Cisco Firepower ether:FcoeInterfaceStats:packetsTxDeltaAvg
        managed object property"
    ::= { cfprApEtherFcoeInterfaceStatsEntry 42 }

cfprApEtherFcoeInterfaceStatsPacketsTxDeltaMax OBJECT-TYPE
    SYNTAX       Unsigned64
    MAX-ACCESS   read-only
    STATUS       current
    DESCRIPTION
        "Cisco Firepower ether:FcoeInterfaceStats:packetsTxDeltaMax
        managed object property"
    ::= { cfprApEtherFcoeInterfaceStatsEntry 43 }

cfprApEtherFcoeInterfaceStatsPacketsTxDeltaMin OBJECT-TYPE
    SYNTAX       Unsigned64
    MAX-ACCESS   read-only
    STATUS       current
    DESCRIPTION
        "Cisco Firepower ether:FcoeInterfaceStats:packetsTxDeltaMin
        managed object property"
    ::= { cfprApEtherFcoeInterfaceStatsEntry 44 }

cfprApEtherFcoeInterfaceStatsSuspect OBJECT-TYPE
    SYNTAX       TruthValue
    MAX-ACCESS   read-only
    STATUS       current
    DESCRIPTION
        "Cisco Firepower ether:FcoeInterfaceStats:suspect
        managed object property"
    ::= { cfprApEtherFcoeInterfaceStatsEntry 45 }

cfprApEtherFcoeInterfaceStatsThresholded OBJECT-TYPE
    SYNTAX       CfprApEtherFcoeInterfaceStatsThresholded
    MAX-ACCESS   read-only
    STATUS       current
    DESCRIPTION
        "Cisco Firepower ether:FcoeInterfaceStats:thresholded
        managed object property"
    ::= { cfprApEtherFcoeInterfaceStatsEntry 46 }

cfprApEtherFcoeInterfaceStatsTimeCollected OBJECT-TYPE
    SYNTAX       DateAndTime
    MAX-ACCESS   read-only
    STATUS       current
    DESCRIPTION
        "Cisco Firepower ether:FcoeInterfaceStats:timeCollected
        managed object property"
    ::= { cfprApEtherFcoeInterfaceStatsEntry 47 }

cfprApEtherFcoeInterfaceStatsUpdate OBJECT-TYPE
    SYNTAX       Gauge32
    MAX-ACCESS   read-only
    STATUS       current
    DESCRIPTION
        "Cisco Firepower ether:FcoeInterfaceStats:update
        managed object property"
    ::= { cfprApEtherFcoeInterfaceStatsEntry 48 }

cfprApEtherFcoeInterfaceStatsHistTable OBJECT-TYPE
    SYNTAX           SEQUENCE OF CfprApEtherFcoeInterfaceStatsHistEntry
    MAX-ACCESS       not-accessible
    STATUS           current
    DESCRIPTION
        "Cisco Firepower ether:FcoeInterfaceStatsHist managed
        object table"
    ::= { cfprApEtherObjects 5 }

cfprApEtherFcoeInterfaceStatsHistEntry OBJECT-TYPE
    SYNTAX           CfprApEtherFcoeInterfaceStatsHistEntry
    MAX-ACCESS       not-accessible
    STATUS           current
    DESCRIPTION
        "Entry for the cfprApEtherFcoeInterfaceStatsHistTable table."
    INDEX { cfprApEtherFcoeInterfaceStatsHistInstanceId }
    ::= { cfprApEtherFcoeInterfaceStatsHistTable 1 }

CfprApEtherFcoeInterfaceStatsHistEntry ::= SEQUENCE {
    cfprApEtherFcoeInterfaceStatsHistInstanceId                      CfprApManagedObjectId,
    cfprApEtherFcoeInterfaceStatsHistDn                              CfprApManagedObjectDn,
    cfprApEtherFcoeInterfaceStatsHistRn                              SnmpAdminString,
    cfprApEtherFcoeInterfaceStatsHistBytesRx                         Unsigned64,
    cfprApEtherFcoeInterfaceStatsHistBytesRxDelta                    Unsigned64,
    cfprApEtherFcoeInterfaceStatsHistBytesRxDeltaAvg                 Unsigned64,
    cfprApEtherFcoeInterfaceStatsHistBytesRxDeltaMax                 Unsigned64,
    cfprApEtherFcoeInterfaceStatsHistBytesRxDeltaMin                 Unsigned64,
    cfprApEtherFcoeInterfaceStatsHistBytesTx                         Unsigned64,
    cfprApEtherFcoeInterfaceStatsHistBytesTxDelta                    Unsigned64,
    cfprApEtherFcoeInterfaceStatsHistBytesTxDeltaAvg                 Unsigned64,
    cfprApEtherFcoeInterfaceStatsHistBytesTxDeltaMax                 Unsigned64,
    cfprApEtherFcoeInterfaceStatsHistBytesTxDeltaMin                 Unsigned64,
    cfprApEtherFcoeInterfaceStatsHistDroppedRx                       Unsigned64,
    cfprApEtherFcoeInterfaceStatsHistDroppedRxDelta                  Unsigned64,
    cfprApEtherFcoeInterfaceStatsHistDroppedRxDeltaAvg               Unsigned64,
    cfprApEtherFcoeInterfaceStatsHistDroppedRxDeltaMax               Unsigned64,
    cfprApEtherFcoeInterfaceStatsHistDroppedRxDeltaMin               Unsigned64,
    cfprApEtherFcoeInterfaceStatsHistDroppedTx                       Unsigned64,
    cfprApEtherFcoeInterfaceStatsHistDroppedTxDelta                  Unsigned64,
    cfprApEtherFcoeInterfaceStatsHistDroppedTxDeltaAvg               Unsigned64,
    cfprApEtherFcoeInterfaceStatsHistDroppedTxDeltaMax               Unsigned64,
    cfprApEtherFcoeInterfaceStatsHistDroppedTxDeltaMin               Unsigned64,
    cfprApEtherFcoeInterfaceStatsHistErrorsRx                        Unsigned64,
    cfprApEtherFcoeInterfaceStatsHistErrorsRxDelta                   Unsigned64,
    cfprApEtherFcoeInterfaceStatsHistErrorsRxDeltaAvg                Unsigned64,
    cfprApEtherFcoeInterfaceStatsHistErrorsRxDeltaMax                Unsigned64,
    cfprApEtherFcoeInterfaceStatsHistErrorsRxDeltaMin                Unsigned64,
    cfprApEtherFcoeInterfaceStatsHistErrorsTx                        Unsigned64,
    cfprApEtherFcoeInterfaceStatsHistErrorsTxDelta                   Unsigned64,
    cfprApEtherFcoeInterfaceStatsHistErrorsTxDeltaAvg                Unsigned64,
    cfprApEtherFcoeInterfaceStatsHistErrorsTxDeltaMax                Unsigned64,
    cfprApEtherFcoeInterfaceStatsHistErrorsTxDeltaMin                Unsigned64,
    cfprApEtherFcoeInterfaceStatsHistId                              Unsigned64,
    cfprApEtherFcoeInterfaceStatsHistMostRecent                      TruthValue,
    cfprApEtherFcoeInterfaceStatsHistPacketsRx                       Unsigned64,
    cfprApEtherFcoeInterfaceStatsHistPacketsRxDelta                  Unsigned64,
    cfprApEtherFcoeInterfaceStatsHistPacketsRxDeltaAvg               Unsigned64,
    cfprApEtherFcoeInterfaceStatsHistPacketsRxDeltaMax               Unsigned64,
    cfprApEtherFcoeInterfaceStatsHistPacketsRxDeltaMin               Unsigned64,
    cfprApEtherFcoeInterfaceStatsHistPacketsTx                       Unsigned64,
    cfprApEtherFcoeInterfaceStatsHistPacketsTxDelta                  Unsigned64,
    cfprApEtherFcoeInterfaceStatsHistPacketsTxDeltaAvg               Unsigned64,
    cfprApEtherFcoeInterfaceStatsHistPacketsTxDeltaMax               Unsigned64,
    cfprApEtherFcoeInterfaceStatsHistPacketsTxDeltaMin               Unsigned64,
    cfprApEtherFcoeInterfaceStatsHistSuspect                         TruthValue,
    cfprApEtherFcoeInterfaceStatsHistThresholded                     CfprApEtherFcoeInterfaceStatsHistThresholded,
    cfprApEtherFcoeInterfaceStatsHistTimeCollected                   DateAndTime
}

cfprApEtherFcoeInterfaceStatsHistInstanceId OBJECT-TYPE
    SYNTAX       CfprApManagedObjectId
    MAX-ACCESS   not-accessible
    STATUS       current
    DESCRIPTION
        "Instance identifier of the managed object."
    ::= { cfprApEtherFcoeInterfaceStatsHistEntry 1 }

cfprApEtherFcoeInterfaceStatsHistDn OBJECT-TYPE
    SYNTAX       CfprApManagedObjectDn
    MAX-ACCESS   read-only
    STATUS       current
    DESCRIPTION
        "Cisco Firepower ether:FcoeInterfaceStatsHist:dn
        managed object property"
    ::= { cfprApEtherFcoeInterfaceStatsHistEntry 2 }

cfprApEtherFcoeInterfaceStatsHistRn OBJECT-TYPE
    SYNTAX       SnmpAdminString
    MAX-ACCESS   read-only
    STATUS       current
    DESCRIPTION
        "Cisco Firepower ether:FcoeInterfaceStatsHist:rn
        managed object property"
    ::= { cfprApEtherFcoeInterfaceStatsHistEntry 3 }

cfprApEtherFcoeInterfaceStatsHistBytesRx OBJECT-TYPE
    SYNTAX       Unsigned64
    MAX-ACCESS   read-only
    STATUS       current
    DESCRIPTION
        "Cisco Firepower ether:FcoeInterfaceStatsHist:bytesRx
        managed object property"
    ::= { cfprApEtherFcoeInterfaceStatsHistEntry 4 }

cfprApEtherFcoeInterfaceStatsHistBytesRxDelta OBJECT-TYPE
    SYNTAX       Unsigned64
    MAX-ACCESS   read-only
    STATUS       current
    DESCRIPTION
        "Cisco Firepower ether:FcoeInterfaceStatsHist:bytesRxDelta
        managed object property"
    ::= { cfprApEtherFcoeInterfaceStatsHistEntry 5 }

cfprApEtherFcoeInterfaceStatsHistBytesRxDeltaAvg OBJECT-TYPE
    SYNTAX       Unsigned64
    MAX-ACCESS   read-only
    STATUS       current
    DESCRIPTION
        "Cisco Firepower ether:FcoeInterfaceStatsHist:bytesRxDeltaAvg
        managed object property"
    ::= { cfprApEtherFcoeInterfaceStatsHistEntry 6 }

cfprApEtherFcoeInterfaceStatsHistBytesRxDeltaMax OBJECT-TYPE
    SYNTAX       Unsigned64
    MAX-ACCESS   read-only
    STATUS       current
    DESCRIPTION
        "Cisco Firepower ether:FcoeInterfaceStatsHist:bytesRxDeltaMax
        managed object property"
    ::= { cfprApEtherFcoeInterfaceStatsHistEntry 7 }

cfprApEtherFcoeInterfaceStatsHistBytesRxDeltaMin OBJECT-TYPE
    SYNTAX       Unsigned64
    MAX-ACCESS   read-only
    STATUS       current
    DESCRIPTION
        "Cisco Firepower ether:FcoeInterfaceStatsHist:bytesRxDeltaMin
        managed object property"
    ::= { cfprApEtherFcoeInterfaceStatsHistEntry 8 }

cfprApEtherFcoeInterfaceStatsHistBytesTx OBJECT-TYPE
    SYNTAX       Unsigned64
    MAX-ACCESS   read-only
    STATUS       current
    DESCRIPTION
        "Cisco Firepower ether:FcoeInterfaceStatsHist:bytesTx
        managed object property"
    ::= { cfprApEtherFcoeInterfaceStatsHistEntry 9 }

cfprApEtherFcoeInterfaceStatsHistBytesTxDelta OBJECT-TYPE
    SYNTAX       Unsigned64
    MAX-ACCESS   read-only
    STATUS       current
    DESCRIPTION
        "Cisco Firepower ether:FcoeInterfaceStatsHist:bytesTxDelta
        managed object property"
    ::= { cfprApEtherFcoeInterfaceStatsHistEntry 10 }

cfprApEtherFcoeInterfaceStatsHistBytesTxDeltaAvg OBJECT-TYPE
    SYNTAX       Unsigned64
    MAX-ACCESS   read-only
    STATUS       current
    DESCRIPTION
        "Cisco Firepower ether:FcoeInterfaceStatsHist:bytesTxDeltaAvg
        managed object property"
    ::= { cfprApEtherFcoeInterfaceStatsHistEntry 11 }

cfprApEtherFcoeInterfaceStatsHistBytesTxDeltaMax OBJECT-TYPE
    SYNTAX       Unsigned64
    MAX-ACCESS   read-only
    STATUS       current
    DESCRIPTION
        "Cisco Firepower ether:FcoeInterfaceStatsHist:bytesTxDeltaMax
        managed object property"
    ::= { cfprApEtherFcoeInterfaceStatsHistEntry 12 }

cfprApEtherFcoeInterfaceStatsHistBytesTxDeltaMin OBJECT-TYPE
    SYNTAX       Unsigned64
    MAX-ACCESS   read-only
    STATUS       current
    DESCRIPTION
        "Cisco Firepower ether:FcoeInterfaceStatsHist:bytesTxDeltaMin
        managed object property"
    ::= { cfprApEtherFcoeInterfaceStatsHistEntry 13 }

cfprApEtherFcoeInterfaceStatsHistDroppedRx OBJECT-TYPE
    SYNTAX       Unsigned64
    MAX-ACCESS   read-only
    STATUS       current
    DESCRIPTION
        "Cisco Firepower ether:FcoeInterfaceStatsHist:droppedRx
        managed object property"
    ::= { cfprApEtherFcoeInterfaceStatsHistEntry 14 }

cfprApEtherFcoeInterfaceStatsHistDroppedRxDelta OBJECT-TYPE
    SYNTAX       Unsigned64
    MAX-ACCESS   read-only
    STATUS       current
    DESCRIPTION
        "Cisco Firepower ether:FcoeInterfaceStatsHist:droppedRxDelta
        managed object property"
    ::= { cfprApEtherFcoeInterfaceStatsHistEntry 15 }

cfprApEtherFcoeInterfaceStatsHistDroppedRxDeltaAvg OBJECT-TYPE
    SYNTAX       Unsigned64
    MAX-ACCESS   read-only
    STATUS       current
    DESCRIPTION
        "Cisco Firepower ether:FcoeInterfaceStatsHist:droppedRxDeltaAvg
        managed object property"
    ::= { cfprApEtherFcoeInterfaceStatsHistEntry 16 }

cfprApEtherFcoeInterfaceStatsHistDroppedRxDeltaMax OBJECT-TYPE
    SYNTAX       Unsigned64
    MAX-ACCESS   read-only
    STATUS       current
    DESCRIPTION
        "Cisco Firepower ether:FcoeInterfaceStatsHist:droppedRxDeltaMax
        managed object property"
    ::= { cfprApEtherFcoeInterfaceStatsHistEntry 17 }

cfprApEtherFcoeInterfaceStatsHistDroppedRxDeltaMin OBJECT-TYPE
    SYNTAX       Unsigned64
    MAX-ACCESS   read-only
    STATUS       current
    DESCRIPTION
        "Cisco Firepower ether:FcoeInterfaceStatsHist:droppedRxDeltaMin
        managed object property"
    ::= { cfprApEtherFcoeInterfaceStatsHistEntry 18 }

cfprApEtherFcoeInterfaceStatsHistDroppedTx OBJECT-TYPE
    SYNTAX       Unsigned64
    MAX-ACCESS   read-only
    STATUS       current
    DESCRIPTION
        "Cisco Firepower ether:FcoeInterfaceStatsHist:droppedTx
        managed object property"
    ::= { cfprApEtherFcoeInterfaceStatsHistEntry 19 }

cfprApEtherFcoeInterfaceStatsHistDroppedTxDelta OBJECT-TYPE
    SYNTAX       Unsigned64
    MAX-ACCESS   read-only
    STATUS       current
    DESCRIPTION
        "Cisco Firepower ether:FcoeInterfaceStatsHist:droppedTxDelta
        managed object property"
    ::= { cfprApEtherFcoeInterfaceStatsHistEntry 20 }

cfprApEtherFcoeInterfaceStatsHistDroppedTxDeltaAvg OBJECT-TYPE
    SYNTAX       Unsigned64
    MAX-ACCESS   read-only
    STATUS       current
    DESCRIPTION
        "Cisco Firepower ether:FcoeInterfaceStatsHist:droppedTxDeltaAvg
        managed object property"
    ::= { cfprApEtherFcoeInterfaceStatsHistEntry 21 }

cfprApEtherFcoeInterfaceStatsHistDroppedTxDeltaMax OBJECT-TYPE
    SYNTAX       Unsigned64
    MAX-ACCESS   read-only
    STATUS       current
    DESCRIPTION
        "Cisco Firepower ether:FcoeInterfaceStatsHist:droppedTxDeltaMax
        managed object property"
    ::= { cfprApEtherFcoeInterfaceStatsHistEntry 22 }

cfprApEtherFcoeInterfaceStatsHistDroppedTxDeltaMin OBJECT-TYPE
    SYNTAX       Unsigned64
    MAX-ACCESS   read-only
    STATUS       current
    DESCRIPTION
        "Cisco Firepower ether:FcoeInterfaceStatsHist:droppedTxDeltaMin
        managed object property"
    ::= { cfprApEtherFcoeInterfaceStatsHistEntry 23 }

cfprApEtherFcoeInterfaceStatsHistErrorsRx OBJECT-TYPE
    SYNTAX       Unsigned64
    MAX-ACCESS   read-only
    STATUS       current
    DESCRIPTION
        "Cisco Firepower ether:FcoeInterfaceStatsHist:errorsRx
        managed object property"
    ::= { cfprApEtherFcoeInterfaceStatsHistEntry 24 }

cfprApEtherFcoeInterfaceStatsHistErrorsRxDelta OBJECT-TYPE
    SYNTAX       Unsigned64
    MAX-ACCESS   read-only
    STATUS       current
    DESCRIPTION
        "Cisco Firepower ether:FcoeInterfaceStatsHist:errorsRxDelta
        managed object property"
    ::= { cfprApEtherFcoeInterfaceStatsHistEntry 25 }

cfprApEtherFcoeInterfaceStatsHistErrorsRxDeltaAvg OBJECT-TYPE
    SYNTAX       Unsigned64
    MAX-ACCESS   read-only
    STATUS       current
    DESCRIPTION
        "Cisco Firepower ether:FcoeInterfaceStatsHist:errorsRxDeltaAvg
        managed object property"
    ::= { cfprApEtherFcoeInterfaceStatsHistEntry 26 }

cfprApEtherFcoeInterfaceStatsHistErrorsRxDeltaMax OBJECT-TYPE
    SYNTAX       Unsigned64
    MAX-ACCESS   read-only
    STATUS       current
    DESCRIPTION
        "Cisco Firepower ether:FcoeInterfaceStatsHist:errorsRxDeltaMax
        managed object property"
    ::= { cfprApEtherFcoeInterfaceStatsHistEntry 27 }

cfprApEtherFcoeInterfaceStatsHistErrorsRxDeltaMin OBJECT-TYPE
    SYNTAX       Unsigned64
    MAX-ACCESS   read-only
    STATUS       current
    DESCRIPTION
        "Cisco Firepower ether:FcoeInterfaceStatsHist:errorsRxDeltaMin
        managed object property"
    ::= { cfprApEtherFcoeInterfaceStatsHistEntry 28 }

cfprApEtherFcoeInterfaceStatsHistErrorsTx OBJECT-TYPE
    SYNTAX       Unsigned64
    MAX-ACCESS   read-only
    STATUS       current
    DESCRIPTION
        "Cisco Firepower ether:FcoeInterfaceStatsHist:errorsTx
        managed object property"
    ::= { cfprApEtherFcoeInterfaceStatsHistEntry 29 }

cfprApEtherFcoeInterfaceStatsHistErrorsTxDelta OBJECT-TYPE
    SYNTAX       Unsigned64
    MAX-ACCESS   read-only
    STATUS       current
    DESCRIPTION
        "Cisco Firepower ether:FcoeInterfaceStatsHist:errorsTxDelta
        managed object property"
    ::= { cfprApEtherFcoeInterfaceStatsHistEntry 30 }

cfprApEtherFcoeInterfaceStatsHistErrorsTxDeltaAvg OBJECT-TYPE
    SYNTAX       Unsigned64
    MAX-ACCESS   read-only
    STATUS       current
    DESCRIPTION
        "Cisco Firepower ether:FcoeInterfaceStatsHist:errorsTxDeltaAvg
        managed object property"
    ::= { cfprApEtherFcoeInterfaceStatsHistEntry 31 }

cfprApEtherFcoeInterfaceStatsHistErrorsTxDeltaMax OBJECT-TYPE
    SYNTAX       Unsigned64
    MAX-ACCESS   read-only
    STATUS       current
    DESCRIPTION
        "Cisco Firepower ether:FcoeInterfaceStatsHist:errorsTxDeltaMax
        managed object property"
    ::= { cfprApEtherFcoeInterfaceStatsHistEntry 32 }

cfprApEtherFcoeInterfaceStatsHistErrorsTxDeltaMin OBJECT-TYPE
    SYNTAX       Unsigned64
    MAX-ACCESS   read-only
    STATUS       current
    DESCRIPTION
        "Cisco Firepower ether:FcoeInterfaceStatsHist:errorsTxDeltaMin
        managed object property"
    ::= { cfprApEtherFcoeInterfaceStatsHistEntry 33 }

cfprApEtherFcoeInterfaceStatsHistId OBJECT-TYPE
    SYNTAX       Unsigned64
    MAX-ACCESS   read-only
    STATUS       current
    DESCRIPTION
        "Cisco Firepower ether:FcoeInterfaceStatsHist:id
        managed object property"
    ::= { cfprApEtherFcoeInterfaceStatsHistEntry 34 }

cfprApEtherFcoeInterfaceStatsHistMostRecent OBJECT-TYPE
    SYNTAX       TruthValue
    MAX-ACCESS   read-only
    STATUS       current
    DESCRIPTION
        "Cisco Firepower ether:FcoeInterfaceStatsHist:mostRecent
        managed object property"
    ::= { cfprApEtherFcoeInterfaceStatsHistEntry 35 }

cfprApEtherFcoeInterfaceStatsHistPacketsRx OBJECT-TYPE
    SYNTAX       Unsigned64
    MAX-ACCESS   read-only
    STATUS       current
    DESCRIPTION
        "Cisco Firepower ether:FcoeInterfaceStatsHist:packetsRx
        managed object property"
    ::= { cfprApEtherFcoeInterfaceStatsHistEntry 36 }

cfprApEtherFcoeInterfaceStatsHistPacketsRxDelta OBJECT-TYPE
    SYNTAX       Unsigned64
    MAX-ACCESS   read-only
    STATUS       current
    DESCRIPTION
        "Cisco Firepower ether:FcoeInterfaceStatsHist:packetsRxDelta
        managed object property"
    ::= { cfprApEtherFcoeInterfaceStatsHistEntry 37 }

cfprApEtherFcoeInterfaceStatsHistPacketsRxDeltaAvg OBJECT-TYPE
    SYNTAX       Unsigned64
    MAX-ACCESS   read-only
    STATUS       current
    DESCRIPTION
        "Cisco Firepower ether:FcoeInterfaceStatsHist:packetsRxDeltaAvg
        managed object property"
    ::= { cfprApEtherFcoeInterfaceStatsHistEntry 38 }

cfprApEtherFcoeInterfaceStatsHistPacketsRxDeltaMax OBJECT-TYPE
    SYNTAX       Unsigned64
    MAX-ACCESS   read-only
    STATUS       current
    DESCRIPTION
        "Cisco Firepower ether:FcoeInterfaceStatsHist:packetsRxDeltaMax
        managed object property"
    ::= { cfprApEtherFcoeInterfaceStatsHistEntry 39 }

cfprApEtherFcoeInterfaceStatsHistPacketsRxDeltaMin OBJECT-TYPE
    SYNTAX       Unsigned64
    MAX-ACCESS   read-only
    STATUS       current
    DESCRIPTION
        "Cisco Firepower ether:FcoeInterfaceStatsHist:packetsRxDeltaMin
        managed object property"
    ::= { cfprApEtherFcoeInterfaceStatsHistEntry 40 }

cfprApEtherFcoeInterfaceStatsHistPacketsTx OBJECT-TYPE
    SYNTAX       Unsigned64
    MAX-ACCESS   read-only
    STATUS       current
    DESCRIPTION
        "Cisco Firepower ether:FcoeInterfaceStatsHist:packetsTx
        managed object property"
    ::= { cfprApEtherFcoeInterfaceStatsHistEntry 41 }

cfprApEtherFcoeInterfaceStatsHistPacketsTxDelta OBJECT-TYPE
    SYNTAX       Unsigned64
    MAX-ACCESS   read-only
    STATUS       current
    DESCRIPTION
        "Cisco Firepower ether:FcoeInterfaceStatsHist:packetsTxDelta
        managed object property"
    ::= { cfprApEtherFcoeInterfaceStatsHistEntry 42 }

cfprApEtherFcoeInterfaceStatsHistPacketsTxDeltaAvg OBJECT-TYPE
    SYNTAX       Unsigned64
    MAX-ACCESS   read-only
    STATUS       current
    DESCRIPTION
        "Cisco Firepower ether:FcoeInterfaceStatsHist:packetsTxDeltaAvg
        managed object property"
    ::= { cfprApEtherFcoeInterfaceStatsHistEntry 43 }

cfprApEtherFcoeInterfaceStatsHistPacketsTxDeltaMax OBJECT-TYPE
    SYNTAX       Unsigned64
    MAX-ACCESS   read-only
    STATUS       current
    DESCRIPTION
        "Cisco Firepower ether:FcoeInterfaceStatsHist:packetsTxDeltaMax
        managed object property"
    ::= { cfprApEtherFcoeInterfaceStatsHistEntry 44 }

cfprApEtherFcoeInterfaceStatsHistPacketsTxDeltaMin OBJECT-TYPE
    SYNTAX       Unsigned64
    MAX-ACCESS   read-only
    STATUS       current
    DESCRIPTION
        "Cisco Firepower ether:FcoeInterfaceStatsHist:packetsTxDeltaMin
        managed object property"
    ::= { cfprApEtherFcoeInterfaceStatsHistEntry 45 }

cfprApEtherFcoeInterfaceStatsHistSuspect OBJECT-TYPE
    SYNTAX       TruthValue
    MAX-ACCESS   read-only
    STATUS       current
    DESCRIPTION
        "Cisco Firepower ether:FcoeInterfaceStatsHist:suspect
        managed object property"
    ::= { cfprApEtherFcoeInterfaceStatsHistEntry 46 }

cfprApEtherFcoeInterfaceStatsHistThresholded OBJECT-TYPE
    SYNTAX       CfprApEtherFcoeInterfaceStatsHistThresholded
    MAX-ACCESS   read-only
    STATUS       current
    DESCRIPTION
        "Cisco Firepower ether:FcoeInterfaceStatsHist:thresholded
        managed object property"
    ::= { cfprApEtherFcoeInterfaceStatsHistEntry 47 }

cfprApEtherFcoeInterfaceStatsHistTimeCollected OBJECT-TYPE
    SYNTAX       DateAndTime
    MAX-ACCESS   read-only
    STATUS       current
    DESCRIPTION
        "Cisco Firepower ether:FcoeInterfaceStatsHist:timeCollected
        managed object property"
    ::= { cfprApEtherFcoeInterfaceStatsHistEntry 48 }

cfprApEtherFtwPortPairTable OBJECT-TYPE
    SYNTAX           SEQUENCE OF CfprApEtherFtwPortPairEntry
    MAX-ACCESS       not-accessible
    STATUS           current
    DESCRIPTION
        "Cisco Firepower ether:FtwPortPair managed object table"
    ::= { cfprApEtherObjects 6 }

cfprApEtherFtwPortPairEntry OBJECT-TYPE
    SYNTAX           CfprApEtherFtwPortPairEntry
    MAX-ACCESS       not-accessible
    STATUS           current
    DESCRIPTION
        "Entry for the cfprApEtherFtwPortPairTable table."
    INDEX { cfprApEtherFtwPortPairInstanceId }
    ::= { cfprApEtherFtwPortPairTable 1 }

CfprApEtherFtwPortPairEntry ::= SEQUENCE {
    cfprApEtherFtwPortPairInstanceId                                 CfprApManagedObjectId,
    cfprApEtherFtwPortPairDn                                         CfprApManagedObjectDn,
    cfprApEtherFtwPortPairRn                                         SnmpAdminString,
    cfprApEtherFtwPortPairAggrPortId                                 Gauge32,
    cfprApEtherFtwPortPairChassisId                                  Gauge32,
    cfprApEtherFtwPortPairEpDn                                       SnmpAdminString,
    cfprApEtherFtwPortPairFsmDescr                                   SnmpAdminString,
    cfprApEtherFtwPortPairFsmPrev                                    SnmpAdminString,
    cfprApEtherFtwPortPairFsmProgr                                   Gauge32,
    cfprApEtherFtwPortPairFsmRmtInvErrCode                           Gauge32,
    cfprApEtherFtwPortPairFsmRmtInvErrDescr                          SnmpAdminString,
    cfprApEtherFtwPortPairFsmRmtInvRslt                              CfprApConditionRemoteInvRslt,
    cfprApEtherFtwPortPairFsmStageDescr                              SnmpAdminString,
    cfprApEtherFtwPortPairFsmStamp                                   DateAndTime,
    cfprApEtherFtwPortPairFsmStatus                                  SnmpAdminString,
    cfprApEtherFtwPortPairFsmTry                                     Gauge32,
    cfprApEtherFtwPortPairIfRole                                     CfprApNetworkPortRole,
    cfprApEtherFtwPortPairIfType                                     CfprApNetworkPhysEpIfType,
    cfprApEtherFtwPortPairLocale                                     CfprApNetworkLocale,
    cfprApEtherFtwPortPairMode                                       CfprApEtherFtwPortPairMode,
    cfprApEtherFtwPortPairName                                       SnmpAdminString,
    cfprApEtherFtwPortPairOperMode                                   CfprApEtherFtwOperMode,
    cfprApEtherFtwPortPairPeerAggrPortId                             Gauge32,
    cfprApEtherFtwPortPairPeerChassisId                              Gauge32,
    cfprApEtherFtwPortPairPeerDn                                     SnmpAdminString,
    cfprApEtherFtwPortPairPeerPortId                                 Gauge32,
    cfprApEtherFtwPortPairPeerPortName                               SnmpAdminString,
    cfprApEtherFtwPortPairPeerSlotId                                 Gauge32,
    cfprApEtherFtwPortPairPortId                                     Gauge32,
    cfprApEtherFtwPortPairPortName                                   SnmpAdminString,
    cfprApEtherFtwPortPairSlotId                                     Gauge32,
    cfprApEtherFtwPortPairSwitchId                                   CfprApNetworkSwitchId,
    cfprApEtherFtwPortPairTransport                                  CfprApNetworkTransport,
    cfprApEtherFtwPortPairType                                       CfprApNetworkConnectionType,
    cfprApEtherFtwPortPairWdtStart                                   Gauge32,
    cfprApEtherFtwPortPairWdtState                                   CfprApEtherFtwPortPairWdtState
}

cfprApEtherFtwPortPairInstanceId OBJECT-TYPE
    SYNTAX       CfprApManagedObjectId
    MAX-ACCESS   not-accessible
    STATUS       current
    DESCRIPTION
        "Instance identifier of the managed object."
    ::= { cfprApEtherFtwPortPairEntry 1 }

cfprApEtherFtwPortPairDn OBJECT-TYPE
    SYNTAX       CfprApManagedObjectDn
    MAX-ACCESS   read-only
    STATUS       current
    DESCRIPTION
        "Cisco Firepower ether:FtwPortPair:dn managed object property"
    ::= { cfprApEtherFtwPortPairEntry 2 }

cfprApEtherFtwPortPairRn OBJECT-TYPE
    SYNTAX       SnmpAdminString
    MAX-ACCESS   read-only
    STATUS       current
    DESCRIPTION
        "Cisco Firepower ether:FtwPortPair:rn managed object property"
    ::= { cfprApEtherFtwPortPairEntry 3 }

cfprApEtherFtwPortPairAggrPortId OBJECT-TYPE
    SYNTAX       Gauge32
    MAX-ACCESS   read-only
    STATUS       current
    DESCRIPTION
        "Cisco Firepower ether:FtwPortPair:aggrPortId managed
        object property"
    ::= { cfprApEtherFtwPortPairEntry 4 }

cfprApEtherFtwPortPairChassisId OBJECT-TYPE
    SYNTAX       Gauge32
    MAX-ACCESS   read-only
    STATUS       current
    DESCRIPTION
        "Cisco Firepower ether:FtwPortPair:chassisId managed
        object property"
    ::= { cfprApEtherFtwPortPairEntry 5 }

cfprApEtherFtwPortPairEpDn OBJECT-TYPE
    SYNTAX       SnmpAdminString
    MAX-ACCESS   read-only
    STATUS       current
    DESCRIPTION
        "Cisco Firepower ether:FtwPortPair:epDn managed object property"
    ::= { cfprApEtherFtwPortPairEntry 6 }

cfprApEtherFtwPortPairFsmDescr OBJECT-TYPE
    SYNTAX       SnmpAdminString
    MAX-ACCESS   read-only
    STATUS       current
    DESCRIPTION
        "Cisco Firepower ether:FtwPortPair:fsmDescr managed
        object property"
    ::= { cfprApEtherFtwPortPairEntry 7 }

cfprApEtherFtwPortPairFsmPrev OBJECT-TYPE
    SYNTAX       SnmpAdminString
    MAX-ACCESS   read-only
    STATUS       current
    DESCRIPTION
        "Cisco Firepower ether:FtwPortPair:fsmPrev managed
        object property"
    ::= { cfprApEtherFtwPortPairEntry 8 }

cfprApEtherFtwPortPairFsmProgr OBJECT-TYPE
    SYNTAX       Gauge32
    MAX-ACCESS   read-only
    STATUS       current
    DESCRIPTION
        "Cisco Firepower ether:FtwPortPair:fsmProgr managed
        object property"
    ::= { cfprApEtherFtwPortPairEntry 9 }

cfprApEtherFtwPortPairFsmRmtInvErrCode OBJECT-TYPE
    SYNTAX       Gauge32
    MAX-ACCESS   read-only
    STATUS       current
    DESCRIPTION
        "Cisco Firepower ether:FtwPortPair:fsmRmtInvErrCode
        managed object property"
    ::= { cfprApEtherFtwPortPairEntry 10 }

cfprApEtherFtwPortPairFsmRmtInvErrDescr OBJECT-TYPE
    SYNTAX       SnmpAdminString
    MAX-ACCESS   read-only
    STATUS       current
    DESCRIPTION
        "Cisco Firepower ether:FtwPortPair:fsmRmtInvErrDescr
        managed object property"
    ::= { cfprApEtherFtwPortPairEntry 11 }

cfprApEtherFtwPortPairFsmRmtInvRslt OBJECT-TYPE
    SYNTAX       CfprApConditionRemoteInvRslt
    MAX-ACCESS   read-only
    STATUS       current
    DESCRIPTION
        "Cisco Firepower ether:FtwPortPair:fsmRmtInvRslt
        managed object property"
    ::= { cfprApEtherFtwPortPairEntry 12 }

cfprApEtherFtwPortPairFsmStageDescr OBJECT-TYPE
    SYNTAX       SnmpAdminString
    MAX-ACCESS   read-only
    STATUS       current
    DESCRIPTION
        "Cisco Firepower ether:FtwPortPair:fsmStageDescr
        managed object property"
    ::= { cfprApEtherFtwPortPairEntry 13 }

cfprApEtherFtwPortPairFsmStamp OBJECT-TYPE
    SYNTAX       DateAndTime
    MAX-ACCESS   read-only
    STATUS       current
    DESCRIPTION
        "Cisco Firepower ether:FtwPortPair:fsmStamp managed
        object property"
    ::= { cfprApEtherFtwPortPairEntry 14 }

cfprApEtherFtwPortPairFsmStatus OBJECT-TYPE
    SYNTAX       SnmpAdminString
    MAX-ACCESS   read-only
    STATUS       current
    DESCRIPTION
        "Cisco Firepower ether:FtwPortPair:fsmStatus managed
        object property"
    ::= { cfprApEtherFtwPortPairEntry 15 }

cfprApEtherFtwPortPairFsmTry OBJECT-TYPE
    SYNTAX       Gauge32
    MAX-ACCESS   read-only
    STATUS       current
    DESCRIPTION
        "Cisco Firepower ether:FtwPortPair:fsmTry managed object property"
    ::= { cfprApEtherFtwPortPairEntry 16 }

cfprApEtherFtwPortPairIfRole OBJECT-TYPE
    SYNTAX       CfprApNetworkPortRole
    MAX-ACCESS   read-only
    STATUS       current
    DESCRIPTION
        "Cisco Firepower ether:FtwPortPair:ifRole managed object property"
    ::= { cfprApEtherFtwPortPairEntry 17 }

cfprApEtherFtwPortPairIfType OBJECT-TYPE
    SYNTAX       CfprApNetworkPhysEpIfType
    MAX-ACCESS   read-only
    STATUS       current
    DESCRIPTION
        "Cisco Firepower ether:FtwPortPair:ifType managed object property"
    ::= { cfprApEtherFtwPortPairEntry 18 }

cfprApEtherFtwPortPairLocale OBJECT-TYPE
    SYNTAX       CfprApNetworkLocale
    MAX-ACCESS   read-only
    STATUS       current
    DESCRIPTION
        "Cisco Firepower ether:FtwPortPair:locale managed object property"
    ::= { cfprApEtherFtwPortPairEntry 19 }

cfprApEtherFtwPortPairMode OBJECT-TYPE
    SYNTAX       CfprApEtherFtwPortPairMode
    MAX-ACCESS   read-only
    STATUS       current
    DESCRIPTION
        "Cisco Firepower ether:FtwPortPair:mode managed object property"
    ::= { cfprApEtherFtwPortPairEntry 20 }

cfprApEtherFtwPortPairName OBJECT-TYPE
    SYNTAX       SnmpAdminString
    MAX-ACCESS   read-only
    STATUS       current
    DESCRIPTION
        "Cisco Firepower ether:FtwPortPair:name managed object property"
    ::= { cfprApEtherFtwPortPairEntry 21 }

cfprApEtherFtwPortPairOperMode OBJECT-TYPE
    SYNTAX       CfprApEtherFtwOperMode
    MAX-ACCESS   read-only
    STATUS       current
    DESCRIPTION
        "Cisco Firepower ether:FtwPortPair:operMode managed
        object property"
    ::= { cfprApEtherFtwPortPairEntry 22 }

cfprApEtherFtwPortPairPeerAggrPortId OBJECT-TYPE
    SYNTAX       Gauge32
    MAX-ACCESS   read-only
    STATUS       current
    DESCRIPTION
        "Cisco Firepower ether:FtwPortPair:peerAggrPortId
        managed object property"
    ::= { cfprApEtherFtwPortPairEntry 23 }

cfprApEtherFtwPortPairPeerChassisId OBJECT-TYPE
    SYNTAX       Gauge32
    MAX-ACCESS   read-only
    STATUS       current
    DESCRIPTION
        "Cisco Firepower ether:FtwPortPair:peerChassisId
        managed object property"
    ::= { cfprApEtherFtwPortPairEntry 24 }

cfprApEtherFtwPortPairPeerDn OBJECT-TYPE
    SYNTAX       SnmpAdminString
    MAX-ACCESS   read-only
    STATUS       current
    DESCRIPTION
        "Cisco Firepower ether:FtwPortPair:peerDn managed object property"
    ::= { cfprApEtherFtwPortPairEntry 25 }

cfprApEtherFtwPortPairPeerPortId OBJECT-TYPE
    SYNTAX       Gauge32
    MAX-ACCESS   read-only
    STATUS       current
    DESCRIPTION
        "Cisco Firepower ether:FtwPortPair:peerPortId managed
        object property"
    ::= { cfprApEtherFtwPortPairEntry 26 }

cfprApEtherFtwPortPairPeerPortName OBJECT-TYPE
    SYNTAX       SnmpAdminString
    MAX-ACCESS   read-only
    STATUS       current
    DESCRIPTION
        "Cisco Firepower ether:FtwPortPair:peerPortName
        managed object property"
    ::= { cfprApEtherFtwPortPairEntry 27 }

cfprApEtherFtwPortPairPeerSlotId OBJECT-TYPE
    SYNTAX       Gauge32
    MAX-ACCESS   read-only
    STATUS       current
    DESCRIPTION
        "Cisco Firepower ether:FtwPortPair:peerSlotId managed
        object property"
    ::= { cfprApEtherFtwPortPairEntry 28 }

cfprApEtherFtwPortPairPortId OBJECT-TYPE
    SYNTAX       Gauge32
    MAX-ACCESS   read-only
    STATUS       current
    DESCRIPTION
        "Cisco Firepower ether:FtwPortPair:portId managed object property"
    ::= { cfprApEtherFtwPortPairEntry 29 }

cfprApEtherFtwPortPairPortName OBJECT-TYPE
    SYNTAX       SnmpAdminString
    MAX-ACCESS   read-only
    STATUS       current
    DESCRIPTION
        "Cisco Firepower ether:FtwPortPair:portName managed
        object property"
    ::= { cfprApEtherFtwPortPairEntry 30 }

cfprApEtherFtwPortPairSlotId OBJECT-TYPE
    SYNTAX       Gauge32
    MAX-ACCESS   read-only
    STATUS       current
    DESCRIPTION
        "Cisco Firepower ether:FtwPortPair:slotId managed object property"
    ::= { cfprApEtherFtwPortPairEntry 31 }

cfprApEtherFtwPortPairSwitchId OBJECT-TYPE
    SYNTAX       CfprApNetworkSwitchId
    MAX-ACCESS   read-only
    STATUS       current
    DESCRIPTION
        "Cisco Firepower ether:FtwPortPair:switchId managed
        object property"
    ::= { cfprApEtherFtwPortPairEntry 32 }

cfprApEtherFtwPortPairTransport OBJECT-TYPE
    SYNTAX       CfprApNetworkTransport
    MAX-ACCESS   read-only
    STATUS       current
    DESCRIPTION
        "Cisco Firepower ether:FtwPortPair:transport managed
        object property"
    ::= { cfprApEtherFtwPortPairEntry 33 }

cfprApEtherFtwPortPairType OBJECT-TYPE
    SYNTAX       CfprApNetworkConnectionType
    MAX-ACCESS   read-only
    STATUS       current
    DESCRIPTION
        "Cisco Firepower ether:FtwPortPair:type managed object property"
    ::= { cfprApEtherFtwPortPairEntry 34 }

cfprApEtherFtwPortPairWdtStart OBJECT-TYPE
    SYNTAX       Gauge32
    MAX-ACCESS   read-only
    STATUS       current
    DESCRIPTION
        "Cisco Firepower ether:FtwPortPair:wdtStart managed
        object property"
    ::= { cfprApEtherFtwPortPairEntry 35 }

cfprApEtherFtwPortPairWdtState OBJECT-TYPE
    SYNTAX       CfprApEtherFtwPortPairWdtState
    MAX-ACCESS   read-only
    STATUS       current
    DESCRIPTION
        "Cisco Firepower ether:FtwPortPair:wdtState managed
        object property"
    ::= { cfprApEtherFtwPortPairEntry 36 }

cfprApEtherFtwPortPairFsmTable OBJECT-TYPE
    SYNTAX           SEQUENCE OF CfprApEtherFtwPortPairFsmEntry
    MAX-ACCESS       not-accessible
    STATUS           current
    DESCRIPTION
        "Cisco Firepower ether:FtwPortPairFsm managed object table"
    ::= { cfprApEtherObjects 7 }

cfprApEtherFtwPortPairFsmEntry OBJECT-TYPE
    SYNTAX           CfprApEtherFtwPortPairFsmEntry
    MAX-ACCESS       not-accessible
    STATUS           current
    DESCRIPTION
        "Entry for the cfprApEtherFtwPortPairFsmTable table."
    INDEX { cfprApEtherFtwPortPairFsmInstanceId }
    ::= { cfprApEtherFtwPortPairFsmTable 1 }

CfprApEtherFtwPortPairFsmEntry ::= SEQUENCE {
    cfprApEtherFtwPortPairFsmInstanceId                              CfprApManagedObjectId,
    cfprApEtherFtwPortPairFsmDn                                      CfprApManagedObjectDn,
    cfprApEtherFtwPortPairFsmRn                                      SnmpAdminString,
    cfprApEtherFtwPortPairFsmCompletionTime                          DateAndTime,
    cfprApEtherFtwPortPairFsmCurrentFsm                              CfprApEtherFtwPortPairFsmCurrentFsm,
    cfprApEtherFtwPortPairFsmDescrData                               SnmpAdminString,
    cfprApEtherFtwPortPairFsmFsmStatus                               CfprApFsmFsmStageStatus,
    cfprApEtherFtwPortPairFsmProgress                                Gauge32,
    cfprApEtherFtwPortPairFsmRmtErrCode                              Gauge32,
    cfprApEtherFtwPortPairFsmRmtErrDescr                             SnmpAdminString,
    cfprApEtherFtwPortPairFsmRmtRslt                                 CfprApConditionRemoteInvRslt
}

cfprApEtherFtwPortPairFsmInstanceId OBJECT-TYPE
    SYNTAX       CfprApManagedObjectId
    MAX-ACCESS   not-accessible
    STATUS       current
    DESCRIPTION
        "Instance identifier of the managed object."
    ::= { cfprApEtherFtwPortPairFsmEntry 1 }

cfprApEtherFtwPortPairFsmDn OBJECT-TYPE
    SYNTAX       CfprApManagedObjectDn
    MAX-ACCESS   read-only
    STATUS       current
    DESCRIPTION
        "Cisco Firepower ether:FtwPortPairFsm:dn managed object property"
    ::= { cfprApEtherFtwPortPairFsmEntry 2 }

cfprApEtherFtwPortPairFsmRn OBJECT-TYPE
    SYNTAX       SnmpAdminString
    MAX-ACCESS   read-only
    STATUS       current
    DESCRIPTION
        "Cisco Firepower ether:FtwPortPairFsm:rn managed object property"
    ::= { cfprApEtherFtwPortPairFsmEntry 3 }

cfprApEtherFtwPortPairFsmCompletionTime OBJECT-TYPE
    SYNTAX       DateAndTime
    MAX-ACCESS   read-only
    STATUS       current
    DESCRIPTION
        "Cisco Firepower ether:FtwPortPairFsm:completionTime
        managed object property"
    ::= { cfprApEtherFtwPortPairFsmEntry 4 }

cfprApEtherFtwPortPairFsmCurrentFsm OBJECT-TYPE
    SYNTAX       CfprApEtherFtwPortPairFsmCurrentFsm
    MAX-ACCESS   read-only
    STATUS       current
    DESCRIPTION
        "Cisco Firepower ether:FtwPortPairFsm:currentFsm
        managed object property"
    ::= { cfprApEtherFtwPortPairFsmEntry 5 }

cfprApEtherFtwPortPairFsmDescrData OBJECT-TYPE
    SYNTAX       SnmpAdminString
    MAX-ACCESS   read-only
    STATUS       current
    DESCRIPTION
        "Cisco Firepower ether:FtwPortPairFsm:descr managed
        object property"
    ::= { cfprApEtherFtwPortPairFsmEntry 6 }

cfprApEtherFtwPortPairFsmFsmStatus OBJECT-TYPE
    SYNTAX       CfprApFsmFsmStageStatus
    MAX-ACCESS   read-only
    STATUS       current
    DESCRIPTION
        "Cisco Firepower ether:FtwPortPairFsm:fsmStatus
        managed object property"
    ::= { cfprApEtherFtwPortPairFsmEntry 7 }

cfprApEtherFtwPortPairFsmProgress OBJECT-TYPE
    SYNTAX       Gauge32
    MAX-ACCESS   read-only
    STATUS       current
    DESCRIPTION
        "Cisco Firepower ether:FtwPortPairFsm:progress
        managed object property"
    ::= { cfprApEtherFtwPortPairFsmEntry 8 }

cfprApEtherFtwPortPairFsmRmtErrCode OBJECT-TYPE
    SYNTAX       Gauge32
    MAX-ACCESS   read-only
    STATUS       current
    DESCRIPTION
        "Cisco Firepower ether:FtwPortPairFsm:rmtErrCode
        managed object property"
    ::= { cfprApEtherFtwPortPairFsmEntry 9 }

cfprApEtherFtwPortPairFsmRmtErrDescr OBJECT-TYPE
    SYNTAX       SnmpAdminString
    MAX-ACCESS   read-only
    STATUS       current
    DESCRIPTION
        "Cisco Firepower ether:FtwPortPairFsm:rmtErrDescr
        managed object property"
    ::= { cfprApEtherFtwPortPairFsmEntry 10 }

cfprApEtherFtwPortPairFsmRmtRslt OBJECT-TYPE
    SYNTAX       CfprApConditionRemoteInvRslt
    MAX-ACCESS   read-only
    STATUS       current
    DESCRIPTION
        "Cisco Firepower ether:FtwPortPairFsm:rmtRslt managed
        object property"
    ::= { cfprApEtherFtwPortPairFsmEntry 11 }

cfprApEtherFtwPortPairFsmStageTable OBJECT-TYPE
    SYNTAX           SEQUENCE OF CfprApEtherFtwPortPairFsmStageEntry
    MAX-ACCESS       not-accessible
    STATUS           current
    DESCRIPTION
        "Cisco Firepower ether:FtwPortPairFsmStage managed object table"
    ::= { cfprApEtherObjects 8 }

cfprApEtherFtwPortPairFsmStageEntry OBJECT-TYPE
    SYNTAX           CfprApEtherFtwPortPairFsmStageEntry
    MAX-ACCESS       not-accessible
    STATUS           current
    DESCRIPTION
        "Entry for the cfprApEtherFtwPortPairFsmStageTable table."
    INDEX { cfprApEtherFtwPortPairFsmStageInstanceId }
    ::= { cfprApEtherFtwPortPairFsmStageTable 1 }

CfprApEtherFtwPortPairFsmStageEntry ::= SEQUENCE {
    cfprApEtherFtwPortPairFsmStageInstanceId                         CfprApManagedObjectId,
    cfprApEtherFtwPortPairFsmStageDn                                 CfprApManagedObjectDn,
    cfprApEtherFtwPortPairFsmStageRn                                 SnmpAdminString,
    cfprApEtherFtwPortPairFsmStageDescrData                          SnmpAdminString,
    cfprApEtherFtwPortPairFsmStageLastUpdateTime                     DateAndTime,
    cfprApEtherFtwPortPairFsmStageName                               CfprApEtherFtwPortPairFsmStageName,
    cfprApEtherFtwPortPairFsmStageOrder                              Gauge32,
    cfprApEtherFtwPortPairFsmStageRetry                              Gauge32,
    cfprApEtherFtwPortPairFsmStageStageStatus                        CfprApFsmFsmStageStatus
}

cfprApEtherFtwPortPairFsmStageInstanceId OBJECT-TYPE
    SYNTAX       CfprApManagedObjectId
    MAX-ACCESS   not-accessible
    STATUS       current
    DESCRIPTION
        "Instance identifier of the managed object."
    ::= { cfprApEtherFtwPortPairFsmStageEntry 1 }

cfprApEtherFtwPortPairFsmStageDn OBJECT-TYPE
    SYNTAX       CfprApManagedObjectDn
    MAX-ACCESS   read-only
    STATUS       current
    DESCRIPTION
        "Cisco Firepower ether:FtwPortPairFsmStage:dn managed
        object property"
    ::= { cfprApEtherFtwPortPairFsmStageEntry 2 }

cfprApEtherFtwPortPairFsmStageRn OBJECT-TYPE
    SYNTAX       SnmpAdminString
    MAX-ACCESS   read-only
    STATUS       current
    DESCRIPTION
        "Cisco Firepower ether:FtwPortPairFsmStage:rn managed
        object property"
    ::= { cfprApEtherFtwPortPairFsmStageEntry 3 }

cfprApEtherFtwPortPairFsmStageDescrData OBJECT-TYPE
    SYNTAX       SnmpAdminString
    MAX-ACCESS   read-only
    STATUS       current
    DESCRIPTION
        "Cisco Firepower ether:FtwPortPairFsmStage:descr
        managed object property"
    ::= { cfprApEtherFtwPortPairFsmStageEntry 4 }

cfprApEtherFtwPortPairFsmStageLastUpdateTime OBJECT-TYPE
    SYNTAX       DateAndTime
    MAX-ACCESS   read-only
    STATUS       current
    DESCRIPTION
        "Cisco Firepower ether:FtwPortPairFsmStage:lastUpdateTime
        managed object property"
    ::= { cfprApEtherFtwPortPairFsmStageEntry 5 }

cfprApEtherFtwPortPairFsmStageName OBJECT-TYPE
    SYNTAX       CfprApEtherFtwPortPairFsmStageName
    MAX-ACCESS   read-only
    STATUS       current
    DESCRIPTION
        "Cisco Firepower ether:FtwPortPairFsmStage:name
        managed object property"
    ::= { cfprApEtherFtwPortPairFsmStageEntry 6 }

cfprApEtherFtwPortPairFsmStageOrder OBJECT-TYPE
    SYNTAX       Gauge32
    MAX-ACCESS   read-only
    STATUS       current
    DESCRIPTION
        "Cisco Firepower ether:FtwPortPairFsmStage:order
        managed object property"
    ::= { cfprApEtherFtwPortPairFsmStageEntry 7 }

cfprApEtherFtwPortPairFsmStageRetry OBJECT-TYPE
    SYNTAX       Gauge32
    MAX-ACCESS   read-only
    STATUS       current
    DESCRIPTION
        "Cisco Firepower ether:FtwPortPairFsmStage:retry
        managed object property"
    ::= { cfprApEtherFtwPortPairFsmStageEntry 8 }

cfprApEtherFtwPortPairFsmStageStageStatus OBJECT-TYPE
    SYNTAX       CfprApFsmFsmStageStatus
    MAX-ACCESS   read-only
    STATUS       current
    DESCRIPTION
        "Cisco Firepower ether:FtwPortPairFsmStage:stageStatus
        managed object property"
    ::= { cfprApEtherFtwPortPairFsmStageEntry 9 }

cfprApEtherFtwPortPairFsmTaskTable OBJECT-TYPE
    SYNTAX           SEQUENCE OF CfprApEtherFtwPortPairFsmTaskEntry
    MAX-ACCESS       not-accessible
    STATUS           current
    DESCRIPTION
        "Cisco Firepower ether:FtwPortPairFsmTask managed object table"
    ::= { cfprApEtherObjects 9 }

cfprApEtherFtwPortPairFsmTaskEntry OBJECT-TYPE
    SYNTAX           CfprApEtherFtwPortPairFsmTaskEntry
    MAX-ACCESS       not-accessible
    STATUS           current
    DESCRIPTION
        "Entry for the cfprApEtherFtwPortPairFsmTaskTable table."
    INDEX { cfprApEtherFtwPortPairFsmTaskInstanceId }
    ::= { cfprApEtherFtwPortPairFsmTaskTable 1 }

CfprApEtherFtwPortPairFsmTaskEntry ::= SEQUENCE {
    cfprApEtherFtwPortPairFsmTaskInstanceId                          CfprApManagedObjectId,
    cfprApEtherFtwPortPairFsmTaskDn                                  CfprApManagedObjectDn,
    cfprApEtherFtwPortPairFsmTaskRn                                  SnmpAdminString,
    cfprApEtherFtwPortPairFsmTaskCompletion                          CfprApFsmCompletion,
    cfprApEtherFtwPortPairFsmTaskFlags                               CfprApFsmFlags,
    cfprApEtherFtwPortPairFsmTaskItem                                CfprApEtherFtwPortPairFsmTaskItem,
    cfprApEtherFtwPortPairFsmTaskSeqId                               Gauge32
}

cfprApEtherFtwPortPairFsmTaskInstanceId OBJECT-TYPE
    SYNTAX       CfprApManagedObjectId
    MAX-ACCESS   not-accessible
    STATUS       current
    DESCRIPTION
        "Instance identifier of the managed object."
    ::= { cfprApEtherFtwPortPairFsmTaskEntry 1 }

cfprApEtherFtwPortPairFsmTaskDn OBJECT-TYPE
    SYNTAX       CfprApManagedObjectDn
    MAX-ACCESS   read-only
    STATUS       current
    DESCRIPTION
        "Cisco Firepower ether:FtwPortPairFsmTask:dn managed
        object property"
    ::= { cfprApEtherFtwPortPairFsmTaskEntry 2 }

cfprApEtherFtwPortPairFsmTaskRn OBJECT-TYPE
    SYNTAX       SnmpAdminString
    MAX-ACCESS   read-only
    STATUS       current
    DESCRIPTION
        "Cisco Firepower ether:FtwPortPairFsmTask:rn managed
        object property"
    ::= { cfprApEtherFtwPortPairFsmTaskEntry 3 }

cfprApEtherFtwPortPairFsmTaskCompletion OBJECT-TYPE
    SYNTAX       CfprApFsmCompletion
    MAX-ACCESS   read-only
    STATUS       current
    DESCRIPTION
        "Cisco Firepower ether:FtwPortPairFsmTask:completion
        managed object property"
    ::= { cfprApEtherFtwPortPairFsmTaskEntry 4 }

cfprApEtherFtwPortPairFsmTaskFlags OBJECT-TYPE
    SYNTAX       CfprApFsmFlags
    MAX-ACCESS   read-only
    STATUS       current
    DESCRIPTION
        "Cisco Firepower ether:FtwPortPairFsmTask:flags
        managed object property"
    ::= { cfprApEtherFtwPortPairFsmTaskEntry 5 }

cfprApEtherFtwPortPairFsmTaskItem OBJECT-TYPE
    SYNTAX       CfprApEtherFtwPortPairFsmTaskItem
    MAX-ACCESS   read-only
    STATUS       current
    DESCRIPTION
        "Cisco Firepower ether:FtwPortPairFsmTask:item
        managed object property"
    ::= { cfprApEtherFtwPortPairFsmTaskEntry 6 }

cfprApEtherFtwPortPairFsmTaskSeqId OBJECT-TYPE
    SYNTAX       Gauge32
    MAX-ACCESS   read-only
    STATUS       current
    DESCRIPTION
        "Cisco Firepower ether:FtwPortPairFsmTask:seqId
        managed object property"
    ::= { cfprApEtherFtwPortPairFsmTaskEntry 7 }

cfprApEtherLossStatsTable OBJECT-TYPE
    SYNTAX           SEQUENCE OF CfprApEtherLossStatsEntry
    MAX-ACCESS       not-accessible
    STATUS           current
    DESCRIPTION
        "Cisco Firepower ether:LossStats managed object table"
    ::= { cfprApEtherObjects 10 }

cfprApEtherLossStatsEntry OBJECT-TYPE
    SYNTAX           CfprApEtherLossStatsEntry
    MAX-ACCESS       not-accessible
    STATUS           current
    DESCRIPTION
        "Entry for the cfprApEtherLossStatsTable table."
    INDEX { cfprApEtherLossStatsInstanceId }
    ::= { cfprApEtherLossStatsTable 1 }

CfprApEtherLossStatsEntry ::= SEQUENCE {
    cfprApEtherLossStatsInstanceId                                   CfprApManagedObjectId,
    cfprApEtherLossStatsDn                                           CfprApManagedObjectDn,
    cfprApEtherLossStatsRn                                           SnmpAdminString,
    cfprApEtherLossStatsSQETest                                      Unsigned64,
    cfprApEtherLossStatsSQETestDelta                                 Counter64,
    cfprApEtherLossStatsSQETestDeltaAvg                              Unsigned64,
    cfprApEtherLossStatsSQETestDeltaMax                              Unsigned64,
    cfprApEtherLossStatsSQETestDeltaMin                              Unsigned64,
    cfprApEtherLossStatsCarrierSense                                 Unsigned64,
    cfprApEtherLossStatsCarrierSenseDelta                            Counter64,
    cfprApEtherLossStatsCarrierSenseDeltaAvg                         Unsigned64,
    cfprApEtherLossStatsCarrierSenseDeltaMax                         Unsigned64,
    cfprApEtherLossStatsCarrierSenseDeltaMin                         Unsigned64,
    cfprApEtherLossStatsExcessCollision                              Unsigned64,
    cfprApEtherLossStatsExcessCollisionDelta                         Counter64,
    cfprApEtherLossStatsExcessCollisionDeltaAvg                      Unsigned64,
    cfprApEtherLossStatsExcessCollisionDeltaMax                      Unsigned64,
    cfprApEtherLossStatsExcessCollisionDeltaMin                      Unsigned64,
    cfprApEtherLossStatsGiants                                       Unsigned64,
    cfprApEtherLossStatsGiantsDelta                                  Counter64,
    cfprApEtherLossStatsGiantsDeltaAvg                               Unsigned64,
    cfprApEtherLossStatsGiantsDeltaMax                               Unsigned64,
    cfprApEtherLossStatsGiantsDeltaMin                               Unsigned64,
    cfprApEtherLossStatsIntervals                                    Gauge32,
    cfprApEtherLossStatsLateCollision                                Unsigned64,
    cfprApEtherLossStatsLateCollisionDelta                           Counter64,
    cfprApEtherLossStatsLateCollisionDeltaAvg                        Unsigned64,
    cfprApEtherLossStatsLateCollisionDeltaMax                        Unsigned64,
    cfprApEtherLossStatsLateCollisionDeltaMin                        Unsigned64,
    cfprApEtherLossStatsMultiCollision                               Unsigned64,
    cfprApEtherLossStatsMultiCollisionDelta                          Counter64,
    cfprApEtherLossStatsMultiCollisionDeltaAvg                       Unsigned64,
    cfprApEtherLossStatsMultiCollisionDeltaMax                       Unsigned64,
    cfprApEtherLossStatsMultiCollisionDeltaMin                       Unsigned64,
    cfprApEtherLossStatsSingleCollision                              Unsigned64,
    cfprApEtherLossStatsSingleCollisionDelta                         Counter64,
    cfprApEtherLossStatsSingleCollisionDeltaAvg                      Unsigned64,
    cfprApEtherLossStatsSingleCollisionDeltaMax                      Unsigned64,
    cfprApEtherLossStatsSingleCollisionDeltaMin                      Unsigned64,
    cfprApEtherLossStatsSuspect                                      TruthValue,
    cfprApEtherLossStatsSymbol                                       Unsigned64,
    cfprApEtherLossStatsSymbolDelta                                  Counter64,
    cfprApEtherLossStatsSymbolDeltaAvg                               Unsigned64,
    cfprApEtherLossStatsSymbolDeltaMax                               Unsigned64,
    cfprApEtherLossStatsSymbolDeltaMin                               Unsigned64,
    cfprApEtherLossStatsThresholded                                  CfprApEtherLossStatsThresholded,
    cfprApEtherLossStatsTimeCollected                                DateAndTime,
    cfprApEtherLossStatsUpdate                                       Gauge32
}

cfprApEtherLossStatsInstanceId OBJECT-TYPE
    SYNTAX       CfprApManagedObjectId
    MAX-ACCESS   not-accessible
    STATUS       current
    DESCRIPTION
        "Instance identifier of the managed object."
    ::= { cfprApEtherLossStatsEntry 1 }

cfprApEtherLossStatsDn OBJECT-TYPE
    SYNTAX       CfprApManagedObjectDn
    MAX-ACCESS   read-only
    STATUS       current
    DESCRIPTION
        "Cisco Firepower ether:LossStats:dn managed object property"
    ::= { cfprApEtherLossStatsEntry 2 }

cfprApEtherLossStatsRn OBJECT-TYPE
    SYNTAX       SnmpAdminString
    MAX-ACCESS   read-only
    STATUS       current
    DESCRIPTION
        "Cisco Firepower ether:LossStats:rn managed object property"
    ::= { cfprApEtherLossStatsEntry 3 }

cfprApEtherLossStatsSQETest OBJECT-TYPE
    SYNTAX       Unsigned64
    MAX-ACCESS   read-only
    STATUS       current
    DESCRIPTION
        "Cisco Firepower ether:LossStats:SQETest managed object property"
    ::= { cfprApEtherLossStatsEntry 4 }

cfprApEtherLossStatsSQETestDelta OBJECT-TYPE
    SYNTAX       Counter64
    MAX-ACCESS   read-only
    STATUS       current
    DESCRIPTION
        "Cisco Firepower ether:LossStats:SQETestDelta managed
        object property"
    ::= { cfprApEtherLossStatsEntry 5 }

cfprApEtherLossStatsSQETestDeltaAvg OBJECT-TYPE
    SYNTAX       Unsigned64
    MAX-ACCESS   read-only
    STATUS       current
    DESCRIPTION
        "Cisco Firepower ether:LossStats:SQETestDeltaAvg
        managed object property"
    ::= { cfprApEtherLossStatsEntry 6 }

cfprApEtherLossStatsSQETestDeltaMax OBJECT-TYPE
    SYNTAX       Unsigned64
    MAX-ACCESS   read-only
    STATUS       current
    DESCRIPTION
        "Cisco Firepower ether:LossStats:SQETestDeltaMax
        managed object property"
    ::= { cfprApEtherLossStatsEntry 7 }

cfprApEtherLossStatsSQETestDeltaMin OBJECT-TYPE
    SYNTAX       Unsigned64
    MAX-ACCESS   read-only
    STATUS       current
    DESCRIPTION
        "Cisco Firepower ether:LossStats:SQETestDeltaMin
        managed object property"
    ::= { cfprApEtherLossStatsEntry 8 }

cfprApEtherLossStatsCarrierSense OBJECT-TYPE
    SYNTAX       Unsigned64
    MAX-ACCESS   read-only
    STATUS       current
    DESCRIPTION
        "Cisco Firepower ether:LossStats:carrierSense managed
        object property"
    ::= { cfprApEtherLossStatsEntry 9 }

cfprApEtherLossStatsCarrierSenseDelta OBJECT-TYPE
    SYNTAX       Counter64
    MAX-ACCESS   read-only
    STATUS       current
    DESCRIPTION
        "Cisco Firepower ether:LossStats:carrierSenseDelta
        managed object property"
    ::= { cfprApEtherLossStatsEntry 10 }

cfprApEtherLossStatsCarrierSenseDeltaAvg OBJECT-TYPE
    SYNTAX       Unsigned64
    MAX-ACCESS   read-only
    STATUS       current
    DESCRIPTION
        "Cisco Firepower ether:LossStats:carrierSenseDeltaAvg
        managed object property"
    ::= { cfprApEtherLossStatsEntry 11 }

cfprApEtherLossStatsCarrierSenseDeltaMax OBJECT-TYPE
    SYNTAX       Unsigned64
    MAX-ACCESS   read-only
    STATUS       current
    DESCRIPTION
        "Cisco Firepower ether:LossStats:carrierSenseDeltaMax
        managed object property"
    ::= { cfprApEtherLossStatsEntry 12 }

cfprApEtherLossStatsCarrierSenseDeltaMin OBJECT-TYPE
    SYNTAX       Unsigned64
    MAX-ACCESS   read-only
    STATUS       current
    DESCRIPTION
        "Cisco Firepower ether:LossStats:carrierSenseDeltaMin
        managed object property"
    ::= { cfprApEtherLossStatsEntry 13 }

cfprApEtherLossStatsExcessCollision OBJECT-TYPE
    SYNTAX       Unsigned64
    MAX-ACCESS   read-only
    STATUS       current
    DESCRIPTION
        "Cisco Firepower ether:LossStats:excessCollision
        managed object property"
    ::= { cfprApEtherLossStatsEntry 14 }

cfprApEtherLossStatsExcessCollisionDelta OBJECT-TYPE
    SYNTAX       Counter64
    MAX-ACCESS   read-only
    STATUS       current
    DESCRIPTION
        "Cisco Firepower ether:LossStats:excessCollisionDelta
        managed object property"
    ::= { cfprApEtherLossStatsEntry 15 }

cfprApEtherLossStatsExcessCollisionDeltaAvg OBJECT-TYPE
    SYNTAX       Unsigned64
    MAX-ACCESS   read-only
    STATUS       current
    DESCRIPTION
        "Cisco Firepower ether:LossStats:excessCollisionDeltaAvg
        managed object property"
    ::= { cfprApEtherLossStatsEntry 16 }

cfprApEtherLossStatsExcessCollisionDeltaMax OBJECT-TYPE
    SYNTAX       Unsigned64
    MAX-ACCESS   read-only
    STATUS       current
    DESCRIPTION
        "Cisco Firepower ether:LossStats:excessCollisionDeltaMax
        managed object property"
    ::= { cfprApEtherLossStatsEntry 17 }

cfprApEtherLossStatsExcessCollisionDeltaMin OBJECT-TYPE
    SYNTAX       Unsigned64
    MAX-ACCESS   read-only
    STATUS       current
    DESCRIPTION
        "Cisco Firepower ether:LossStats:excessCollisionDeltaMin
        managed object property"
    ::= { cfprApEtherLossStatsEntry 18 }

cfprApEtherLossStatsGiants OBJECT-TYPE
    SYNTAX       Unsigned64
    MAX-ACCESS   read-only
    STATUS       current
    DESCRIPTION
        "Cisco Firepower ether:LossStats:giants managed object property"
    ::= { cfprApEtherLossStatsEntry 19 }

cfprApEtherLossStatsGiantsDelta OBJECT-TYPE
    SYNTAX       Counter64
    MAX-ACCESS   read-only
    STATUS       current
    DESCRIPTION
        "Cisco Firepower ether:LossStats:giantsDelta managed
        object property"
    ::= { cfprApEtherLossStatsEntry 20 }

cfprApEtherLossStatsGiantsDeltaAvg OBJECT-TYPE
    SYNTAX       Unsigned64
    MAX-ACCESS   read-only
    STATUS       current
    DESCRIPTION
        "Cisco Firepower ether:LossStats:giantsDeltaAvg
        managed object property"
    ::= { cfprApEtherLossStatsEntry 21 }

cfprApEtherLossStatsGiantsDeltaMax OBJECT-TYPE
    SYNTAX       Unsigned64
    MAX-ACCESS   read-only
    STATUS       current
    DESCRIPTION
        "Cisco Firepower ether:LossStats:giantsDeltaMax
        managed object property"
    ::= { cfprApEtherLossStatsEntry 22 }

cfprApEtherLossStatsGiantsDeltaMin OBJECT-TYPE
    SYNTAX       Unsigned64
    MAX-ACCESS   read-only
    STATUS       current
    DESCRIPTION
        "Cisco Firepower ether:LossStats:giantsDeltaMin
        managed object property"
    ::= { cfprApEtherLossStatsEntry 23 }

cfprApEtherLossStatsIntervals OBJECT-TYPE
    SYNTAX       Gauge32
    MAX-ACCESS   read-only
    STATUS       current
    DESCRIPTION
        "Cisco Firepower ether:LossStats:intervals managed
        object property"
    ::= { cfprApEtherLossStatsEntry 24 }

cfprApEtherLossStatsLateCollision OBJECT-TYPE
    SYNTAX       Unsigned64
    MAX-ACCESS   read-only
    STATUS       current
    DESCRIPTION
        "Cisco Firepower ether:LossStats:lateCollision
        managed object property"
    ::= { cfprApEtherLossStatsEntry 25 }

cfprApEtherLossStatsLateCollisionDelta OBJECT-TYPE
    SYNTAX       Counter64
    MAX-ACCESS   read-only
    STATUS       current
    DESCRIPTION
        "Cisco Firepower ether:LossStats:lateCollisionDelta
        managed object property"
    ::= { cfprApEtherLossStatsEntry 26 }

cfprApEtherLossStatsLateCollisionDeltaAvg OBJECT-TYPE
    SYNTAX       Unsigned64
    MAX-ACCESS   read-only
    STATUS       current
    DESCRIPTION
        "Cisco Firepower ether:LossStats:lateCollisionDeltaAvg
        managed object property"
    ::= { cfprApEtherLossStatsEntry 27 }

cfprApEtherLossStatsLateCollisionDeltaMax OBJECT-TYPE
    SYNTAX       Unsigned64
    MAX-ACCESS   read-only
    STATUS       current
    DESCRIPTION
        "Cisco Firepower ether:LossStats:lateCollisionDeltaMax
        managed object property"
    ::= { cfprApEtherLossStatsEntry 28 }

cfprApEtherLossStatsLateCollisionDeltaMin OBJECT-TYPE
    SYNTAX       Unsigned64
    MAX-ACCESS   read-only
    STATUS       current
    DESCRIPTION
        "Cisco Firepower ether:LossStats:lateCollisionDeltaMin
        managed object property"
    ::= { cfprApEtherLossStatsEntry 29 }

cfprApEtherLossStatsMultiCollision OBJECT-TYPE
    SYNTAX       Unsigned64
    MAX-ACCESS   read-only
    STATUS       current
    DESCRIPTION
        "Cisco Firepower ether:LossStats:multiCollision
        managed object property"
    ::= { cfprApEtherLossStatsEntry 30 }

cfprApEtherLossStatsMultiCollisionDelta OBJECT-TYPE
    SYNTAX       Counter64
    MAX-ACCESS   read-only
    STATUS       current
    DESCRIPTION
        "Cisco Firepower ether:LossStats:multiCollisionDelta
        managed object property"
    ::= { cfprApEtherLossStatsEntry 31 }

cfprApEtherLossStatsMultiCollisionDeltaAvg OBJECT-TYPE
    SYNTAX       Unsigned64
    MAX-ACCESS   read-only
    STATUS       current
    DESCRIPTION
        "Cisco Firepower ether:LossStats:multiCollisionDeltaAvg
        managed object property"
    ::= { cfprApEtherLossStatsEntry 32 }

cfprApEtherLossStatsMultiCollisionDeltaMax OBJECT-TYPE
    SYNTAX       Unsigned64
    MAX-ACCESS   read-only
    STATUS       current
    DESCRIPTION
        "Cisco Firepower ether:LossStats:multiCollisionDeltaMax
        managed object property"
    ::= { cfprApEtherLossStatsEntry 33 }

cfprApEtherLossStatsMultiCollisionDeltaMin OBJECT-TYPE
    SYNTAX       Unsigned64
    MAX-ACCESS   read-only
    STATUS       current
    DESCRIPTION
        "Cisco Firepower ether:LossStats:multiCollisionDeltaMin
        managed object property"
    ::= { cfprApEtherLossStatsEntry 34 }

cfprApEtherLossStatsSingleCollision OBJECT-TYPE
    SYNTAX       Unsigned64
    MAX-ACCESS   read-only
    STATUS       current
    DESCRIPTION
        "Cisco Firepower ether:LossStats:singleCollision
        managed object property"
    ::= { cfprApEtherLossStatsEntry 35 }

cfprApEtherLossStatsSingleCollisionDelta OBJECT-TYPE
    SYNTAX       Counter64
    MAX-ACCESS   read-only
    STATUS       current
    DESCRIPTION
        "Cisco Firepower ether:LossStats:singleCollisionDelta
        managed object property"
    ::= { cfprApEtherLossStatsEntry 36 }

cfprApEtherLossStatsSingleCollisionDeltaAvg OBJECT-TYPE
    SYNTAX       Unsigned64
    MAX-ACCESS   read-only
    STATUS       current
    DESCRIPTION
        "Cisco Firepower ether:LossStats:singleCollisionDeltaAvg
        managed object property"
    ::= { cfprApEtherLossStatsEntry 37 }

cfprApEtherLossStatsSingleCollisionDeltaMax OBJECT-TYPE
    SYNTAX       Unsigned64
    MAX-ACCESS   read-only
    STATUS       current
    DESCRIPTION
        "Cisco Firepower ether:LossStats:singleCollisionDeltaMax
        managed object property"
    ::= { cfprApEtherLossStatsEntry 38 }

cfprApEtherLossStatsSingleCollisionDeltaMin OBJECT-TYPE
    SYNTAX       Unsigned64
    MAX-ACCESS   read-only
    STATUS       current
    DESCRIPTION
        "Cisco Firepower ether:LossStats:singleCollisionDeltaMin
        managed object property"
    ::= { cfprApEtherLossStatsEntry 39 }

cfprApEtherLossStatsSuspect OBJECT-TYPE
    SYNTAX       TruthValue
    MAX-ACCESS   read-only
    STATUS       current
    DESCRIPTION
        "Cisco Firepower ether:LossStats:suspect managed object property"
    ::= { cfprApEtherLossStatsEntry 40 }

cfprApEtherLossStatsSymbol OBJECT-TYPE
    SYNTAX       Unsigned64
    MAX-ACCESS   read-only
    STATUS       current
    DESCRIPTION
        "Cisco Firepower ether:LossStats:symbol managed object property"
    ::= { cfprApEtherLossStatsEntry 41 }

cfprApEtherLossStatsSymbolDelta OBJECT-TYPE
    SYNTAX       Counter64
    MAX-ACCESS   read-only
    STATUS       current
    DESCRIPTION
        "Cisco Firepower ether:LossStats:symbolDelta managed
        object property"
    ::= { cfprApEtherLossStatsEntry 42 }

cfprApEtherLossStatsSymbolDeltaAvg OBJECT-TYPE
    SYNTAX       Unsigned64
    MAX-ACCESS   read-only
    STATUS       current
    DESCRIPTION
        "Cisco Firepower ether:LossStats:symbolDeltaAvg
        managed object property"
    ::= { cfprApEtherLossStatsEntry 43 }

cfprApEtherLossStatsSymbolDeltaMax OBJECT-TYPE
    SYNTAX       Unsigned64
    MAX-ACCESS   read-only
    STATUS       current
    DESCRIPTION
        "Cisco Firepower ether:LossStats:symbolDeltaMax
        managed object property"
    ::= { cfprApEtherLossStatsEntry 44 }

cfprApEtherLossStatsSymbolDeltaMin OBJECT-TYPE
    SYNTAX       Unsigned64
    MAX-ACCESS   read-only
    STATUS       current
    DESCRIPTION
        "Cisco Firepower ether:LossStats:symbolDeltaMin
        managed object property"
    ::= { cfprApEtherLossStatsEntry 45 }

cfprApEtherLossStatsThresholded OBJECT-TYPE
    SYNTAX       CfprApEtherLossStatsThresholded
    MAX-ACCESS   read-only
    STATUS       current
    DESCRIPTION
        "Cisco Firepower ether:LossStats:thresholded managed
        object property"
    ::= { cfprApEtherLossStatsEntry 46 }

cfprApEtherLossStatsTimeCollected OBJECT-TYPE
    SYNTAX       DateAndTime
    MAX-ACCESS   read-only
    STATUS       current
    DESCRIPTION
        "Cisco Firepower ether:LossStats:timeCollected
        managed object property"
    ::= { cfprApEtherLossStatsEntry 47 }

cfprApEtherLossStatsUpdate OBJECT-TYPE
    SYNTAX       Gauge32
    MAX-ACCESS   read-only
    STATUS       current
    DESCRIPTION
        "Cisco Firepower ether:LossStats:update managed object property"
    ::= { cfprApEtherLossStatsEntry 48 }

cfprApEtherLossStatsHistTable OBJECT-TYPE
    SYNTAX           SEQUENCE OF CfprApEtherLossStatsHistEntry
    MAX-ACCESS       not-accessible
    STATUS           current
    DESCRIPTION
        "Cisco Firepower ether:LossStatsHist managed object table"
    ::= { cfprApEtherObjects 11 }

cfprApEtherLossStatsHistEntry OBJECT-TYPE
    SYNTAX           CfprApEtherLossStatsHistEntry
    MAX-ACCESS       not-accessible
    STATUS           current
    DESCRIPTION
        "Entry for the cfprApEtherLossStatsHistTable table."
    INDEX { cfprApEtherLossStatsHistInstanceId }
    ::= { cfprApEtherLossStatsHistTable 1 }

CfprApEtherLossStatsHistEntry ::= SEQUENCE {
    cfprApEtherLossStatsHistInstanceId                               CfprApManagedObjectId,
    cfprApEtherLossStatsHistDn                                       CfprApManagedObjectDn,
    cfprApEtherLossStatsHistRn                                       SnmpAdminString,
    cfprApEtherLossStatsHistSQETest                                  Unsigned64,
    cfprApEtherLossStatsHistSQETestDelta                             Unsigned64,
    cfprApEtherLossStatsHistSQETestDeltaAvg                          Unsigned64,
    cfprApEtherLossStatsHistSQETestDeltaMax                          Unsigned64,
    cfprApEtherLossStatsHistSQETestDeltaMin                          Unsigned64,
    cfprApEtherLossStatsHistCarrierSense                             Unsigned64,
    cfprApEtherLossStatsHistCarrierSenseDelta                        Unsigned64,
    cfprApEtherLossStatsHistCarrierSenseDeltaAvg                     Unsigned64,
    cfprApEtherLossStatsHistCarrierSenseDeltaMax                     Unsigned64,
    cfprApEtherLossStatsHistCarrierSenseDeltaMin                     Unsigned64,
    cfprApEtherLossStatsHistExcessCollision                          Unsigned64,
    cfprApEtherLossStatsHistExcessCollisionDelta                     Unsigned64,
    cfprApEtherLossStatsHistExcessCollisionDeltaAvg                  Unsigned64,
    cfprApEtherLossStatsHistExcessCollisionDeltaMax                  Unsigned64,
    cfprApEtherLossStatsHistExcessCollisionDeltaMin                  Unsigned64,
    cfprApEtherLossStatsHistGiants                                   Unsigned64,
    cfprApEtherLossStatsHistGiantsDelta                              Unsigned64,
    cfprApEtherLossStatsHistGiantsDeltaAvg                           Unsigned64,
    cfprApEtherLossStatsHistGiantsDeltaMax                           Unsigned64,
    cfprApEtherLossStatsHistGiantsDeltaMin                           Unsigned64,
    cfprApEtherLossStatsHistId                                       Unsigned64,
    cfprApEtherLossStatsHistLateCollision                            Unsigned64,
    cfprApEtherLossStatsHistLateCollisionDelta                       Unsigned64,
    cfprApEtherLossStatsHistLateCollisionDeltaAvg                    Unsigned64,
    cfprApEtherLossStatsHistLateCollisionDeltaMax                    Unsigned64,
    cfprApEtherLossStatsHistLateCollisionDeltaMin                    Unsigned64,
    cfprApEtherLossStatsHistMostRecent                               TruthValue,
    cfprApEtherLossStatsHistMultiCollision                           Unsigned64,
    cfprApEtherLossStatsHistMultiCollisionDelta                      Unsigned64,
    cfprApEtherLossStatsHistMultiCollisionDeltaAvg                   Unsigned64,
    cfprApEtherLossStatsHistMultiCollisionDeltaMax                   Unsigned64,
    cfprApEtherLossStatsHistMultiCollisionDeltaMin                   Unsigned64,
    cfprApEtherLossStatsHistSingleCollision                          Unsigned64,
    cfprApEtherLossStatsHistSingleCollisionDelta                     Unsigned64,
    cfprApEtherLossStatsHistSingleCollisionDeltaAvg                  Unsigned64,
    cfprApEtherLossStatsHistSingleCollisionDeltaMax                  Unsigned64,
    cfprApEtherLossStatsHistSingleCollisionDeltaMin                  Unsigned64,
    cfprApEtherLossStatsHistSuspect                                  TruthValue,
    cfprApEtherLossStatsHistSymbol                                   Unsigned64,
    cfprApEtherLossStatsHistSymbolDelta                              Unsigned64,
    cfprApEtherLossStatsHistSymbolDeltaAvg                           Unsigned64,
    cfprApEtherLossStatsHistSymbolDeltaMax                           Unsigned64,
    cfprApEtherLossStatsHistSymbolDeltaMin                           Unsigned64,
    cfprApEtherLossStatsHistThresholded                              CfprApEtherLossStatsHistThresholded,
    cfprApEtherLossStatsHistTimeCollected                            DateAndTime
}

cfprApEtherLossStatsHistInstanceId OBJECT-TYPE
    SYNTAX       CfprApManagedObjectId
    MAX-ACCESS   not-accessible
    STATUS       current
    DESCRIPTION
        "Instance identifier of the managed object."
    ::= { cfprApEtherLossStatsHistEntry 1 }

cfprApEtherLossStatsHistDn OBJECT-TYPE
    SYNTAX       CfprApManagedObjectDn
    MAX-ACCESS   read-only
    STATUS       current
    DESCRIPTION
        "Cisco Firepower ether:LossStatsHist:dn managed object property"
    ::= { cfprApEtherLossStatsHistEntry 2 }

cfprApEtherLossStatsHistRn OBJECT-TYPE
    SYNTAX       SnmpAdminString
    MAX-ACCESS   read-only
    STATUS       current
    DESCRIPTION
        "Cisco Firepower ether:LossStatsHist:rn managed object property"
    ::= { cfprApEtherLossStatsHistEntry 3 }

cfprApEtherLossStatsHistSQETest OBJECT-TYPE
    SYNTAX       Unsigned64
    MAX-ACCESS   read-only
    STATUS       current
    DESCRIPTION
        "Cisco Firepower ether:LossStatsHist:SQETest managed
        object property"
    ::= { cfprApEtherLossStatsHistEntry 4 }

cfprApEtherLossStatsHistSQETestDelta OBJECT-TYPE
    SYNTAX       Unsigned64
    MAX-ACCESS   read-only
    STATUS       current
    DESCRIPTION
        "Cisco Firepower ether:LossStatsHist:SQETestDelta
        managed object property"
    ::= { cfprApEtherLossStatsHistEntry 5 }

cfprApEtherLossStatsHistSQETestDeltaAvg OBJECT-TYPE
    SYNTAX       Unsigned64
    MAX-ACCESS   read-only
    STATUS       current
    DESCRIPTION
        "Cisco Firepower ether:LossStatsHist:SQETestDeltaAvg
        managed object property"
    ::= { cfprApEtherLossStatsHistEntry 6 }

cfprApEtherLossStatsHistSQETestDeltaMax OBJECT-TYPE
    SYNTAX       Unsigned64
    MAX-ACCESS   read-only
    STATUS       current
    DESCRIPTION
        "Cisco Firepower ether:LossStatsHist:SQETestDeltaMax
        managed object property"
    ::= { cfprApEtherLossStatsHistEntry 7 }

cfprApEtherLossStatsHistSQETestDeltaMin OBJECT-TYPE
    SYNTAX       Unsigned64
    MAX-ACCESS   read-only
    STATUS       current
    DESCRIPTION
        "Cisco Firepower ether:LossStatsHist:SQETestDeltaMin
        managed object property"
    ::= { cfprApEtherLossStatsHistEntry 8 }

cfprApEtherLossStatsHistCarrierSense OBJECT-TYPE
    SYNTAX       Unsigned64
    MAX-ACCESS   read-only
    STATUS       current
    DESCRIPTION
        "Cisco Firepower ether:LossStatsHist:carrierSense
        managed object property"
    ::= { cfprApEtherLossStatsHistEntry 9 }

cfprApEtherLossStatsHistCarrierSenseDelta OBJECT-TYPE
    SYNTAX       Unsigned64
    MAX-ACCESS   read-only
    STATUS       current
    DESCRIPTION
        "Cisco Firepower ether:LossStatsHist:carrierSenseDelta
        managed object property"
    ::= { cfprApEtherLossStatsHistEntry 10 }

cfprApEtherLossStatsHistCarrierSenseDeltaAvg OBJECT-TYPE
    SYNTAX       Unsigned64
    MAX-ACCESS   read-only
    STATUS       current
    DESCRIPTION
        "Cisco Firepower ether:LossStatsHist:carrierSenseDeltaAvg
        managed object property"
    ::= { cfprApEtherLossStatsHistEntry 11 }

cfprApEtherLossStatsHistCarrierSenseDeltaMax OBJECT-TYPE
    SYNTAX       Unsigned64
    MAX-ACCESS   read-only
    STATUS       current
    DESCRIPTION
        "Cisco Firepower ether:LossStatsHist:carrierSenseDeltaMax
        managed object property"
    ::= { cfprApEtherLossStatsHistEntry 12 }

cfprApEtherLossStatsHistCarrierSenseDeltaMin OBJECT-TYPE
    SYNTAX       Unsigned64
    MAX-ACCESS   read-only
    STATUS       current
    DESCRIPTION
        "Cisco Firepower ether:LossStatsHist:carrierSenseDeltaMin
        managed object property"
    ::= { cfprApEtherLossStatsHistEntry 13 }

cfprApEtherLossStatsHistExcessCollision OBJECT-TYPE
    SYNTAX       Unsigned64
    MAX-ACCESS   read-only
    STATUS       current
    DESCRIPTION
        "Cisco Firepower ether:LossStatsHist:excessCollision
        managed object property"
    ::= { cfprApEtherLossStatsHistEntry 14 }

cfprApEtherLossStatsHistExcessCollisionDelta OBJECT-TYPE
    SYNTAX       Unsigned64
    MAX-ACCESS   read-only
    STATUS       current
    DESCRIPTION
        "Cisco Firepower ether:LossStatsHist:excessCollisionDelta
        managed object property"
    ::= { cfprApEtherLossStatsHistEntry 15 }

cfprApEtherLossStatsHistExcessCollisionDeltaAvg OBJECT-TYPE
    SYNTAX       Unsigned64
    MAX-ACCESS   read-only
    STATUS       current
    DESCRIPTION
        "Cisco Firepower ether:LossStatsHist:excessCollisionDeltaAvg
        managed object property"
    ::= { cfprApEtherLossStatsHistEntry 16 }

cfprApEtherLossStatsHistExcessCollisionDeltaMax OBJECT-TYPE
    SYNTAX       Unsigned64
    MAX-ACCESS   read-only
    STATUS       current
    DESCRIPTION
        "Cisco Firepower ether:LossStatsHist:excessCollisionDeltaMax
        managed object property"
    ::= { cfprApEtherLossStatsHistEntry 17 }

cfprApEtherLossStatsHistExcessCollisionDeltaMin OBJECT-TYPE
    SYNTAX       Unsigned64
    MAX-ACCESS   read-only
    STATUS       current
    DESCRIPTION
        "Cisco Firepower ether:LossStatsHist:excessCollisionDeltaMin
        managed object property"
    ::= { cfprApEtherLossStatsHistEntry 18 }

cfprApEtherLossStatsHistGiants OBJECT-TYPE
    SYNTAX       Unsigned64
    MAX-ACCESS   read-only
    STATUS       current
    DESCRIPTION
        "Cisco Firepower ether:LossStatsHist:giants managed
        object property"
    ::= { cfprApEtherLossStatsHistEntry 19 }

cfprApEtherLossStatsHistGiantsDelta OBJECT-TYPE
    SYNTAX       Unsigned64
    MAX-ACCESS   read-only
    STATUS       current
    DESCRIPTION
        "Cisco Firepower ether:LossStatsHist:giantsDelta
        managed object property"
    ::= { cfprApEtherLossStatsHistEntry 20 }

cfprApEtherLossStatsHistGiantsDeltaAvg OBJECT-TYPE
    SYNTAX       Unsigned64
    MAX-ACCESS   read-only
    STATUS       current
    DESCRIPTION
        "Cisco Firepower ether:LossStatsHist:giantsDeltaAvg
        managed object property"
    ::= { cfprApEtherLossStatsHistEntry 21 }

cfprApEtherLossStatsHistGiantsDeltaMax OBJECT-TYPE
    SYNTAX       Unsigned64
    MAX-ACCESS   read-only
    STATUS       current
    DESCRIPTION
        "Cisco Firepower ether:LossStatsHist:giantsDeltaMax
        managed object property"
    ::= { cfprApEtherLossStatsHistEntry 22 }

cfprApEtherLossStatsHistGiantsDeltaMin OBJECT-TYPE
    SYNTAX       Unsigned64
    MAX-ACCESS   read-only
    STATUS       current
    DESCRIPTION
        "Cisco Firepower ether:LossStatsHist:giantsDeltaMin
        managed object property"
    ::= { cfprApEtherLossStatsHistEntry 23 }

cfprApEtherLossStatsHistId OBJECT-TYPE
    SYNTAX       Unsigned64
    MAX-ACCESS   read-only
    STATUS       current
    DESCRIPTION
        "Cisco Firepower ether:LossStatsHist:id managed object property"
    ::= { cfprApEtherLossStatsHistEntry 24 }

cfprApEtherLossStatsHistLateCollision OBJECT-TYPE
    SYNTAX       Unsigned64
    MAX-ACCESS   read-only
    STATUS       current
    DESCRIPTION
        "Cisco Firepower ether:LossStatsHist:lateCollision
        managed object property"
    ::= { cfprApEtherLossStatsHistEntry 25 }

cfprApEtherLossStatsHistLateCollisionDelta OBJECT-TYPE
    SYNTAX       Unsigned64
    MAX-ACCESS   read-only
    STATUS       current
    DESCRIPTION
        "Cisco Firepower ether:LossStatsHist:lateCollisionDelta
        managed object property"
    ::= { cfprApEtherLossStatsHistEntry 26 }

cfprApEtherLossStatsHistLateCollisionDeltaAvg OBJECT-TYPE
    SYNTAX       Unsigned64
    MAX-ACCESS   read-only
    STATUS       current
    DESCRIPTION
        "Cisco Firepower ether:LossStatsHist:lateCollisionDeltaAvg
        managed object property"
    ::= { cfprApEtherLossStatsHistEntry 27 }

cfprApEtherLossStatsHistLateCollisionDeltaMax OBJECT-TYPE
    SYNTAX       Unsigned64
    MAX-ACCESS   read-only
    STATUS       current
    DESCRIPTION
        "Cisco Firepower ether:LossStatsHist:lateCollisionDeltaMax
        managed object property"
    ::= { cfprApEtherLossStatsHistEntry 28 }

cfprApEtherLossStatsHistLateCollisionDeltaMin OBJECT-TYPE
    SYNTAX       Unsigned64
    MAX-ACCESS   read-only
    STATUS       current
    DESCRIPTION
        "Cisco Firepower ether:LossStatsHist:lateCollisionDeltaMin
        managed object property"
    ::= { cfprApEtherLossStatsHistEntry 29 }

cfprApEtherLossStatsHistMostRecent OBJECT-TYPE
    SYNTAX       TruthValue
    MAX-ACCESS   read-only
    STATUS       current
    DESCRIPTION
        "Cisco Firepower ether:LossStatsHist:mostRecent
        managed object property"
    ::= { cfprApEtherLossStatsHistEntry 30 }

cfprApEtherLossStatsHistMultiCollision OBJECT-TYPE
    SYNTAX       Unsigned64
    MAX-ACCESS   read-only
    STATUS       current
    DESCRIPTION
        "Cisco Firepower ether:LossStatsHist:multiCollision
        managed object property"
    ::= { cfprApEtherLossStatsHistEntry 31 }

cfprApEtherLossStatsHistMultiCollisionDelta OBJECT-TYPE
    SYNTAX       Unsigned64
    MAX-ACCESS   read-only
    STATUS       current
    DESCRIPTION
        "Cisco Firepower ether:LossStatsHist:multiCollisionDelta
        managed object property"
    ::= { cfprApEtherLossStatsHistEntry 32 }

cfprApEtherLossStatsHistMultiCollisionDeltaAvg OBJECT-TYPE
    SYNTAX       Unsigned64
    MAX-ACCESS   read-only
    STATUS       current
    DESCRIPTION
        "Cisco Firepower ether:LossStatsHist:multiCollisionDeltaAvg
        managed object property"
    ::= { cfprApEtherLossStatsHistEntry 33 }

cfprApEtherLossStatsHistMultiCollisionDeltaMax OBJECT-TYPE
    SYNTAX       Unsigned64
    MAX-ACCESS   read-only
    STATUS       current
    DESCRIPTION
        "Cisco Firepower ether:LossStatsHist:multiCollisionDeltaMax
        managed object property"
    ::= { cfprApEtherLossStatsHistEntry 34 }

cfprApEtherLossStatsHistMultiCollisionDeltaMin OBJECT-TYPE
    SYNTAX       Unsigned64
    MAX-ACCESS   read-only
    STATUS       current
    DESCRIPTION
        "Cisco Firepower ether:LossStatsHist:multiCollisionDeltaMin
        managed object property"
    ::= { cfprApEtherLossStatsHistEntry 35 }

cfprApEtherLossStatsHistSingleCollision OBJECT-TYPE
    SYNTAX       Unsigned64
    MAX-ACCESS   read-only
    STATUS       current
    DESCRIPTION
        "Cisco Firepower ether:LossStatsHist:singleCollision
        managed object property"
    ::= { cfprApEtherLossStatsHistEntry 36 }

cfprApEtherLossStatsHistSingleCollisionDelta OBJECT-TYPE
    SYNTAX       Unsigned64
    MAX-ACCESS   read-only
    STATUS       current
    DESCRIPTION
        "Cisco Firepower ether:LossStatsHist:singleCollisionDelta
        managed object property"
    ::= { cfprApEtherLossStatsHistEntry 37 }

cfprApEtherLossStatsHistSingleCollisionDeltaAvg OBJECT-TYPE
    SYNTAX       Unsigned64
    MAX-ACCESS   read-only
    STATUS       current
    DESCRIPTION
        "Cisco Firepower ether:LossStatsHist:singleCollisionDeltaAvg
        managed object property"
    ::= { cfprApEtherLossStatsHistEntry 38 }

cfprApEtherLossStatsHistSingleCollisionDeltaMax OBJECT-TYPE
    SYNTAX       Unsigned64
    MAX-ACCESS   read-only
    STATUS       current
    DESCRIPTION
        "Cisco Firepower ether:LossStatsHist:singleCollisionDeltaMax
        managed object property"
    ::= { cfprApEtherLossStatsHistEntry 39 }

cfprApEtherLossStatsHistSingleCollisionDeltaMin OBJECT-TYPE
    SYNTAX       Unsigned64
    MAX-ACCESS   read-only
    STATUS       current
    DESCRIPTION
        "Cisco Firepower ether:LossStatsHist:singleCollisionDeltaMin
        managed object property"
    ::= { cfprApEtherLossStatsHistEntry 40 }

cfprApEtherLossStatsHistSuspect OBJECT-TYPE
    SYNTAX       TruthValue
    MAX-ACCESS   read-only
    STATUS       current
    DESCRIPTION
        "Cisco Firepower ether:LossStatsHist:suspect managed
        object property"
    ::= { cfprApEtherLossStatsHistEntry 41 }

cfprApEtherLossStatsHistSymbol OBJECT-TYPE
    SYNTAX       Unsigned64
    MAX-ACCESS   read-only
    STATUS       current
    DESCRIPTION
        "Cisco Firepower ether:LossStatsHist:symbol managed
        object property"
    ::= { cfprApEtherLossStatsHistEntry 42 }

cfprApEtherLossStatsHistSymbolDelta OBJECT-TYPE
    SYNTAX       Unsigned64
    MAX-ACCESS   read-only
    STATUS       current
    DESCRIPTION
        "Cisco Firepower ether:LossStatsHist:symbolDelta
        managed object property"
    ::= { cfprApEtherLossStatsHistEntry 43 }

cfprApEtherLossStatsHistSymbolDeltaAvg OBJECT-TYPE
    SYNTAX       Unsigned64
    MAX-ACCESS   read-only
    STATUS       current
    DESCRIPTION
        "Cisco Firepower ether:LossStatsHist:symbolDeltaAvg
        managed object property"
    ::= { cfprApEtherLossStatsHistEntry 44 }

cfprApEtherLossStatsHistSymbolDeltaMax OBJECT-TYPE
    SYNTAX       Unsigned64
    MAX-ACCESS   read-only
    STATUS       current
    DESCRIPTION
        "Cisco Firepower ether:LossStatsHist:symbolDeltaMax
        managed object property"
    ::= { cfprApEtherLossStatsHistEntry 45 }

cfprApEtherLossStatsHistSymbolDeltaMin OBJECT-TYPE
    SYNTAX       Unsigned64
    MAX-ACCESS   read-only
    STATUS       current
    DESCRIPTION
        "Cisco Firepower ether:LossStatsHist:symbolDeltaMin
        managed object property"
    ::= { cfprApEtherLossStatsHistEntry 46 }

cfprApEtherLossStatsHistThresholded OBJECT-TYPE
    SYNTAX       CfprApEtherLossStatsHistThresholded
    MAX-ACCESS   read-only
    STATUS       current
    DESCRIPTION
        "Cisco Firepower ether:LossStatsHist:thresholded
        managed object property"
    ::= { cfprApEtherLossStatsHistEntry 47 }

cfprApEtherLossStatsHistTimeCollected OBJECT-TYPE
    SYNTAX       DateAndTime
    MAX-ACCESS   read-only
    STATUS       current
    DESCRIPTION
        "Cisco Firepower ether:LossStatsHist:timeCollected
        managed object property"
    ::= { cfprApEtherLossStatsHistEntry 48 }

cfprApEtherNiErrStatsTable OBJECT-TYPE
    SYNTAX           SEQUENCE OF CfprApEtherNiErrStatsEntry
    MAX-ACCESS       not-accessible
    STATUS           current
    DESCRIPTION
        "Cisco Firepower ether:NiErrStats managed object table"
    ::= { cfprApEtherObjects 12 }

cfprApEtherNiErrStatsEntry OBJECT-TYPE
    SYNTAX           CfprApEtherNiErrStatsEntry
    MAX-ACCESS       not-accessible
    STATUS           current
    DESCRIPTION
        "Entry for the cfprApEtherNiErrStatsTable table."
    INDEX { cfprApEtherNiErrStatsInstanceId }
    ::= { cfprApEtherNiErrStatsTable 1 }

CfprApEtherNiErrStatsEntry ::= SEQUENCE {
    cfprApEtherNiErrStatsInstanceId                                  CfprApManagedObjectId,
    cfprApEtherNiErrStatsDn                                          CfprApManagedObjectDn,
    cfprApEtherNiErrStatsRn                                          SnmpAdminString,
    cfprApEtherNiErrStatsCrc                                         Unsigned64,
    cfprApEtherNiErrStatsCrcDelta                                    Counter64,
    cfprApEtherNiErrStatsCrcDeltaAvg                                 Unsigned64,
    cfprApEtherNiErrStatsCrcDeltaMax                                 Unsigned64,
    cfprApEtherNiErrStatsCrcDeltaMin                                 Unsigned64,
    cfprApEtherNiErrStatsFrameTx                                     Unsigned64,
    cfprApEtherNiErrStatsFrameTxDelta                                Counter64,
    cfprApEtherNiErrStatsFrameTxDeltaAvg                             Unsigned64,
    cfprApEtherNiErrStatsFrameTxDeltaMax                             Unsigned64,
    cfprApEtherNiErrStatsFrameTxDeltaMin                             Unsigned64,
    cfprApEtherNiErrStatsInRange                                     Unsigned64,
    cfprApEtherNiErrStatsInRangeDelta                                Counter64,
    cfprApEtherNiErrStatsInRangeDeltaAvg                             Unsigned64,
    cfprApEtherNiErrStatsInRangeDeltaMax                             Unsigned64,
    cfprApEtherNiErrStatsInRangeDeltaMin                             Unsigned64,
    cfprApEtherNiErrStatsIntervals                                   Gauge32,
    cfprApEtherNiErrStatsSuspect                                     TruthValue,
    cfprApEtherNiErrStatsThresholded                                 CfprApEtherNiErrStatsThresholded,
    cfprApEtherNiErrStatsTimeCollected                               DateAndTime,
    cfprApEtherNiErrStatsTooLong                                     Unsigned64,
    cfprApEtherNiErrStatsTooLongDelta                                Counter64,
    cfprApEtherNiErrStatsTooLongDeltaAvg                             Unsigned64,
    cfprApEtherNiErrStatsTooLongDeltaMax                             Unsigned64,
    cfprApEtherNiErrStatsTooLongDeltaMin                             Unsigned64,
    cfprApEtherNiErrStatsTooShort                                    Unsigned64,
    cfprApEtherNiErrStatsTooShortDelta                               Counter64,
    cfprApEtherNiErrStatsTooShortDeltaAvg                            Unsigned64,
    cfprApEtherNiErrStatsTooShortDeltaMax                            Unsigned64,
    cfprApEtherNiErrStatsTooShortDeltaMin                            Unsigned64,
    cfprApEtherNiErrStatsUpdate                                      Gauge32
}

cfprApEtherNiErrStatsInstanceId OBJECT-TYPE
    SYNTAX       CfprApManagedObjectId
    MAX-ACCESS   not-accessible
    STATUS       current
    DESCRIPTION
        "Instance identifier of the managed object."
    ::= { cfprApEtherNiErrStatsEntry 1 }

cfprApEtherNiErrStatsDn OBJECT-TYPE
    SYNTAX       CfprApManagedObjectDn
    MAX-ACCESS   read-only
    STATUS       current
    DESCRIPTION
        "Cisco Firepower ether:NiErrStats:dn managed object property"
    ::= { cfprApEtherNiErrStatsEntry 2 }

cfprApEtherNiErrStatsRn OBJECT-TYPE
    SYNTAX       SnmpAdminString
    MAX-ACCESS   read-only
    STATUS       current
    DESCRIPTION
        "Cisco Firepower ether:NiErrStats:rn managed object property"
    ::= { cfprApEtherNiErrStatsEntry 3 }

cfprApEtherNiErrStatsCrc OBJECT-TYPE
    SYNTAX       Unsigned64
    MAX-ACCESS   read-only
    STATUS       current
    DESCRIPTION
        "Cisco Firepower ether:NiErrStats:crc managed object property"
    ::= { cfprApEtherNiErrStatsEntry 4 }

cfprApEtherNiErrStatsCrcDelta OBJECT-TYPE
    SYNTAX       Counter64
    MAX-ACCESS   read-only
    STATUS       current
    DESCRIPTION
        "Cisco Firepower ether:NiErrStats:crcDelta managed
        object property"
    ::= { cfprApEtherNiErrStatsEntry 5 }

cfprApEtherNiErrStatsCrcDeltaAvg OBJECT-TYPE
    SYNTAX       Unsigned64
    MAX-ACCESS   read-only
    STATUS       current
    DESCRIPTION
        "Cisco Firepower ether:NiErrStats:crcDeltaAvg managed
        object property"
    ::= { cfprApEtherNiErrStatsEntry 6 }

cfprApEtherNiErrStatsCrcDeltaMax OBJECT-TYPE
    SYNTAX       Unsigned64
    MAX-ACCESS   read-only
    STATUS       current
    DESCRIPTION
        "Cisco Firepower ether:NiErrStats:crcDeltaMax managed
        object property"
    ::= { cfprApEtherNiErrStatsEntry 7 }

cfprApEtherNiErrStatsCrcDeltaMin OBJECT-TYPE
    SYNTAX       Unsigned64
    MAX-ACCESS   read-only
    STATUS       current
    DESCRIPTION
        "Cisco Firepower ether:NiErrStats:crcDeltaMin managed
        object property"
    ::= { cfprApEtherNiErrStatsEntry 8 }

cfprApEtherNiErrStatsFrameTx OBJECT-TYPE
    SYNTAX       Unsigned64
    MAX-ACCESS   read-only
    STATUS       current
    DESCRIPTION
        "Cisco Firepower ether:NiErrStats:frameTx managed object property"
    ::= { cfprApEtherNiErrStatsEntry 9 }

cfprApEtherNiErrStatsFrameTxDelta OBJECT-TYPE
    SYNTAX       Counter64
    MAX-ACCESS   read-only
    STATUS       current
    DESCRIPTION
        "Cisco Firepower ether:NiErrStats:frameTxDelta
        managed object property"
    ::= { cfprApEtherNiErrStatsEntry 10 }

cfprApEtherNiErrStatsFrameTxDeltaAvg OBJECT-TYPE
    SYNTAX       Unsigned64
    MAX-ACCESS   read-only
    STATUS       current
    DESCRIPTION
        "Cisco Firepower ether:NiErrStats:frameTxDeltaAvg
        managed object property"
    ::= { cfprApEtherNiErrStatsEntry 11 }

cfprApEtherNiErrStatsFrameTxDeltaMax OBJECT-TYPE
    SYNTAX       Unsigned64
    MAX-ACCESS   read-only
    STATUS       current
    DESCRIPTION
        "Cisco Firepower ether:NiErrStats:frameTxDeltaMax
        managed object property"
    ::= { cfprApEtherNiErrStatsEntry 12 }

cfprApEtherNiErrStatsFrameTxDeltaMin OBJECT-TYPE
    SYNTAX       Unsigned64
    MAX-ACCESS   read-only
    STATUS       current
    DESCRIPTION
        "Cisco Firepower ether:NiErrStats:frameTxDeltaMin
        managed object property"
    ::= { cfprApEtherNiErrStatsEntry 13 }

cfprApEtherNiErrStatsInRange OBJECT-TYPE
    SYNTAX       Unsigned64
    MAX-ACCESS   read-only
    STATUS       current
    DESCRIPTION
        "Cisco Firepower ether:NiErrStats:inRange managed object property"
    ::= { cfprApEtherNiErrStatsEntry 14 }

cfprApEtherNiErrStatsInRangeDelta OBJECT-TYPE
    SYNTAX       Counter64
    MAX-ACCESS   read-only
    STATUS       current
    DESCRIPTION
        "Cisco Firepower ether:NiErrStats:inRangeDelta
        managed object property"
    ::= { cfprApEtherNiErrStatsEntry 15 }

cfprApEtherNiErrStatsInRangeDeltaAvg OBJECT-TYPE
    SYNTAX       Unsigned64
    MAX-ACCESS   read-only
    STATUS       current
    DESCRIPTION
        "Cisco Firepower ether:NiErrStats:inRangeDeltaAvg
        managed object property"
    ::= { cfprApEtherNiErrStatsEntry 16 }

cfprApEtherNiErrStatsInRangeDeltaMax OBJECT-TYPE
    SYNTAX       Unsigned64
    MAX-ACCESS   read-only
    STATUS       current
    DESCRIPTION
        "Cisco Firepower ether:NiErrStats:inRangeDeltaMax
        managed object property"
    ::= { cfprApEtherNiErrStatsEntry 17 }

cfprApEtherNiErrStatsInRangeDeltaMin OBJECT-TYPE
    SYNTAX       Unsigned64
    MAX-ACCESS   read-only
    STATUS       current
    DESCRIPTION
        "Cisco Firepower ether:NiErrStats:inRangeDeltaMin
        managed object property"
    ::= { cfprApEtherNiErrStatsEntry 18 }

cfprApEtherNiErrStatsIntervals OBJECT-TYPE
    SYNTAX       Gauge32
    MAX-ACCESS   read-only
    STATUS       current
    DESCRIPTION
        "Cisco Firepower ether:NiErrStats:intervals managed
        object property"
    ::= { cfprApEtherNiErrStatsEntry 19 }

cfprApEtherNiErrStatsSuspect OBJECT-TYPE
    SYNTAX       TruthValue
    MAX-ACCESS   read-only
    STATUS       current
    DESCRIPTION
        "Cisco Firepower ether:NiErrStats:suspect managed object property"
    ::= { cfprApEtherNiErrStatsEntry 20 }

cfprApEtherNiErrStatsThresholded OBJECT-TYPE
    SYNTAX       CfprApEtherNiErrStatsThresholded
    MAX-ACCESS   read-only
    STATUS       current
    DESCRIPTION
        "Cisco Firepower ether:NiErrStats:thresholded managed
        object property"
    ::= { cfprApEtherNiErrStatsEntry 21 }

cfprApEtherNiErrStatsTimeCollected OBJECT-TYPE
    SYNTAX       DateAndTime
    MAX-ACCESS   read-only
    STATUS       current
    DESCRIPTION
        "Cisco Firepower ether:NiErrStats:timeCollected
        managed object property"
    ::= { cfprApEtherNiErrStatsEntry 22 }

cfprApEtherNiErrStatsTooLong OBJECT-TYPE
    SYNTAX       Unsigned64
    MAX-ACCESS   read-only
    STATUS       current
    DESCRIPTION
        "Cisco Firepower ether:NiErrStats:tooLong managed object property"
    ::= { cfprApEtherNiErrStatsEntry 23 }

cfprApEtherNiErrStatsTooLongDelta OBJECT-TYPE
    SYNTAX       Counter64
    MAX-ACCESS   read-only
    STATUS       current
    DESCRIPTION
        "Cisco Firepower ether:NiErrStats:tooLongDelta
        managed object property"
    ::= { cfprApEtherNiErrStatsEntry 24 }

cfprApEtherNiErrStatsTooLongDeltaAvg OBJECT-TYPE
    SYNTAX       Unsigned64
    MAX-ACCESS   read-only
    STATUS       current
    DESCRIPTION
        "Cisco Firepower ether:NiErrStats:tooLongDeltaAvg
        managed object property"
    ::= { cfprApEtherNiErrStatsEntry 25 }

cfprApEtherNiErrStatsTooLongDeltaMax OBJECT-TYPE
    SYNTAX       Unsigned64
    MAX-ACCESS   read-only
    STATUS       current
    DESCRIPTION
        "Cisco Firepower ether:NiErrStats:tooLongDeltaMax
        managed object property"
    ::= { cfprApEtherNiErrStatsEntry 26 }

cfprApEtherNiErrStatsTooLongDeltaMin OBJECT-TYPE
    SYNTAX       Unsigned64
    MAX-ACCESS   read-only
    STATUS       current
    DESCRIPTION
        "Cisco Firepower ether:NiErrStats:tooLongDeltaMin
        managed object property"
    ::= { cfprApEtherNiErrStatsEntry 27 }

cfprApEtherNiErrStatsTooShort OBJECT-TYPE
    SYNTAX       Unsigned64
    MAX-ACCESS   read-only
    STATUS       current
    DESCRIPTION
        "Cisco Firepower ether:NiErrStats:tooShort managed
        object property"
    ::= { cfprApEtherNiErrStatsEntry 28 }

cfprApEtherNiErrStatsTooShortDelta OBJECT-TYPE
    SYNTAX       Counter64
    MAX-ACCESS   read-only
    STATUS       current
    DESCRIPTION
        "Cisco Firepower ether:NiErrStats:tooShortDelta
        managed object property"
    ::= { cfprApEtherNiErrStatsEntry 29 }

cfprApEtherNiErrStatsTooShortDeltaAvg OBJECT-TYPE
    SYNTAX       Unsigned64
    MAX-ACCESS   read-only
    STATUS       current
    DESCRIPTION
        "Cisco Firepower ether:NiErrStats:tooShortDeltaAvg
        managed object property"
    ::= { cfprApEtherNiErrStatsEntry 30 }

cfprApEtherNiErrStatsTooShortDeltaMax OBJECT-TYPE
    SYNTAX       Unsigned64
    MAX-ACCESS   read-only
    STATUS       current
    DESCRIPTION
        "Cisco Firepower ether:NiErrStats:tooShortDeltaMax
        managed object property"
    ::= { cfprApEtherNiErrStatsEntry 31 }

cfprApEtherNiErrStatsTooShortDeltaMin OBJECT-TYPE
    SYNTAX       Unsigned64
    MAX-ACCESS   read-only
    STATUS       current
    DESCRIPTION
        "Cisco Firepower ether:NiErrStats:tooShortDeltaMin
        managed object property"
    ::= { cfprApEtherNiErrStatsEntry 32 }

cfprApEtherNiErrStatsUpdate OBJECT-TYPE
    SYNTAX       Gauge32
    MAX-ACCESS   read-only
    STATUS       current
    DESCRIPTION
        "Cisco Firepower ether:NiErrStats:update managed object property"
    ::= { cfprApEtherNiErrStatsEntry 33 }

cfprApEtherNiErrStatsHistTable OBJECT-TYPE
    SYNTAX           SEQUENCE OF CfprApEtherNiErrStatsHistEntry
    MAX-ACCESS       not-accessible
    STATUS           current
    DESCRIPTION
        "Cisco Firepower ether:NiErrStatsHist managed object table"
    ::= { cfprApEtherObjects 13 }

cfprApEtherNiErrStatsHistEntry OBJECT-TYPE
    SYNTAX           CfprApEtherNiErrStatsHistEntry
    MAX-ACCESS       not-accessible
    STATUS           current
    DESCRIPTION
        "Entry for the cfprApEtherNiErrStatsHistTable table."
    INDEX { cfprApEtherNiErrStatsHistInstanceId }
    ::= { cfprApEtherNiErrStatsHistTable 1 }

CfprApEtherNiErrStatsHistEntry ::= SEQUENCE {
    cfprApEtherNiErrStatsHistInstanceId                              CfprApManagedObjectId,
    cfprApEtherNiErrStatsHistDn                                      CfprApManagedObjectDn,
    cfprApEtherNiErrStatsHistRn                                      SnmpAdminString,
    cfprApEtherNiErrStatsHistCrc                                     Unsigned64,
    cfprApEtherNiErrStatsHistCrcDelta                                Unsigned64,
    cfprApEtherNiErrStatsHistCrcDeltaAvg                             Unsigned64,
    cfprApEtherNiErrStatsHistCrcDeltaMax                             Unsigned64,
    cfprApEtherNiErrStatsHistCrcDeltaMin                             Unsigned64,
    cfprApEtherNiErrStatsHistFrameTx                                 Unsigned64,
    cfprApEtherNiErrStatsHistFrameTxDelta                            Unsigned64,
    cfprApEtherNiErrStatsHistFrameTxDeltaAvg                         Unsigned64,
    cfprApEtherNiErrStatsHistFrameTxDeltaMax                         Unsigned64,
    cfprApEtherNiErrStatsHistFrameTxDeltaMin                         Unsigned64,
    cfprApEtherNiErrStatsHistId                                      Unsigned64,
    cfprApEtherNiErrStatsHistInRange                                 Unsigned64,
    cfprApEtherNiErrStatsHistInRangeDelta                            Unsigned64,
    cfprApEtherNiErrStatsHistInRangeDeltaAvg                         Unsigned64,
    cfprApEtherNiErrStatsHistInRangeDeltaMax                         Unsigned64,
    cfprApEtherNiErrStatsHistInRangeDeltaMin                         Unsigned64,
    cfprApEtherNiErrStatsHistMostRecent                              TruthValue,
    cfprApEtherNiErrStatsHistSuspect                                 TruthValue,
    cfprApEtherNiErrStatsHistThresholded                             CfprApEtherNiErrStatsHistThresholded,
    cfprApEtherNiErrStatsHistTimeCollected                           DateAndTime,
    cfprApEtherNiErrStatsHistTooLong                                 Unsigned64,
    cfprApEtherNiErrStatsHistTooLongDelta                            Unsigned64,
    cfprApEtherNiErrStatsHistTooLongDeltaAvg                         Unsigned64,
    cfprApEtherNiErrStatsHistTooLongDeltaMax                         Unsigned64,
    cfprApEtherNiErrStatsHistTooLongDeltaMin                         Unsigned64,
    cfprApEtherNiErrStatsHistTooShort                                Unsigned64,
    cfprApEtherNiErrStatsHistTooShortDelta                           Unsigned64,
    cfprApEtherNiErrStatsHistTooShortDeltaAvg                        Unsigned64,
    cfprApEtherNiErrStatsHistTooShortDeltaMax                        Unsigned64,
    cfprApEtherNiErrStatsHistTooShortDeltaMin                        Unsigned64
}

cfprApEtherNiErrStatsHistInstanceId OBJECT-TYPE
    SYNTAX       CfprApManagedObjectId
    MAX-ACCESS   not-accessible
    STATUS       current
    DESCRIPTION
        "Instance identifier of the managed object."
    ::= { cfprApEtherNiErrStatsHistEntry 1 }

cfprApEtherNiErrStatsHistDn OBJECT-TYPE
    SYNTAX       CfprApManagedObjectDn
    MAX-ACCESS   read-only
    STATUS       current
    DESCRIPTION
        "Cisco Firepower ether:NiErrStatsHist:dn managed object property"
    ::= { cfprApEtherNiErrStatsHistEntry 2 }

cfprApEtherNiErrStatsHistRn OBJECT-TYPE
    SYNTAX       SnmpAdminString
    MAX-ACCESS   read-only
    STATUS       current
    DESCRIPTION
        "Cisco Firepower ether:NiErrStatsHist:rn managed object property"
    ::= { cfprApEtherNiErrStatsHistEntry 3 }

cfprApEtherNiErrStatsHistCrc OBJECT-TYPE
    SYNTAX       Unsigned64
    MAX-ACCESS   read-only
    STATUS       current
    DESCRIPTION
        "Cisco Firepower ether:NiErrStatsHist:crc managed object property"
    ::= { cfprApEtherNiErrStatsHistEntry 4 }

cfprApEtherNiErrStatsHistCrcDelta OBJECT-TYPE
    SYNTAX       Unsigned64
    MAX-ACCESS   read-only
    STATUS       current
    DESCRIPTION
        "Cisco Firepower ether:NiErrStatsHist:crcDelta
        managed object property"
    ::= { cfprApEtherNiErrStatsHistEntry 5 }

cfprApEtherNiErrStatsHistCrcDeltaAvg OBJECT-TYPE
    SYNTAX       Unsigned64
    MAX-ACCESS   read-only
    STATUS       current
    DESCRIPTION
        "Cisco Firepower ether:NiErrStatsHist:crcDeltaAvg
        managed object property"
    ::= { cfprApEtherNiErrStatsHistEntry 6 }

cfprApEtherNiErrStatsHistCrcDeltaMax OBJECT-TYPE
    SYNTAX       Unsigned64
    MAX-ACCESS   read-only
    STATUS       current
    DESCRIPTION
        "Cisco Firepower ether:NiErrStatsHist:crcDeltaMax
        managed object property"
    ::= { cfprApEtherNiErrStatsHistEntry 7 }

cfprApEtherNiErrStatsHistCrcDeltaMin OBJECT-TYPE
    SYNTAX       Unsigned64
    MAX-ACCESS   read-only
    STATUS       current
    DESCRIPTION
        "Cisco Firepower ether:NiErrStatsHist:crcDeltaMin
        managed object property"
    ::= { cfprApEtherNiErrStatsHistEntry 8 }

cfprApEtherNiErrStatsHistFrameTx OBJECT-TYPE
    SYNTAX       Unsigned64
    MAX-ACCESS   read-only
    STATUS       current
    DESCRIPTION
        "Cisco Firepower ether:NiErrStatsHist:frameTx managed
        object property"
    ::= { cfprApEtherNiErrStatsHistEntry 9 }

cfprApEtherNiErrStatsHistFrameTxDelta OBJECT-TYPE
    SYNTAX       Unsigned64
    MAX-ACCESS   read-only
    STATUS       current
    DESCRIPTION
        "Cisco Firepower ether:NiErrStatsHist:frameTxDelta
        managed object property"
    ::= { cfprApEtherNiErrStatsHistEntry 10 }

cfprApEtherNiErrStatsHistFrameTxDeltaAvg OBJECT-TYPE
    SYNTAX       Unsigned64
    MAX-ACCESS   read-only
    STATUS       current
    DESCRIPTION
        "Cisco Firepower ether:NiErrStatsHist:frameTxDeltaAvg
        managed object property"
    ::= { cfprApEtherNiErrStatsHistEntry 11 }

cfprApEtherNiErrStatsHistFrameTxDeltaMax OBJECT-TYPE
    SYNTAX       Unsigned64
    MAX-ACCESS   read-only
    STATUS       current
    DESCRIPTION
        "Cisco Firepower ether:NiErrStatsHist:frameTxDeltaMax
        managed object property"
    ::= { cfprApEtherNiErrStatsHistEntry 12 }

cfprApEtherNiErrStatsHistFrameTxDeltaMin OBJECT-TYPE
    SYNTAX       Unsigned64
    MAX-ACCESS   read-only
    STATUS       current
    DESCRIPTION
        "Cisco Firepower ether:NiErrStatsHist:frameTxDeltaMin
        managed object property"
    ::= { cfprApEtherNiErrStatsHistEntry 13 }

cfprApEtherNiErrStatsHistId OBJECT-TYPE
    SYNTAX       Unsigned64
    MAX-ACCESS   read-only
    STATUS       current
    DESCRIPTION
        "Cisco Firepower ether:NiErrStatsHist:id managed object property"
    ::= { cfprApEtherNiErrStatsHistEntry 14 }

cfprApEtherNiErrStatsHistInRange OBJECT-TYPE
    SYNTAX       Unsigned64
    MAX-ACCESS   read-only
    STATUS       current
    DESCRIPTION
        "Cisco Firepower ether:NiErrStatsHist:inRange managed
        object property"
    ::= { cfprApEtherNiErrStatsHistEntry 15 }

cfprApEtherNiErrStatsHistInRangeDelta OBJECT-TYPE
    SYNTAX       Unsigned64
    MAX-ACCESS   read-only
    STATUS       current
    DESCRIPTION
        "Cisco Firepower ether:NiErrStatsHist:inRangeDelta
        managed object property"
    ::= { cfprApEtherNiErrStatsHistEntry 16 }

cfprApEtherNiErrStatsHistInRangeDeltaAvg OBJECT-TYPE
    SYNTAX       Unsigned64
    MAX-ACCESS   read-only
    STATUS       current
    DESCRIPTION
        "Cisco Firepower ether:NiErrStatsHist:inRangeDeltaAvg
        managed object property"
    ::= { cfprApEtherNiErrStatsHistEntry 17 }

cfprApEtherNiErrStatsHistInRangeDeltaMax OBJECT-TYPE
    SYNTAX       Unsigned64
    MAX-ACCESS   read-only
    STATUS       current
    DESCRIPTION
        "Cisco Firepower ether:NiErrStatsHist:inRangeDeltaMax
        managed object property"
    ::= { cfprApEtherNiErrStatsHistEntry 18 }

cfprApEtherNiErrStatsHistInRangeDeltaMin OBJECT-TYPE
    SYNTAX       Unsigned64
    MAX-ACCESS   read-only
    STATUS       current
    DESCRIPTION
        "Cisco Firepower ether:NiErrStatsHist:inRangeDeltaMin
        managed object property"
    ::= { cfprApEtherNiErrStatsHistEntry 19 }

cfprApEtherNiErrStatsHistMostRecent OBJECT-TYPE
    SYNTAX       TruthValue
    MAX-ACCESS   read-only
    STATUS       current
    DESCRIPTION
        "Cisco Firepower ether:NiErrStatsHist:mostRecent
        managed object property"
    ::= { cfprApEtherNiErrStatsHistEntry 20 }

cfprApEtherNiErrStatsHistSuspect OBJECT-TYPE
    SYNTAX       TruthValue
    MAX-ACCESS   read-only
    STATUS       current
    DESCRIPTION
        "Cisco Firepower ether:NiErrStatsHist:suspect managed
        object property"
    ::= { cfprApEtherNiErrStatsHistEntry 21 }

cfprApEtherNiErrStatsHistThresholded OBJECT-TYPE
    SYNTAX       CfprApEtherNiErrStatsHistThresholded
    MAX-ACCESS   read-only
    STATUS       current
    DESCRIPTION
        "Cisco Firepower ether:NiErrStatsHist:thresholded
        managed object property"
    ::= { cfprApEtherNiErrStatsHistEntry 22 }

cfprApEtherNiErrStatsHistTimeCollected OBJECT-TYPE
    SYNTAX       DateAndTime
    MAX-ACCESS   read-only
    STATUS       current
    DESCRIPTION
        "Cisco Firepower ether:NiErrStatsHist:timeCollected
        managed object property"
    ::= { cfprApEtherNiErrStatsHistEntry 23 }

cfprApEtherNiErrStatsHistTooLong OBJECT-TYPE
    SYNTAX       Unsigned64
    MAX-ACCESS   read-only
    STATUS       current
    DESCRIPTION
        "Cisco Firepower ether:NiErrStatsHist:tooLong managed
        object property"
    ::= { cfprApEtherNiErrStatsHistEntry 24 }

cfprApEtherNiErrStatsHistTooLongDelta OBJECT-TYPE
    SYNTAX       Unsigned64
    MAX-ACCESS   read-only
    STATUS       current
    DESCRIPTION
        "Cisco Firepower ether:NiErrStatsHist:tooLongDelta
        managed object property"
    ::= { cfprApEtherNiErrStatsHistEntry 25 }

cfprApEtherNiErrStatsHistTooLongDeltaAvg OBJECT-TYPE
    SYNTAX       Unsigned64
    MAX-ACCESS   read-only
    STATUS       current
    DESCRIPTION
        "Cisco Firepower ether:NiErrStatsHist:tooLongDeltaAvg
        managed object property"
    ::= { cfprApEtherNiErrStatsHistEntry 26 }

cfprApEtherNiErrStatsHistTooLongDeltaMax OBJECT-TYPE
    SYNTAX       Unsigned64
    MAX-ACCESS   read-only
    STATUS       current
    DESCRIPTION
        "Cisco Firepower ether:NiErrStatsHist:tooLongDeltaMax
        managed object property"
    ::= { cfprApEtherNiErrStatsHistEntry 27 }

cfprApEtherNiErrStatsHistTooLongDeltaMin OBJECT-TYPE
    SYNTAX       Unsigned64
    MAX-ACCESS   read-only
    STATUS       current
    DESCRIPTION
        "Cisco Firepower ether:NiErrStatsHist:tooLongDeltaMin
        managed object property"
    ::= { cfprApEtherNiErrStatsHistEntry 28 }

cfprApEtherNiErrStatsHistTooShort OBJECT-TYPE
    SYNTAX       Unsigned64
    MAX-ACCESS   read-only
    STATUS       current
    DESCRIPTION
        "Cisco Firepower ether:NiErrStatsHist:tooShort
        managed object property"
    ::= { cfprApEtherNiErrStatsHistEntry 29 }

cfprApEtherNiErrStatsHistTooShortDelta OBJECT-TYPE
    SYNTAX       Unsigned64
    MAX-ACCESS   read-only
    STATUS       current
    DESCRIPTION
        "Cisco Firepower ether:NiErrStatsHist:tooShortDelta
        managed object property"
    ::= { cfprApEtherNiErrStatsHistEntry 30 }

cfprApEtherNiErrStatsHistTooShortDeltaAvg OBJECT-TYPE
    SYNTAX       Unsigned64
    MAX-ACCESS   read-only
    STATUS       current
    DESCRIPTION
        "Cisco Firepower ether:NiErrStatsHist:tooShortDeltaAvg
        managed object property"
    ::= { cfprApEtherNiErrStatsHistEntry 31 }

cfprApEtherNiErrStatsHistTooShortDeltaMax OBJECT-TYPE
    SYNTAX       Unsigned64
    MAX-ACCESS   read-only
    STATUS       current
    DESCRIPTION
        "Cisco Firepower ether:NiErrStatsHist:tooShortDeltaMax
        managed object property"
    ::= { cfprApEtherNiErrStatsHistEntry 32 }

cfprApEtherNiErrStatsHistTooShortDeltaMin OBJECT-TYPE
    SYNTAX       Unsigned64
    MAX-ACCESS   read-only
    STATUS       current
    DESCRIPTION
        "Cisco Firepower ether:NiErrStatsHist:tooShortDeltaMin
        managed object property"
    ::= { cfprApEtherNiErrStatsHistEntry 33 }

cfprApEtherNicIfConfigTable OBJECT-TYPE
    SYNTAX           SEQUENCE OF CfprApEtherNicIfConfigEntry
    MAX-ACCESS       not-accessible
    STATUS           current
    DESCRIPTION
        "Cisco Firepower ether:NicIfConfig managed object table"
    ::= { cfprApEtherObjects 14 }

cfprApEtherNicIfConfigEntry OBJECT-TYPE
    SYNTAX           CfprApEtherNicIfConfigEntry
    MAX-ACCESS       not-accessible
    STATUS           current
    DESCRIPTION
        "Entry for the cfprApEtherNicIfConfigTable table."
    INDEX { cfprApEtherNicIfConfigInstanceId }
    ::= { cfprApEtherNicIfConfigTable 1 }

CfprApEtherNicIfConfigEntry ::= SEQUENCE {
    cfprApEtherNicIfConfigInstanceId                                 CfprApManagedObjectId,
    cfprApEtherNicIfConfigDn                                         CfprApManagedObjectDn,
    cfprApEtherNicIfConfigRn                                         SnmpAdminString
}

cfprApEtherNicIfConfigInstanceId OBJECT-TYPE
    SYNTAX       CfprApManagedObjectId
    MAX-ACCESS   not-accessible
    STATUS       current
    DESCRIPTION
        "Instance identifier of the managed object."
    ::= { cfprApEtherNicIfConfigEntry 1 }

cfprApEtherNicIfConfigDn OBJECT-TYPE
    SYNTAX       CfprApManagedObjectDn
    MAX-ACCESS   read-only
    STATUS       current
    DESCRIPTION
        "Cisco Firepower ether:NicIfConfig:dn managed object property"
    ::= { cfprApEtherNicIfConfigEntry 2 }

cfprApEtherNicIfConfigRn OBJECT-TYPE
    SYNTAX       SnmpAdminString
    MAX-ACCESS   read-only
    STATUS       current
    DESCRIPTION
        "Cisco Firepower ether:NicIfConfig:rn managed object property"
    ::= { cfprApEtherNicIfConfigEntry 3 }

cfprApEtherPIoTable OBJECT-TYPE
    SYNTAX           SEQUENCE OF CfprApEtherPIoEntry
    MAX-ACCESS       not-accessible
    STATUS           current
    DESCRIPTION
        "Cisco Firepower ether:PIo managed object table"
    ::= { cfprApEtherObjects 15 }

cfprApEtherPIoEntry OBJECT-TYPE
    SYNTAX           CfprApEtherPIoEntry
    MAX-ACCESS       not-accessible
    STATUS           current
    DESCRIPTION
        "Entry for the cfprApEtherPIoTable table."
    INDEX { cfprApEtherPIoInstanceId }
    ::= { cfprApEtherPIoTable 1 }

CfprApEtherPIoEntry ::= SEQUENCE {
    cfprApEtherPIoInstanceId                                         CfprApManagedObjectId,
    cfprApEtherPIoDn                                                 CfprApManagedObjectDn,
    cfprApEtherPIoRn                                                 SnmpAdminString,
    cfprApEtherPIoAdminState                                         CfprApFabricAdminState,
    cfprApEtherPIoAdminTransport                                     CfprApNetworkTransport,
    cfprApEtherPIoAggrPortId                                         Gauge32,
    cfprApEtherPIoChassisId                                          Gauge32,
    cfprApEtherPIoEncap                                              CfprApPortEncap,
    cfprApEtherPIoEpDn                                               SnmpAdminString,
    cfprApEtherPIoFltAggr                                            Unsigned64,
    cfprApEtherPIoFsmDescr                                           SnmpAdminString,
    cfprApEtherPIoFsmPrev                                            SnmpAdminString,
    cfprApEtherPIoFsmProgr                                           Gauge32,
    cfprApEtherPIoFsmRmtInvErrCode                                   Gauge32,
    cfprApEtherPIoFsmRmtInvErrDescr                                  SnmpAdminString,
    cfprApEtherPIoFsmRmtInvRslt                                      CfprApConditionRemoteInvRslt,
    cfprApEtherPIoFsmStageDescr                                      SnmpAdminString,
    cfprApEtherPIoFsmStamp                                           DateAndTime,
    cfprApEtherPIoFsmStatus                                          SnmpAdminString,
    cfprApEtherPIoFsmTry                                             Gauge32,
    cfprApEtherPIoFtwPhyDn                                           SnmpAdminString,
    cfprApEtherPIoIfRole                                             CfprApNetworkPortRole,
    cfprApEtherPIoIfType                                             CfprApNetworkPhysEpIfType,
    cfprApEtherPIoIsPortChannelMember                                TruthValue,
    cfprApEtherPIoLc                                                 CfprApFsmLifecycle,
    cfprApEtherPIoLicGP                                              Unsigned64,
    cfprApEtherPIoLicState                                           CfprApLicenseState,
    cfprApEtherPIoLocale                                             CfprApNetworkLocale,
    cfprApEtherPIoMac                                                MacAddress,
    cfprApEtherPIoMode                                               CfprApPortMode,
    cfprApEtherPIoModel                                              SnmpAdminString,
    cfprApEtherPIoName                                               SnmpAdminString,
    cfprApEtherPIoOperDuplex                                         CfprApPortDuplex,
    cfprApEtherPIoOperSpeed                                          CfprApPortEthSpeed,
    cfprApEtherPIoOperState                                          CfprApNetworkPortOperState,
    cfprApEtherPIoPeerAggrPortId                                     Gauge32,
    cfprApEtherPIoPeerChassisId                                      Gauge32,
    cfprApEtherPIoPeerDn                                             SnmpAdminString,
    cfprApEtherPIoPeerPortId                                         Gauge32,
    cfprApEtherPIoPeerSlotId                                         Gauge32,
    cfprApEtherPIoPortId                                             Gauge32,
    cfprApEtherPIoRevision                                           SnmpAdminString,
    cfprApEtherPIoSerial                                             SnmpAdminString,
    cfprApEtherPIoSlotId                                             Gauge32,
    cfprApEtherPIoStateQual                                          SnmpAdminString,
    cfprApEtherPIoSwitchId                                           CfprApNetworkSwitchId,
    cfprApEtherPIoTransport                                          CfprApNetworkTransport,
    cfprApEtherPIoTs                                                 DateAndTime,
    cfprApEtherPIoType                                               CfprApNetworkConnectionType,
    cfprApEtherPIoUnifiedPort                                        TruthValue,
    cfprApEtherPIoUsrLbl                                             SnmpAdminString,
    cfprApEtherPIoVendor                                             SnmpAdminString,
    cfprApEtherPIoXcvrType                                           CfprApEquipmentXcvrType
}

cfprApEtherPIoInstanceId OBJECT-TYPE
    SYNTAX       CfprApManagedObjectId
    MAX-ACCESS   not-accessible
    STATUS       current
    DESCRIPTION
        "Instance identifier of the managed object."
    ::= { cfprApEtherPIoEntry 1 }

cfprApEtherPIoDn OBJECT-TYPE
    SYNTAX       CfprApManagedObjectDn
    MAX-ACCESS   read-only
    STATUS       current
    DESCRIPTION
        "Cisco Firepower ether:PIo:dn managed object property"
    ::= { cfprApEtherPIoEntry 2 }

cfprApEtherPIoRn OBJECT-TYPE
    SYNTAX       SnmpAdminString
    MAX-ACCESS   read-only
    STATUS       current
    DESCRIPTION
        "Cisco Firepower ether:PIo:rn managed object property"
    ::= { cfprApEtherPIoEntry 3 }

cfprApEtherPIoAdminState OBJECT-TYPE
    SYNTAX       CfprApFabricAdminState
    MAX-ACCESS   read-only
    STATUS       current
    DESCRIPTION
        "Cisco Firepower ether:PIo:adminState managed object property"
    ::= { cfprApEtherPIoEntry 4 }

cfprApEtherPIoAdminTransport OBJECT-TYPE
    SYNTAX       CfprApNetworkTransport
    MAX-ACCESS   read-only
    STATUS       current
    DESCRIPTION
        "Cisco Firepower ether:PIo:adminTransport managed object property"
    ::= { cfprApEtherPIoEntry 5 }

cfprApEtherPIoAggrPortId OBJECT-TYPE
    SYNTAX       Gauge32
    MAX-ACCESS   read-only
    STATUS       current
    DESCRIPTION
        "Cisco Firepower ether:PIo:aggrPortId managed object property"
    ::= { cfprApEtherPIoEntry 6 }

cfprApEtherPIoChassisId OBJECT-TYPE
    SYNTAX       Gauge32
    MAX-ACCESS   read-only
    STATUS       current
    DESCRIPTION
        "Cisco Firepower ether:PIo:chassisId managed object property"
    ::= { cfprApEtherPIoEntry 7 }

cfprApEtherPIoEncap OBJECT-TYPE
    SYNTAX       CfprApPortEncap
    MAX-ACCESS   read-only
    STATUS       current
    DESCRIPTION
        "Cisco Firepower ether:PIo:encap managed object property"
    ::= { cfprApEtherPIoEntry 8 }

cfprApEtherPIoEpDn OBJECT-TYPE
    SYNTAX       SnmpAdminString
    MAX-ACCESS   read-only
    STATUS       current
    DESCRIPTION
        "Cisco Firepower ether:PIo:epDn managed object property"
    ::= { cfprApEtherPIoEntry 9 }

cfprApEtherPIoFltAggr OBJECT-TYPE
    SYNTAX       Unsigned64
    MAX-ACCESS   read-only
    STATUS       current
    DESCRIPTION
        "Cisco Firepower ether:PIo:fltAggr managed object property"
    ::= { cfprApEtherPIoEntry 10 }

cfprApEtherPIoFsmDescr OBJECT-TYPE
    SYNTAX       SnmpAdminString
    MAX-ACCESS   read-only
    STATUS       current
    DESCRIPTION
        "Cisco Firepower ether:PIo:fsmDescr managed object property"
    ::= { cfprApEtherPIoEntry 11 }

cfprApEtherPIoFsmPrev OBJECT-TYPE
    SYNTAX       SnmpAdminString
    MAX-ACCESS   read-only
    STATUS       current
    DESCRIPTION
        "Cisco Firepower ether:PIo:fsmPrev managed object property"
    ::= { cfprApEtherPIoEntry 12 }

cfprApEtherPIoFsmProgr OBJECT-TYPE
    SYNTAX       Gauge32
    MAX-ACCESS   read-only
    STATUS       current
    DESCRIPTION
        "Cisco Firepower ether:PIo:fsmProgr managed object property"
    ::= { cfprApEtherPIoEntry 13 }

cfprApEtherPIoFsmRmtInvErrCode OBJECT-TYPE
    SYNTAX       Gauge32
    MAX-ACCESS   read-only
    STATUS       current
    DESCRIPTION
        "Cisco Firepower ether:PIo:fsmRmtInvErrCode managed
        object property"
    ::= { cfprApEtherPIoEntry 14 }

cfprApEtherPIoFsmRmtInvErrDescr OBJECT-TYPE
    SYNTAX       SnmpAdminString
    MAX-ACCESS   read-only
    STATUS       current
    DESCRIPTION
        "Cisco Firepower ether:PIo:fsmRmtInvErrDescr managed
        object property"
    ::= { cfprApEtherPIoEntry 15 }

cfprApEtherPIoFsmRmtInvRslt OBJECT-TYPE
    SYNTAX       CfprApConditionRemoteInvRslt
    MAX-ACCESS   read-only
    STATUS       current
    DESCRIPTION
        "Cisco Firepower ether:PIo:fsmRmtInvRslt managed object property"
    ::= { cfprApEtherPIoEntry 16 }

cfprApEtherPIoFsmStageDescr OBJECT-TYPE
    SYNTAX       SnmpAdminString
    MAX-ACCESS   read-only
    STATUS       current
    DESCRIPTION
        "Cisco Firepower ether:PIo:fsmStageDescr managed object property"
    ::= { cfprApEtherPIoEntry 17 }

cfprApEtherPIoFsmStamp OBJECT-TYPE
    SYNTAX       DateAndTime
    MAX-ACCESS   read-only
    STATUS       current
    DESCRIPTION
        "Cisco Firepower ether:PIo:fsmStamp managed object property"
    ::= { cfprApEtherPIoEntry 18 }

cfprApEtherPIoFsmStatus OBJECT-TYPE
    SYNTAX       SnmpAdminString
    MAX-ACCESS   read-only
    STATUS       current
    DESCRIPTION
        "Cisco Firepower ether:PIo:fsmStatus managed object property"
    ::= { cfprApEtherPIoEntry 19 }

cfprApEtherPIoFsmTry OBJECT-TYPE
    SYNTAX       Gauge32
    MAX-ACCESS   read-only
    STATUS       current
    DESCRIPTION
        "Cisco Firepower ether:PIo:fsmTry managed object property"
    ::= { cfprApEtherPIoEntry 20 }

cfprApEtherPIoFtwPhyDn OBJECT-TYPE
    SYNTAX       SnmpAdminString
    MAX-ACCESS   read-only
    STATUS       current
    DESCRIPTION
        "Cisco Firepower ether:PIo:ftwPhyDn managed object property"
    ::= { cfprApEtherPIoEntry 21 }

cfprApEtherPIoIfRole OBJECT-TYPE
    SYNTAX       CfprApNetworkPortRole
    MAX-ACCESS   read-only
    STATUS       current
    DESCRIPTION
        "Cisco Firepower ether:PIo:ifRole managed object property"
    ::= { cfprApEtherPIoEntry 22 }

cfprApEtherPIoIfType OBJECT-TYPE
    SYNTAX       CfprApNetworkPhysEpIfType
    MAX-ACCESS   read-only
    STATUS       current
    DESCRIPTION
        "Cisco Firepower ether:PIo:ifType managed object property"
    ::= { cfprApEtherPIoEntry 23 }

cfprApEtherPIoIsPortChannelMember OBJECT-TYPE
    SYNTAX       TruthValue
    MAX-ACCESS   read-only
    STATUS       current
    DESCRIPTION
        "Cisco Firepower ether:PIo:isPortChannelMember
        managed object property"
    ::= { cfprApEtherPIoEntry 24 }

cfprApEtherPIoLc OBJECT-TYPE
    SYNTAX       CfprApFsmLifecycle
    MAX-ACCESS   read-only
    STATUS       current
    DESCRIPTION
        "Cisco Firepower ether:PIo:lc managed object property"
    ::= { cfprApEtherPIoEntry 25 }

cfprApEtherPIoLicGP OBJECT-TYPE
    SYNTAX       Unsigned64
    MAX-ACCESS   read-only
    STATUS       current
    DESCRIPTION
        "Cisco Firepower ether:PIo:licGP managed object property"
    ::= { cfprApEtherPIoEntry 26 }

cfprApEtherPIoLicState OBJECT-TYPE
    SYNTAX       CfprApLicenseState
    MAX-ACCESS   read-only
    STATUS       current
    DESCRIPTION
        "Cisco Firepower ether:PIo:licState managed object property"
    ::= { cfprApEtherPIoEntry 27 }

cfprApEtherPIoLocale OBJECT-TYPE
    SYNTAX       CfprApNetworkLocale
    MAX-ACCESS   read-only
    STATUS       current
    DESCRIPTION
        "Cisco Firepower ether:PIo:locale managed object property"
    ::= { cfprApEtherPIoEntry 28 }

cfprApEtherPIoMac OBJECT-TYPE
    SYNTAX       MacAddress
    MAX-ACCESS   read-only
    STATUS       current
    DESCRIPTION
        "Cisco Firepower ether:PIo:mac managed object property"
    ::= { cfprApEtherPIoEntry 29 }

cfprApEtherPIoMode OBJECT-TYPE
    SYNTAX       CfprApPortMode
    MAX-ACCESS   read-only
    STATUS       current
    DESCRIPTION
        "Cisco Firepower ether:PIo:mode managed object property"
    ::= { cfprApEtherPIoEntry 30 }

cfprApEtherPIoModel OBJECT-TYPE
    SYNTAX       SnmpAdminString
    MAX-ACCESS   read-only
    STATUS       current
    DESCRIPTION
        "Cisco Firepower ether:PIo:model managed object property"
    ::= { cfprApEtherPIoEntry 31 }

cfprApEtherPIoName OBJECT-TYPE
    SYNTAX       SnmpAdminString
    MAX-ACCESS   read-only
    STATUS       current
    DESCRIPTION
        "Cisco Firepower ether:PIo:name managed object property"
    ::= { cfprApEtherPIoEntry 32 }

cfprApEtherPIoOperDuplex OBJECT-TYPE
    SYNTAX       CfprApPortDuplex
    MAX-ACCESS   read-only
    STATUS       current
    DESCRIPTION
        "Cisco Firepower ether:PIo:operDuplex managed object property"
    ::= { cfprApEtherPIoEntry 33 }

cfprApEtherPIoOperSpeed OBJECT-TYPE
    SYNTAX       CfprApPortEthSpeed
    MAX-ACCESS   read-only
    STATUS       current
    DESCRIPTION
        "Cisco Firepower ether:PIo:operSpeed managed object property"
    ::= { cfprApEtherPIoEntry 34 }

cfprApEtherPIoOperState OBJECT-TYPE
    SYNTAX       CfprApNetworkPortOperState
    MAX-ACCESS   read-only
    STATUS       current
    DESCRIPTION
        "Cisco Firepower ether:PIo:operState managed object property"
    ::= { cfprApEtherPIoEntry 35 }

cfprApEtherPIoPeerAggrPortId OBJECT-TYPE
    SYNTAX       Gauge32
    MAX-ACCESS   read-only
    STATUS       current
    DESCRIPTION
        "Cisco Firepower ether:PIo:peerAggrPortId managed object property"
    ::= { cfprApEtherPIoEntry 36 }

cfprApEtherPIoPeerChassisId OBJECT-TYPE
    SYNTAX       Gauge32
    MAX-ACCESS   read-only
    STATUS       current
    DESCRIPTION
        "Cisco Firepower ether:PIo:peerChassisId managed object property"
    ::= { cfprApEtherPIoEntry 37 }

cfprApEtherPIoPeerDn OBJECT-TYPE
    SYNTAX       SnmpAdminString
    MAX-ACCESS   read-only
    STATUS       current
    DESCRIPTION
        "Cisco Firepower ether:PIo:peerDn managed object property"
    ::= { cfprApEtherPIoEntry 38 }

cfprApEtherPIoPeerPortId OBJECT-TYPE
    SYNTAX       Gauge32
    MAX-ACCESS   read-only
    STATUS       current
    DESCRIPTION
        "Cisco Firepower ether:PIo:peerPortId managed object property"
    ::= { cfprApEtherPIoEntry 39 }

cfprApEtherPIoPeerSlotId OBJECT-TYPE
    SYNTAX       Gauge32
    MAX-ACCESS   read-only
    STATUS       current
    DESCRIPTION
        "Cisco Firepower ether:PIo:peerSlotId managed object property"
    ::= { cfprApEtherPIoEntry 40 }

cfprApEtherPIoPortId OBJECT-TYPE
    SYNTAX       Gauge32
    MAX-ACCESS   read-only
    STATUS       current
    DESCRIPTION
        "Cisco Firepower ether:PIo:portId managed object property"
    ::= { cfprApEtherPIoEntry 41 }

cfprApEtherPIoRevision OBJECT-TYPE
    SYNTAX       SnmpAdminString
    MAX-ACCESS   read-only
    STATUS       current
    DESCRIPTION
        "Cisco Firepower ether:PIo:revision managed object property"
    ::= { cfprApEtherPIoEntry 42 }

cfprApEtherPIoSerial OBJECT-TYPE
    SYNTAX       SnmpAdminString
    MAX-ACCESS   read-only
    STATUS       current
    DESCRIPTION
        "Cisco Firepower ether:PIo:serial managed object property"
    ::= { cfprApEtherPIoEntry 43 }

cfprApEtherPIoSlotId OBJECT-TYPE
    SYNTAX       Gauge32
    MAX-ACCESS   read-only
    STATUS       current
    DESCRIPTION
        "Cisco Firepower ether:PIo:slotId managed object property"
    ::= { cfprApEtherPIoEntry 44 }

cfprApEtherPIoStateQual OBJECT-TYPE
    SYNTAX       SnmpAdminString
    MAX-ACCESS   read-only
    STATUS       current
    DESCRIPTION
        "Cisco Firepower ether:PIo:stateQual managed object property"
    ::= { cfprApEtherPIoEntry 45 }

cfprApEtherPIoSwitchId OBJECT-TYPE
    SYNTAX       CfprApNetworkSwitchId
    MAX-ACCESS   read-only
    STATUS       current
    DESCRIPTION
        "Cisco Firepower ether:PIo:switchId managed object property"
    ::= { cfprApEtherPIoEntry 46 }

cfprApEtherPIoTransport OBJECT-TYPE
    SYNTAX       CfprApNetworkTransport
    MAX-ACCESS   read-only
    STATUS       current
    DESCRIPTION
        "Cisco Firepower ether:PIo:transport managed object property"
    ::= { cfprApEtherPIoEntry 47 }

cfprApEtherPIoTs OBJECT-TYPE
    SYNTAX       DateAndTime
    MAX-ACCESS   read-only
    STATUS       current
    DESCRIPTION
        "Cisco Firepower ether:PIo:ts managed object property"
    ::= { cfprApEtherPIoEntry 48 }

cfprApEtherPIoType OBJECT-TYPE
    SYNTAX       CfprApNetworkConnectionType
    MAX-ACCESS   read-only
    STATUS       current
    DESCRIPTION
        "Cisco Firepower ether:PIo:type managed object property"
    ::= { cfprApEtherPIoEntry 49 }

cfprApEtherPIoUnifiedPort OBJECT-TYPE
    SYNTAX       TruthValue
    MAX-ACCESS   read-only
    STATUS       current
    DESCRIPTION
        "Cisco Firepower ether:PIo:unifiedPort managed object property"
    ::= { cfprApEtherPIoEntry 50 }

cfprApEtherPIoUsrLbl OBJECT-TYPE
    SYNTAX       SnmpAdminString
    MAX-ACCESS   read-only
    STATUS       current
    DESCRIPTION
        "Cisco Firepower ether:PIo:usrLbl managed object property"
    ::= { cfprApEtherPIoEntry 51 }

cfprApEtherPIoVendor OBJECT-TYPE
    SYNTAX       SnmpAdminString
    MAX-ACCESS   read-only
    STATUS       current
    DESCRIPTION
        "Cisco Firepower ether:PIo:vendor managed object property"
    ::= { cfprApEtherPIoEntry 52 }

cfprApEtherPIoXcvrType OBJECT-TYPE
    SYNTAX       CfprApEquipmentXcvrType
    MAX-ACCESS   read-only
    STATUS       current
    DESCRIPTION
        "Cisco Firepower ether:PIo:xcvrType managed object property"
    ::= { cfprApEtherPIoEntry 53 }

cfprApEtherPIoEndPointTable OBJECT-TYPE
    SYNTAX           SEQUENCE OF CfprApEtherPIoEndPointEntry
    MAX-ACCESS       not-accessible
    STATUS           current
    DESCRIPTION
        "Cisco Firepower ether:PIoEndPoint managed object table"
    ::= { cfprApEtherObjects 16 }

cfprApEtherPIoEndPointEntry OBJECT-TYPE
    SYNTAX           CfprApEtherPIoEndPointEntry
    MAX-ACCESS       not-accessible
    STATUS           current
    DESCRIPTION
        "Entry for the cfprApEtherPIoEndPointTable table."
    INDEX { cfprApEtherPIoEndPointInstanceId }
    ::= { cfprApEtherPIoEndPointTable 1 }

CfprApEtherPIoEndPointEntry ::= SEQUENCE {
    cfprApEtherPIoEndPointInstanceId                                 CfprApManagedObjectId,
    cfprApEtherPIoEndPointDn                                         CfprApManagedObjectDn,
    cfprApEtherPIoEndPointRn                                         SnmpAdminString,
    cfprApEtherPIoEndPointEndPointDn                                 SnmpAdminString,
    cfprApEtherPIoEndPointEpCloudType                                CfprApEtherCloudType,
    cfprApEtherPIoEndPointUsrLbl                                     SnmpAdminString
}

cfprApEtherPIoEndPointInstanceId OBJECT-TYPE
    SYNTAX       CfprApManagedObjectId
    MAX-ACCESS   not-accessible
    STATUS       current
    DESCRIPTION
        "Instance identifier of the managed object."
    ::= { cfprApEtherPIoEndPointEntry 1 }

cfprApEtherPIoEndPointDn OBJECT-TYPE
    SYNTAX       CfprApManagedObjectDn
    MAX-ACCESS   read-only
    STATUS       current
    DESCRIPTION
        "Cisco Firepower ether:PIoEndPoint:dn managed object property"
    ::= { cfprApEtherPIoEndPointEntry 2 }

cfprApEtherPIoEndPointRn OBJECT-TYPE
    SYNTAX       SnmpAdminString
    MAX-ACCESS   read-only
    STATUS       current
    DESCRIPTION
        "Cisco Firepower ether:PIoEndPoint:rn managed object property"
    ::= { cfprApEtherPIoEndPointEntry 3 }

cfprApEtherPIoEndPointEndPointDn OBJECT-TYPE
    SYNTAX       SnmpAdminString
    MAX-ACCESS   read-only
    STATUS       current
    DESCRIPTION
        "Cisco Firepower ether:PIoEndPoint:EndPointDn managed
        object property"
    ::= { cfprApEtherPIoEndPointEntry 4 }

cfprApEtherPIoEndPointEpCloudType OBJECT-TYPE
    SYNTAX       CfprApEtherCloudType
    MAX-ACCESS   read-only
    STATUS       current
    DESCRIPTION
        "Cisco Firepower ether:PIoEndPoint:epCloudType
        managed object property"
    ::= { cfprApEtherPIoEndPointEntry 5 }

cfprApEtherPIoEndPointUsrLbl OBJECT-TYPE
    SYNTAX       SnmpAdminString
    MAX-ACCESS   read-only
    STATUS       current
    DESCRIPTION
        "Cisco Firepower ether:PIoEndPoint:usrLbl managed object property"
    ::= { cfprApEtherPIoEndPointEntry 6 }

cfprApEtherPIoFsmTable OBJECT-TYPE
    SYNTAX           SEQUENCE OF CfprApEtherPIoFsmEntry
    MAX-ACCESS       not-accessible
    STATUS           current
    DESCRIPTION
        "Cisco Firepower ether:PIoFsm managed object table"
    ::= { cfprApEtherObjects 17 }

cfprApEtherPIoFsmEntry OBJECT-TYPE
    SYNTAX           CfprApEtherPIoFsmEntry
    MAX-ACCESS       not-accessible
    STATUS           current
    DESCRIPTION
        "Entry for the cfprApEtherPIoFsmTable table."
    INDEX { cfprApEtherPIoFsmInstanceId }
    ::= { cfprApEtherPIoFsmTable 1 }

CfprApEtherPIoFsmEntry ::= SEQUENCE {
    cfprApEtherPIoFsmInstanceId                                      CfprApManagedObjectId,
    cfprApEtherPIoFsmDn                                              CfprApManagedObjectDn,
    cfprApEtherPIoFsmRn                                              SnmpAdminString,
    cfprApEtherPIoFsmCompletionTime                                  DateAndTime,
    cfprApEtherPIoFsmCurrentFsm                                      CfprApEtherPIoFsmCurrentFsm,
    cfprApEtherPIoFsmDescrData                                       SnmpAdminString,
    cfprApEtherPIoFsmFsmStatus                                       CfprApFsmFsmStageStatus,
    cfprApEtherPIoFsmProgress                                        Gauge32,
    cfprApEtherPIoFsmRmtErrCode                                      Gauge32,
    cfprApEtherPIoFsmRmtErrDescr                                     SnmpAdminString,
    cfprApEtherPIoFsmRmtRslt                                         CfprApConditionRemoteInvRslt
}

cfprApEtherPIoFsmInstanceId OBJECT-TYPE
    SYNTAX       CfprApManagedObjectId
    MAX-ACCESS   not-accessible
    STATUS       current
    DESCRIPTION
        "Instance identifier of the managed object."
    ::= { cfprApEtherPIoFsmEntry 1 }

cfprApEtherPIoFsmDn OBJECT-TYPE
    SYNTAX       CfprApManagedObjectDn
    MAX-ACCESS   read-only
    STATUS       current
    DESCRIPTION
        "Cisco Firepower ether:PIoFsm:dn managed object property"
    ::= { cfprApEtherPIoFsmEntry 2 }

cfprApEtherPIoFsmRn OBJECT-TYPE
    SYNTAX       SnmpAdminString
    MAX-ACCESS   read-only
    STATUS       current
    DESCRIPTION
        "Cisco Firepower ether:PIoFsm:rn managed object property"
    ::= { cfprApEtherPIoFsmEntry 3 }

cfprApEtherPIoFsmCompletionTime OBJECT-TYPE
    SYNTAX       DateAndTime
    MAX-ACCESS   read-only
    STATUS       current
    DESCRIPTION
        "Cisco Firepower ether:PIoFsm:completionTime managed
        object property"
    ::= { cfprApEtherPIoFsmEntry 4 }

cfprApEtherPIoFsmCurrentFsm OBJECT-TYPE
    SYNTAX       CfprApEtherPIoFsmCurrentFsm
    MAX-ACCESS   read-only
    STATUS       current
    DESCRIPTION
        "Cisco Firepower ether:PIoFsm:currentFsm managed object property"
    ::= { cfprApEtherPIoFsmEntry 5 }

cfprApEtherPIoFsmDescrData OBJECT-TYPE
    SYNTAX       SnmpAdminString
    MAX-ACCESS   read-only
    STATUS       current
    DESCRIPTION
        "Cisco Firepower ether:PIoFsm:descr managed object property"
    ::= { cfprApEtherPIoFsmEntry 6 }

cfprApEtherPIoFsmFsmStatus OBJECT-TYPE
    SYNTAX       CfprApFsmFsmStageStatus
    MAX-ACCESS   read-only
    STATUS       current
    DESCRIPTION
        "Cisco Firepower ether:PIoFsm:fsmStatus managed object property"
    ::= { cfprApEtherPIoFsmEntry 7 }

cfprApEtherPIoFsmProgress OBJECT-TYPE
    SYNTAX       Gauge32
    MAX-ACCESS   read-only
    STATUS       current
    DESCRIPTION
        "Cisco Firepower ether:PIoFsm:progress managed object property"
    ::= { cfprApEtherPIoFsmEntry 8 }

cfprApEtherPIoFsmRmtErrCode OBJECT-TYPE
    SYNTAX       Gauge32
    MAX-ACCESS   read-only
    STATUS       current
    DESCRIPTION
        "Cisco Firepower ether:PIoFsm:rmtErrCode managed object property"
    ::= { cfprApEtherPIoFsmEntry 9 }

cfprApEtherPIoFsmRmtErrDescr OBJECT-TYPE
    SYNTAX       SnmpAdminString
    MAX-ACCESS   read-only
    STATUS       current
    DESCRIPTION
        "Cisco Firepower ether:PIoFsm:rmtErrDescr managed object property"
    ::= { cfprApEtherPIoFsmEntry 10 }

cfprApEtherPIoFsmRmtRslt OBJECT-TYPE
    SYNTAX       CfprApConditionRemoteInvRslt
    MAX-ACCESS   read-only
    STATUS       current
    DESCRIPTION
        "Cisco Firepower ether:PIoFsm:rmtRslt managed object property"
    ::= { cfprApEtherPIoFsmEntry 11 }

cfprApEtherPIoFsmStageTable OBJECT-TYPE
    SYNTAX           SEQUENCE OF CfprApEtherPIoFsmStageEntry
    MAX-ACCESS       not-accessible
    STATUS           current
    DESCRIPTION
        "Cisco Firepower ether:PIoFsmStage managed object table"
    ::= { cfprApEtherObjects 18 }

cfprApEtherPIoFsmStageEntry OBJECT-TYPE
    SYNTAX           CfprApEtherPIoFsmStageEntry
    MAX-ACCESS       not-accessible
    STATUS           current
    DESCRIPTION
        "Entry for the cfprApEtherPIoFsmStageTable table."
    INDEX { cfprApEtherPIoFsmStageInstanceId }
    ::= { cfprApEtherPIoFsmStageTable 1 }

CfprApEtherPIoFsmStageEntry ::= SEQUENCE {
    cfprApEtherPIoFsmStageInstanceId                                 CfprApManagedObjectId,
    cfprApEtherPIoFsmStageDn                                         CfprApManagedObjectDn,
    cfprApEtherPIoFsmStageRn                                         SnmpAdminString,
    cfprApEtherPIoFsmStageDescrData                                  SnmpAdminString,
    cfprApEtherPIoFsmStageLastUpdateTime                             DateAndTime,
    cfprApEtherPIoFsmStageName                                       CfprApEtherPIoFsmStageName,
    cfprApEtherPIoFsmStageOrder                                      Gauge32,
    cfprApEtherPIoFsmStageRetry                                      Gauge32,
    cfprApEtherPIoFsmStageStageStatus                                CfprApFsmFsmStageStatus
}

cfprApEtherPIoFsmStageInstanceId OBJECT-TYPE
    SYNTAX       CfprApManagedObjectId
    MAX-ACCESS   not-accessible
    STATUS       current
    DESCRIPTION
        "Instance identifier of the managed object."
    ::= { cfprApEtherPIoFsmStageEntry 1 }

cfprApEtherPIoFsmStageDn OBJECT-TYPE
    SYNTAX       CfprApManagedObjectDn
    MAX-ACCESS   read-only
    STATUS       current
    DESCRIPTION
        "Cisco Firepower ether:PIoFsmStage:dn managed object property"
    ::= { cfprApEtherPIoFsmStageEntry 2 }

cfprApEtherPIoFsmStageRn OBJECT-TYPE
    SYNTAX       SnmpAdminString
    MAX-ACCESS   read-only
    STATUS       current
    DESCRIPTION
        "Cisco Firepower ether:PIoFsmStage:rn managed object property"
    ::= { cfprApEtherPIoFsmStageEntry 3 }

cfprApEtherPIoFsmStageDescrData OBJECT-TYPE
    SYNTAX       SnmpAdminString
    MAX-ACCESS   read-only
    STATUS       current
    DESCRIPTION
        "Cisco Firepower ether:PIoFsmStage:descr managed object property"
    ::= { cfprApEtherPIoFsmStageEntry 4 }

cfprApEtherPIoFsmStageLastUpdateTime OBJECT-TYPE
    SYNTAX       DateAndTime
    MAX-ACCESS   read-only
    STATUS       current
    DESCRIPTION
        "Cisco Firepower ether:PIoFsmStage:lastUpdateTime
        managed object property"
    ::= { cfprApEtherPIoFsmStageEntry 5 }

cfprApEtherPIoFsmStageName OBJECT-TYPE
    SYNTAX       CfprApEtherPIoFsmStageName
    MAX-ACCESS   read-only
    STATUS       current
    DESCRIPTION
        "Cisco Firepower ether:PIoFsmStage:name managed object property"
    ::= { cfprApEtherPIoFsmStageEntry 6 }

cfprApEtherPIoFsmStageOrder OBJECT-TYPE
    SYNTAX       Gauge32
    MAX-ACCESS   read-only
    STATUS       current
    DESCRIPTION
        "Cisco Firepower ether:PIoFsmStage:order managed object property"
    ::= { cfprApEtherPIoFsmStageEntry 7 }

cfprApEtherPIoFsmStageRetry OBJECT-TYPE
    SYNTAX       Gauge32
    MAX-ACCESS   read-only
    STATUS       current
    DESCRIPTION
        "Cisco Firepower ether:PIoFsmStage:retry managed object property"
    ::= { cfprApEtherPIoFsmStageEntry 8 }

cfprApEtherPIoFsmStageStageStatus OBJECT-TYPE
    SYNTAX       CfprApFsmFsmStageStatus
    MAX-ACCESS   read-only
    STATUS       current
    DESCRIPTION
        "Cisco Firepower ether:PIoFsmStage:stageStatus
        managed object property"
    ::= { cfprApEtherPIoFsmStageEntry 9 }

cfprApEtherPauseStatsTable OBJECT-TYPE
    SYNTAX           SEQUENCE OF CfprApEtherPauseStatsEntry
    MAX-ACCESS       not-accessible
    STATUS           current
    DESCRIPTION
        "Cisco Firepower ether:PauseStats managed object table"
    ::= { cfprApEtherObjects 19 }

cfprApEtherPauseStatsEntry OBJECT-TYPE
    SYNTAX           CfprApEtherPauseStatsEntry
    MAX-ACCESS       not-accessible
    STATUS           current
    DESCRIPTION
        "Entry for the cfprApEtherPauseStatsTable table."
    INDEX { cfprApEtherPauseStatsInstanceId }
    ::= { cfprApEtherPauseStatsTable 1 }

CfprApEtherPauseStatsEntry ::= SEQUENCE {
    cfprApEtherPauseStatsInstanceId                                  CfprApManagedObjectId,
    cfprApEtherPauseStatsDn                                          CfprApManagedObjectDn,
    cfprApEtherPauseStatsRn                                          SnmpAdminString,
    cfprApEtherPauseStatsIntervals                                   Gauge32,
    cfprApEtherPauseStatsRecvPause                                   Unsigned64,
    cfprApEtherPauseStatsRecvPauseDelta                              Counter64,
    cfprApEtherPauseStatsRecvPauseDeltaAvg                           Unsigned64,
    cfprApEtherPauseStatsRecvPauseDeltaMax                           Unsigned64,
    cfprApEtherPauseStatsRecvPauseDeltaMin                           Unsigned64,
    cfprApEtherPauseStatsResets                                      Unsigned64,
    cfprApEtherPauseStatsResetsDelta                                 Counter64,
    cfprApEtherPauseStatsResetsDeltaAvg                              Unsigned64,
    cfprApEtherPauseStatsResetsDeltaMax                              Unsigned64,
    cfprApEtherPauseStatsResetsDeltaMin                              Unsigned64,
    cfprApEtherPauseStatsSuspect                                     TruthValue,
    cfprApEtherPauseStatsThresholded                                 CfprApEtherPauseStatsThresholded,
    cfprApEtherPauseStatsTimeCollected                               DateAndTime,
    cfprApEtherPauseStatsUpdate                                      Gauge32,
    cfprApEtherPauseStatsXmitPause                                   Unsigned64,
    cfprApEtherPauseStatsXmitPauseDelta                              Counter64,
    cfprApEtherPauseStatsXmitPauseDeltaAvg                           Unsigned64,
    cfprApEtherPauseStatsXmitPauseDeltaMax                           Unsigned64,
    cfprApEtherPauseStatsXmitPauseDeltaMin                           Unsigned64
}

cfprApEtherPauseStatsInstanceId OBJECT-TYPE
    SYNTAX       CfprApManagedObjectId
    MAX-ACCESS   not-accessible
    STATUS       current
    DESCRIPTION
        "Instance identifier of the managed object."
    ::= { cfprApEtherPauseStatsEntry 1 }

cfprApEtherPauseStatsDn OBJECT-TYPE
    SYNTAX       CfprApManagedObjectDn
    MAX-ACCESS   read-only
    STATUS       current
    DESCRIPTION
        "Cisco Firepower ether:PauseStats:dn managed object property"
    ::= { cfprApEtherPauseStatsEntry 2 }

cfprApEtherPauseStatsRn OBJECT-TYPE
    SYNTAX       SnmpAdminString
    MAX-ACCESS   read-only
    STATUS       current
    DESCRIPTION
        "Cisco Firepower ether:PauseStats:rn managed object property"
    ::= { cfprApEtherPauseStatsEntry 3 }

cfprApEtherPauseStatsIntervals OBJECT-TYPE
    SYNTAX       Gauge32
    MAX-ACCESS   read-only
    STATUS       current
    DESCRIPTION
        "Cisco Firepower ether:PauseStats:intervals managed
        object property"
    ::= { cfprApEtherPauseStatsEntry 4 }

cfprApEtherPauseStatsRecvPause OBJECT-TYPE
    SYNTAX       Unsigned64
    MAX-ACCESS   read-only
    STATUS       current
    DESCRIPTION
        "Cisco Firepower ether:PauseStats:recvPause managed
        object property"
    ::= { cfprApEtherPauseStatsEntry 5 }

cfprApEtherPauseStatsRecvPauseDelta OBJECT-TYPE
    SYNTAX       Counter64
    MAX-ACCESS   read-only
    STATUS       current
    DESCRIPTION
        "Cisco Firepower ether:PauseStats:recvPauseDelta
        managed object property"
    ::= { cfprApEtherPauseStatsEntry 6 }

cfprApEtherPauseStatsRecvPauseDeltaAvg OBJECT-TYPE
    SYNTAX       Unsigned64
    MAX-ACCESS   read-only
    STATUS       current
    DESCRIPTION
        "Cisco Firepower ether:PauseStats:recvPauseDeltaAvg
        managed object property"
    ::= { cfprApEtherPauseStatsEntry 7 }

cfprApEtherPauseStatsRecvPauseDeltaMax OBJECT-TYPE
    SYNTAX       Unsigned64
    MAX-ACCESS   read-only
    STATUS       current
    DESCRIPTION
        "Cisco Firepower ether:PauseStats:recvPauseDeltaMax
        managed object property"
    ::= { cfprApEtherPauseStatsEntry 8 }

cfprApEtherPauseStatsRecvPauseDeltaMin OBJECT-TYPE
    SYNTAX       Unsigned64
    MAX-ACCESS   read-only
    STATUS       current
    DESCRIPTION
        "Cisco Firepower ether:PauseStats:recvPauseDeltaMin
        managed object property"
    ::= { cfprApEtherPauseStatsEntry 9 }

cfprApEtherPauseStatsResets OBJECT-TYPE
    SYNTAX       Unsigned64
    MAX-ACCESS   read-only
    STATUS       current
    DESCRIPTION
        "Cisco Firepower ether:PauseStats:resets managed object property"
    ::= { cfprApEtherPauseStatsEntry 10 }

cfprApEtherPauseStatsResetsDelta OBJECT-TYPE
    SYNTAX       Counter64
    MAX-ACCESS   read-only
    STATUS       current
    DESCRIPTION
        "Cisco Firepower ether:PauseStats:resetsDelta managed
        object property"
    ::= { cfprApEtherPauseStatsEntry 11 }

cfprApEtherPauseStatsResetsDeltaAvg OBJECT-TYPE
    SYNTAX       Unsigned64
    MAX-ACCESS   read-only
    STATUS       current
    DESCRIPTION
        "Cisco Firepower ether:PauseStats:resetsDeltaAvg
        managed object property"
    ::= { cfprApEtherPauseStatsEntry 12 }

cfprApEtherPauseStatsResetsDeltaMax OBJECT-TYPE
    SYNTAX       Unsigned64
    MAX-ACCESS   read-only
    STATUS       current
    DESCRIPTION
        "Cisco Firepower ether:PauseStats:resetsDeltaMax
        managed object property"
    ::= { cfprApEtherPauseStatsEntry 13 }

cfprApEtherPauseStatsResetsDeltaMin OBJECT-TYPE
    SYNTAX       Unsigned64
    MAX-ACCESS   read-only
    STATUS       current
    DESCRIPTION
        "Cisco Firepower ether:PauseStats:resetsDeltaMin
        managed object property"
    ::= { cfprApEtherPauseStatsEntry 14 }

cfprApEtherPauseStatsSuspect OBJECT-TYPE
    SYNTAX       TruthValue
    MAX-ACCESS   read-only
    STATUS       current
    DESCRIPTION
        "Cisco Firepower ether:PauseStats:suspect managed object property"
    ::= { cfprApEtherPauseStatsEntry 15 }

cfprApEtherPauseStatsThresholded OBJECT-TYPE
    SYNTAX       CfprApEtherPauseStatsThresholded
    MAX-ACCESS   read-only
    STATUS       current
    DESCRIPTION
        "Cisco Firepower ether:PauseStats:thresholded managed
        object property"
    ::= { cfprApEtherPauseStatsEntry 16 }

cfprApEtherPauseStatsTimeCollected OBJECT-TYPE
    SYNTAX       DateAndTime
    MAX-ACCESS   read-only
    STATUS       current
    DESCRIPTION
        "Cisco Firepower ether:PauseStats:timeCollected
        managed object property"
    ::= { cfprApEtherPauseStatsEntry 17 }

cfprApEtherPauseStatsUpdate OBJECT-TYPE
    SYNTAX       Gauge32
    MAX-ACCESS   read-only
    STATUS       current
    DESCRIPTION
        "Cisco Firepower ether:PauseStats:update managed object property"
    ::= { cfprApEtherPauseStatsEntry 18 }

cfprApEtherPauseStatsXmitPause OBJECT-TYPE
    SYNTAX       Unsigned64
    MAX-ACCESS   read-only
    STATUS       current
    DESCRIPTION
        "Cisco Firepower ether:PauseStats:xmitPause managed
        object property"
    ::= { cfprApEtherPauseStatsEntry 19 }

cfprApEtherPauseStatsXmitPauseDelta OBJECT-TYPE
    SYNTAX       Counter64
    MAX-ACCESS   read-only
    STATUS       current
    DESCRIPTION
        "Cisco Firepower ether:PauseStats:xmitPauseDelta
        managed object property"
    ::= { cfprApEtherPauseStatsEntry 20 }

cfprApEtherPauseStatsXmitPauseDeltaAvg OBJECT-TYPE
    SYNTAX       Unsigned64
    MAX-ACCESS   read-only
    STATUS       current
    DESCRIPTION
        "Cisco Firepower ether:PauseStats:xmitPauseDeltaAvg
        managed object property"
    ::= { cfprApEtherPauseStatsEntry 21 }

cfprApEtherPauseStatsXmitPauseDeltaMax OBJECT-TYPE
    SYNTAX       Unsigned64
    MAX-ACCESS   read-only
    STATUS       current
    DESCRIPTION
        "Cisco Firepower ether:PauseStats:xmitPauseDeltaMax
        managed object property"
    ::= { cfprApEtherPauseStatsEntry 22 }

cfprApEtherPauseStatsXmitPauseDeltaMin OBJECT-TYPE
    SYNTAX       Unsigned64
    MAX-ACCESS   read-only
    STATUS       current
    DESCRIPTION
        "Cisco Firepower ether:PauseStats:xmitPauseDeltaMin
        managed object property"
    ::= { cfprApEtherPauseStatsEntry 23 }

cfprApEtherPauseStatsHistTable OBJECT-TYPE
    SYNTAX           SEQUENCE OF CfprApEtherPauseStatsHistEntry
    MAX-ACCESS       not-accessible
    STATUS           current
    DESCRIPTION
        "Cisco Firepower ether:PauseStatsHist managed object table"
    ::= { cfprApEtherObjects 20 }

cfprApEtherPauseStatsHistEntry OBJECT-TYPE
    SYNTAX           CfprApEtherPauseStatsHistEntry
    MAX-ACCESS       not-accessible
    STATUS           current
    DESCRIPTION
        "Entry for the cfprApEtherPauseStatsHistTable table."
    INDEX { cfprApEtherPauseStatsHistInstanceId }
    ::= { cfprApEtherPauseStatsHistTable 1 }

CfprApEtherPauseStatsHistEntry ::= SEQUENCE {
    cfprApEtherPauseStatsHistInstanceId                              CfprApManagedObjectId,
    cfprApEtherPauseStatsHistDn                                      CfprApManagedObjectDn,
    cfprApEtherPauseStatsHistRn                                      SnmpAdminString,
    cfprApEtherPauseStatsHistId                                      Unsigned64,
    cfprApEtherPauseStatsHistMostRecent                              TruthValue,
    cfprApEtherPauseStatsHistRecvPause                               Unsigned64,
    cfprApEtherPauseStatsHistRecvPauseDelta                          Unsigned64,
    cfprApEtherPauseStatsHistRecvPauseDeltaAvg                       Unsigned64,
    cfprApEtherPauseStatsHistRecvPauseDeltaMax                       Unsigned64,
    cfprApEtherPauseStatsHistRecvPauseDeltaMin                       Unsigned64,
    cfprApEtherPauseStatsHistResets                                  Unsigned64,
    cfprApEtherPauseStatsHistResetsDelta                             Unsigned64,
    cfprApEtherPauseStatsHistResetsDeltaAvg                          Unsigned64,
    cfprApEtherPauseStatsHistResetsDeltaMax                          Unsigned64,
    cfprApEtherPauseStatsHistResetsDeltaMin                          Unsigned64,
    cfprApEtherPauseStatsHistSuspect                                 TruthValue,
    cfprApEtherPauseStatsHistThresholded                             CfprApEtherPauseStatsHistThresholded,
    cfprApEtherPauseStatsHistTimeCollected                           DateAndTime,
    cfprApEtherPauseStatsHistXmitPause                               Unsigned64,
    cfprApEtherPauseStatsHistXmitPauseDelta                          Unsigned64,
    cfprApEtherPauseStatsHistXmitPauseDeltaAvg                       Unsigned64,
    cfprApEtherPauseStatsHistXmitPauseDeltaMax                       Unsigned64,
    cfprApEtherPauseStatsHistXmitPauseDeltaMin                       Unsigned64
}

cfprApEtherPauseStatsHistInstanceId OBJECT-TYPE
    SYNTAX       CfprApManagedObjectId
    MAX-ACCESS   not-accessible
    STATUS       current
    DESCRIPTION
        "Instance identifier of the managed object."
    ::= { cfprApEtherPauseStatsHistEntry 1 }

cfprApEtherPauseStatsHistDn OBJECT-TYPE
    SYNTAX       CfprApManagedObjectDn
    MAX-ACCESS   read-only
    STATUS       current
    DESCRIPTION
        "Cisco Firepower ether:PauseStatsHist:dn managed object property"
    ::= { cfprApEtherPauseStatsHistEntry 2 }

cfprApEtherPauseStatsHistRn OBJECT-TYPE
    SYNTAX       SnmpAdminString
    MAX-ACCESS   read-only
    STATUS       current
    DESCRIPTION
        "Cisco Firepower ether:PauseStatsHist:rn managed object property"
    ::= { cfprApEtherPauseStatsHistEntry 3 }

cfprApEtherPauseStatsHistId OBJECT-TYPE
    SYNTAX       Unsigned64
    MAX-ACCESS   read-only
    STATUS       current
    DESCRIPTION
        "Cisco Firepower ether:PauseStatsHist:id managed object property"
    ::= { cfprApEtherPauseStatsHistEntry 4 }

cfprApEtherPauseStatsHistMostRecent OBJECT-TYPE
    SYNTAX       TruthValue
    MAX-ACCESS   read-only
    STATUS       current
    DESCRIPTION
        "Cisco Firepower ether:PauseStatsHist:mostRecent
        managed object property"
    ::= { cfprApEtherPauseStatsHistEntry 5 }

cfprApEtherPauseStatsHistRecvPause OBJECT-TYPE
    SYNTAX       Unsigned64
    MAX-ACCESS   read-only
    STATUS       current
    DESCRIPTION
        "Cisco Firepower ether:PauseStatsHist:recvPause
        managed object property"
    ::= { cfprApEtherPauseStatsHistEntry 6 }

cfprApEtherPauseStatsHistRecvPauseDelta OBJECT-TYPE
    SYNTAX       Unsigned64
    MAX-ACCESS   read-only
    STATUS       current
    DESCRIPTION
        "Cisco Firepower ether:PauseStatsHist:recvPauseDelta
        managed object property"
    ::= { cfprApEtherPauseStatsHistEntry 7 }

cfprApEtherPauseStatsHistRecvPauseDeltaAvg OBJECT-TYPE
    SYNTAX       Unsigned64
    MAX-ACCESS   read-only
    STATUS       current
    DESCRIPTION
        "Cisco Firepower ether:PauseStatsHist:recvPauseDeltaAvg
        managed object property"
    ::= { cfprApEtherPauseStatsHistEntry 8 }

cfprApEtherPauseStatsHistRecvPauseDeltaMax OBJECT-TYPE
    SYNTAX       Unsigned64
    MAX-ACCESS   read-only
    STATUS       current
    DESCRIPTION
        "Cisco Firepower ether:PauseStatsHist:recvPauseDeltaMax
        managed object property"
    ::= { cfprApEtherPauseStatsHistEntry 9 }

cfprApEtherPauseStatsHistRecvPauseDeltaMin OBJECT-TYPE
    SYNTAX       Unsigned64
    MAX-ACCESS   read-only
    STATUS       current
    DESCRIPTION
        "Cisco Firepower ether:PauseStatsHist:recvPauseDeltaMin
        managed object property"
    ::= { cfprApEtherPauseStatsHistEntry 10 }

cfprApEtherPauseStatsHistResets OBJECT-TYPE
    SYNTAX       Unsigned64
    MAX-ACCESS   read-only
    STATUS       current
    DESCRIPTION
        "Cisco Firepower ether:PauseStatsHist:resets managed
        object property"
    ::= { cfprApEtherPauseStatsHistEntry 11 }

cfprApEtherPauseStatsHistResetsDelta OBJECT-TYPE
    SYNTAX       Unsigned64
    MAX-ACCESS   read-only
    STATUS       current
    DESCRIPTION
        "Cisco Firepower ether:PauseStatsHist:resetsDelta
        managed object property"
    ::= { cfprApEtherPauseStatsHistEntry 12 }

cfprApEtherPauseStatsHistResetsDeltaAvg OBJECT-TYPE
    SYNTAX       Unsigned64
    MAX-ACCESS   read-only
    STATUS       current
    DESCRIPTION
        "Cisco Firepower ether:PauseStatsHist:resetsDeltaAvg
        managed object property"
    ::= { cfprApEtherPauseStatsHistEntry 13 }

cfprApEtherPauseStatsHistResetsDeltaMax OBJECT-TYPE
    SYNTAX       Unsigned64
    MAX-ACCESS   read-only
    STATUS       current
    DESCRIPTION
        "Cisco Firepower ether:PauseStatsHist:resetsDeltaMax
        managed object property"
    ::= { cfprApEtherPauseStatsHistEntry 14 }

cfprApEtherPauseStatsHistResetsDeltaMin OBJECT-TYPE
    SYNTAX       Unsigned64
    MAX-ACCESS   read-only
    STATUS       current
    DESCRIPTION
        "Cisco Firepower ether:PauseStatsHist:resetsDeltaMin
        managed object property"
    ::= { cfprApEtherPauseStatsHistEntry 15 }

cfprApEtherPauseStatsHistSuspect OBJECT-TYPE
    SYNTAX       TruthValue
    MAX-ACCESS   read-only
    STATUS       current
    DESCRIPTION
        "Cisco Firepower ether:PauseStatsHist:suspect managed
        object property"
    ::= { cfprApEtherPauseStatsHistEntry 16 }

cfprApEtherPauseStatsHistThresholded OBJECT-TYPE
    SYNTAX       CfprApEtherPauseStatsHistThresholded
    MAX-ACCESS   read-only
    STATUS       current
    DESCRIPTION
        "Cisco Firepower ether:PauseStatsHist:thresholded
        managed object property"
    ::= { cfprApEtherPauseStatsHistEntry 17 }

cfprApEtherPauseStatsHistTimeCollected OBJECT-TYPE
    SYNTAX       DateAndTime
    MAX-ACCESS   read-only
    STATUS       current
    DESCRIPTION
        "Cisco Firepower ether:PauseStatsHist:timeCollected
        managed object property"
    ::= { cfprApEtherPauseStatsHistEntry 18 }

cfprApEtherPauseStatsHistXmitPause OBJECT-TYPE
    SYNTAX       Unsigned64
    MAX-ACCESS   read-only
    STATUS       current
    DESCRIPTION
        "Cisco Firepower ether:PauseStatsHist:xmitPause
        managed object property"
    ::= { cfprApEtherPauseStatsHistEntry 19 }

cfprApEtherPauseStatsHistXmitPauseDelta OBJECT-TYPE
    SYNTAX       Unsigned64
    MAX-ACCESS   read-only
    STATUS       current
    DESCRIPTION
        "Cisco Firepower ether:PauseStatsHist:xmitPauseDelta
        managed object property"
    ::= { cfprApEtherPauseStatsHistEntry 20 }

cfprApEtherPauseStatsHistXmitPauseDeltaAvg OBJECT-TYPE
    SYNTAX       Unsigned64
    MAX-ACCESS   read-only
    STATUS       current
    DESCRIPTION
        "Cisco Firepower ether:PauseStatsHist:xmitPauseDeltaAvg
        managed object property"
    ::= { cfprApEtherPauseStatsHistEntry 21 }

cfprApEtherPauseStatsHistXmitPauseDeltaMax OBJECT-TYPE
    SYNTAX       Unsigned64
    MAX-ACCESS   read-only
    STATUS       current
    DESCRIPTION
        "Cisco Firepower ether:PauseStatsHist:xmitPauseDeltaMax
        managed object property"
    ::= { cfprApEtherPauseStatsHistEntry 22 }

cfprApEtherPauseStatsHistXmitPauseDeltaMin OBJECT-TYPE
    SYNTAX       Unsigned64
    MAX-ACCESS   read-only
    STATUS       current
    DESCRIPTION
        "Cisco Firepower ether:PauseStatsHist:xmitPauseDeltaMin
        managed object property"
    ::= { cfprApEtherPauseStatsHistEntry 23 }

cfprApEtherPortChanIdElemTable OBJECT-TYPE
    SYNTAX           SEQUENCE OF CfprApEtherPortChanIdElemEntry
    MAX-ACCESS       not-accessible
    STATUS           current
    DESCRIPTION
        "Cisco Firepower ether:PortChanIdElem managed object table"
    ::= { cfprApEtherObjects 21 }

cfprApEtherPortChanIdElemEntry OBJECT-TYPE
    SYNTAX           CfprApEtherPortChanIdElemEntry
    MAX-ACCESS       not-accessible
    STATUS           current
    DESCRIPTION
        "Entry for the cfprApEtherPortChanIdElemTable table."
    INDEX { cfprApEtherPortChanIdElemInstanceId }
    ::= { cfprApEtherPortChanIdElemTable 1 }

CfprApEtherPortChanIdElemEntry ::= SEQUENCE {
    cfprApEtherPortChanIdElemInstanceId                              CfprApManagedObjectId,
    cfprApEtherPortChanIdElemDn                                      CfprApManagedObjectDn,
    cfprApEtherPortChanIdElemRn                                      SnmpAdminString,
    cfprApEtherPortChanIdElemId                                      Gauge32
}

cfprApEtherPortChanIdElemInstanceId OBJECT-TYPE
    SYNTAX       CfprApManagedObjectId
    MAX-ACCESS   not-accessible
    STATUS       current
    DESCRIPTION
        "Instance identifier of the managed object."
    ::= { cfprApEtherPortChanIdElemEntry 1 }

cfprApEtherPortChanIdElemDn OBJECT-TYPE
    SYNTAX       CfprApManagedObjectDn
    MAX-ACCESS   read-only
    STATUS       current
    DESCRIPTION
        "Cisco Firepower ether:PortChanIdElem:dn managed object property"
    ::= { cfprApEtherPortChanIdElemEntry 2 }

cfprApEtherPortChanIdElemRn OBJECT-TYPE
    SYNTAX       SnmpAdminString
    MAX-ACCESS   read-only
    STATUS       current
    DESCRIPTION
        "Cisco Firepower ether:PortChanIdElem:rn managed object property"
    ::= { cfprApEtherPortChanIdElemEntry 3 }

cfprApEtherPortChanIdElemId OBJECT-TYPE
    SYNTAX       Gauge32
    MAX-ACCESS   read-only
    STATUS       current
    DESCRIPTION
        "Cisco Firepower ether:PortChanIdElem:id managed object property"
    ::= { cfprApEtherPortChanIdElemEntry 4 }

cfprApEtherPortChanIdUniverseTable OBJECT-TYPE
    SYNTAX           SEQUENCE OF CfprApEtherPortChanIdUniverseEntry
    MAX-ACCESS       not-accessible
    STATUS           current
    DESCRIPTION
        "Cisco Firepower ether:PortChanIdUniverse managed object table"
    ::= { cfprApEtherObjects 22 }

cfprApEtherPortChanIdUniverseEntry OBJECT-TYPE
    SYNTAX           CfprApEtherPortChanIdUniverseEntry
    MAX-ACCESS       not-accessible
    STATUS           current
    DESCRIPTION
        "Entry for the cfprApEtherPortChanIdUniverseTable table."
    INDEX { cfprApEtherPortChanIdUniverseInstanceId }
    ::= { cfprApEtherPortChanIdUniverseTable 1 }

CfprApEtherPortChanIdUniverseEntry ::= SEQUENCE {
    cfprApEtherPortChanIdUniverseInstanceId                          CfprApManagedObjectId,
    cfprApEtherPortChanIdUniverseDn                                  CfprApManagedObjectDn,
    cfprApEtherPortChanIdUniverseRn                                  SnmpAdminString
}

cfprApEtherPortChanIdUniverseInstanceId OBJECT-TYPE
    SYNTAX       CfprApManagedObjectId
    MAX-ACCESS   not-accessible
    STATUS       current
    DESCRIPTION
        "Instance identifier of the managed object."
    ::= { cfprApEtherPortChanIdUniverseEntry 1 }

cfprApEtherPortChanIdUniverseDn OBJECT-TYPE
    SYNTAX       CfprApManagedObjectDn
    MAX-ACCESS   read-only
    STATUS       current
    DESCRIPTION
        "Cisco Firepower ether:PortChanIdUniverse:dn managed
        object property"
    ::= { cfprApEtherPortChanIdUniverseEntry 2 }

cfprApEtherPortChanIdUniverseRn OBJECT-TYPE
    SYNTAX       SnmpAdminString
    MAX-ACCESS   read-only
    STATUS       current
    DESCRIPTION
        "Cisco Firepower ether:PortChanIdUniverse:rn managed
        object property"
    ::= { cfprApEtherPortChanIdUniverseEntry 3 }

cfprApEtherRxStatsTable OBJECT-TYPE
    SYNTAX           SEQUENCE OF CfprApEtherRxStatsEntry
    MAX-ACCESS       not-accessible
    STATUS           current
    DESCRIPTION
        "Cisco Firepower ether:RxStats managed object table"
    ::= { cfprApEtherObjects 23 }

cfprApEtherRxStatsEntry OBJECT-TYPE
    SYNTAX           CfprApEtherRxStatsEntry
    MAX-ACCESS       not-accessible
    STATUS           current
    DESCRIPTION
        "Entry for the cfprApEtherRxStatsTable table."
    INDEX { cfprApEtherRxStatsInstanceId }
    ::= { cfprApEtherRxStatsTable 1 }

CfprApEtherRxStatsEntry ::= SEQUENCE {
    cfprApEtherRxStatsInstanceId                                     CfprApManagedObjectId,
    cfprApEtherRxStatsDn                                             CfprApManagedObjectDn,
    cfprApEtherRxStatsRn                                             SnmpAdminString,
    cfprApEtherRxStatsBroadcastPackets                               Unsigned64,
    cfprApEtherRxStatsBroadcastPacketsDelta                          Counter64,
    cfprApEtherRxStatsBroadcastPacketsDeltaAvg                       Unsigned64,
    cfprApEtherRxStatsBroadcastPacketsDeltaMax                       Unsigned64,
    cfprApEtherRxStatsBroadcastPacketsDeltaMin                       Unsigned64,
    cfprApEtherRxStatsIntervals                                      Gauge32,
    cfprApEtherRxStatsJumboPackets                                   Unsigned64,
    cfprApEtherRxStatsJumboPacketsDelta                              Counter64,
    cfprApEtherRxStatsJumboPacketsDeltaAvg                           Unsigned64,
    cfprApEtherRxStatsJumboPacketsDeltaMax                           Unsigned64,
    cfprApEtherRxStatsJumboPacketsDeltaMin                           Unsigned64,
    cfprApEtherRxStatsMulticastPackets                               Unsigned64,
    cfprApEtherRxStatsMulticastPacketsDelta                          Counter64,
    cfprApEtherRxStatsMulticastPacketsDeltaAvg                       Unsigned64,
    cfprApEtherRxStatsMulticastPacketsDeltaMax                       Unsigned64,
    cfprApEtherRxStatsMulticastPacketsDeltaMin                       Unsigned64,
    cfprApEtherRxStatsSuspect                                        TruthValue,
    cfprApEtherRxStatsThresholded                                    CfprApEtherRxStatsThresholded,
    cfprApEtherRxStatsTimeCollected                                  DateAndTime,
    cfprApEtherRxStatsTotalBytes                                     Unsigned64,
    cfprApEtherRxStatsTotalBytesDelta                                Counter64,
    cfprApEtherRxStatsTotalBytesDeltaAvg                             Unsigned64,
    cfprApEtherRxStatsTotalBytesDeltaMax                             Unsigned64,
    cfprApEtherRxStatsTotalBytesDeltaMin                             Unsigned64,
    cfprApEtherRxStatsTotalPackets                                   Unsigned64,
    cfprApEtherRxStatsTotalPacketsDelta                              Counter64,
    cfprApEtherRxStatsTotalPacketsDeltaAvg                           Unsigned64,
    cfprApEtherRxStatsTotalPacketsDeltaMax                           Unsigned64,
    cfprApEtherRxStatsTotalPacketsDeltaMin                           Unsigned64,
    cfprApEtherRxStatsUnicastPackets                                 Unsigned64,
    cfprApEtherRxStatsUnicastPacketsDelta                            Counter64,
    cfprApEtherRxStatsUnicastPacketsDeltaAvg                         Unsigned64,
    cfprApEtherRxStatsUnicastPacketsDeltaMax                         Unsigned64,
    cfprApEtherRxStatsUnicastPacketsDeltaMin                         Unsigned64,
    cfprApEtherRxStatsUpdate                                         Gauge32
}

cfprApEtherRxStatsInstanceId OBJECT-TYPE
    SYNTAX       CfprApManagedObjectId
    MAX-ACCESS   not-accessible
    STATUS       current
    DESCRIPTION
        "Instance identifier of the managed object."
    ::= { cfprApEtherRxStatsEntry 1 }

cfprApEtherRxStatsDn OBJECT-TYPE
    SYNTAX       CfprApManagedObjectDn
    MAX-ACCESS   read-only
    STATUS       current
    DESCRIPTION
        "Cisco Firepower ether:RxStats:dn managed object property"
    ::= { cfprApEtherRxStatsEntry 2 }

cfprApEtherRxStatsRn OBJECT-TYPE
    SYNTAX       SnmpAdminString
    MAX-ACCESS   read-only
    STATUS       current
    DESCRIPTION
        "Cisco Firepower ether:RxStats:rn managed object property"
    ::= { cfprApEtherRxStatsEntry 3 }

cfprApEtherRxStatsBroadcastPackets OBJECT-TYPE
    SYNTAX       Unsigned64
    MAX-ACCESS   read-only
    STATUS       current
    DESCRIPTION
        "Cisco Firepower ether:RxStats:broadcastPackets
        managed object property"
    ::= { cfprApEtherRxStatsEntry 4 }

cfprApEtherRxStatsBroadcastPacketsDelta OBJECT-TYPE
    SYNTAX       Counter64
    MAX-ACCESS   read-only
    STATUS       current
    DESCRIPTION
        "Cisco Firepower ether:RxStats:broadcastPacketsDelta
        managed object property"
    ::= { cfprApEtherRxStatsEntry 5 }

cfprApEtherRxStatsBroadcastPacketsDeltaAvg OBJECT-TYPE
    SYNTAX       Unsigned64
    MAX-ACCESS   read-only
    STATUS       current
    DESCRIPTION
        "Cisco Firepower ether:RxStats:broadcastPacketsDeltaAvg
        managed object property"
    ::= { cfprApEtherRxStatsEntry 6 }

cfprApEtherRxStatsBroadcastPacketsDeltaMax OBJECT-TYPE
    SYNTAX       Unsigned64
    MAX-ACCESS   read-only
    STATUS       current
    DESCRIPTION
        "Cisco Firepower ether:RxStats:broadcastPacketsDeltaMax
        managed object property"
    ::= { cfprApEtherRxStatsEntry 7 }

cfprApEtherRxStatsBroadcastPacketsDeltaMin OBJECT-TYPE
    SYNTAX       Unsigned64
    MAX-ACCESS   read-only
    STATUS       current
    DESCRIPTION
        "Cisco Firepower ether:RxStats:broadcastPacketsDeltaMin
        managed object property"
    ::= { cfprApEtherRxStatsEntry 8 }

cfprApEtherRxStatsIntervals OBJECT-TYPE
    SYNTAX       Gauge32
    MAX-ACCESS   read-only
    STATUS       current
    DESCRIPTION
        "Cisco Firepower ether:RxStats:intervals managed object property"
    ::= { cfprApEtherRxStatsEntry 9 }

cfprApEtherRxStatsJumboPackets OBJECT-TYPE
    SYNTAX       Unsigned64
    MAX-ACCESS   read-only
    STATUS       current
    DESCRIPTION
        "Cisco Firepower ether:RxStats:jumboPackets managed
        object property"
    ::= { cfprApEtherRxStatsEntry 10 }

cfprApEtherRxStatsJumboPacketsDelta OBJECT-TYPE
    SYNTAX       Counter64
    MAX-ACCESS   read-only
    STATUS       current
    DESCRIPTION
        "Cisco Firepower ether:RxStats:jumboPacketsDelta
        managed object property"
    ::= { cfprApEtherRxStatsEntry 11 }

cfprApEtherRxStatsJumboPacketsDeltaAvg OBJECT-TYPE
    SYNTAX       Unsigned64
    MAX-ACCESS   read-only
    STATUS       current
    DESCRIPTION
        "Cisco Firepower ether:RxStats:jumboPacketsDeltaAvg
        managed object property"
    ::= { cfprApEtherRxStatsEntry 12 }

cfprApEtherRxStatsJumboPacketsDeltaMax OBJECT-TYPE
    SYNTAX       Unsigned64
    MAX-ACCESS   read-only
    STATUS       current
    DESCRIPTION
        "Cisco Firepower ether:RxStats:jumboPacketsDeltaMax
        managed object property"
    ::= { cfprApEtherRxStatsEntry 13 }

cfprApEtherRxStatsJumboPacketsDeltaMin OBJECT-TYPE
    SYNTAX       Unsigned64
    MAX-ACCESS   read-only
    STATUS       current
    DESCRIPTION
        "Cisco Firepower ether:RxStats:jumboPacketsDeltaMin
        managed object property"
    ::= { cfprApEtherRxStatsEntry 14 }

cfprApEtherRxStatsMulticastPackets OBJECT-TYPE
    SYNTAX       Unsigned64
    MAX-ACCESS   read-only
    STATUS       current
    DESCRIPTION
        "Cisco Firepower ether:RxStats:multicastPackets
        managed object property"
    ::= { cfprApEtherRxStatsEntry 15 }

cfprApEtherRxStatsMulticastPacketsDelta OBJECT-TYPE
    SYNTAX       Counter64
    MAX-ACCESS   read-only
    STATUS       current
    DESCRIPTION
        "Cisco Firepower ether:RxStats:multicastPacketsDelta
        managed object property"
    ::= { cfprApEtherRxStatsEntry 16 }

cfprApEtherRxStatsMulticastPacketsDeltaAvg OBJECT-TYPE
    SYNTAX       Unsigned64
    MAX-ACCESS   read-only
    STATUS       current
    DESCRIPTION
        "Cisco Firepower ether:RxStats:multicastPacketsDeltaAvg
        managed object property"
    ::= { cfprApEtherRxStatsEntry 17 }

cfprApEtherRxStatsMulticastPacketsDeltaMax OBJECT-TYPE
    SYNTAX       Unsigned64
    MAX-ACCESS   read-only
    STATUS       current
    DESCRIPTION
        "Cisco Firepower ether:RxStats:multicastPacketsDeltaMax
        managed object property"
    ::= { cfprApEtherRxStatsEntry 18 }

cfprApEtherRxStatsMulticastPacketsDeltaMin OBJECT-TYPE
    SYNTAX       Unsigned64
    MAX-ACCESS   read-only
    STATUS       current
    DESCRIPTION
        "Cisco Firepower ether:RxStats:multicastPacketsDeltaMin
        managed object property"
    ::= { cfprApEtherRxStatsEntry 19 }

cfprApEtherRxStatsSuspect OBJECT-TYPE
    SYNTAX       TruthValue
    MAX-ACCESS   read-only
    STATUS       current
    DESCRIPTION
        "Cisco Firepower ether:RxStats:suspect managed object property"
    ::= { cfprApEtherRxStatsEntry 20 }

cfprApEtherRxStatsThresholded OBJECT-TYPE
    SYNTAX       CfprApEtherRxStatsThresholded
    MAX-ACCESS   read-only
    STATUS       current
    DESCRIPTION
        "Cisco Firepower ether:RxStats:thresholded managed
        object property"
    ::= { cfprApEtherRxStatsEntry 21 }

cfprApEtherRxStatsTimeCollected OBJECT-TYPE
    SYNTAX       DateAndTime
    MAX-ACCESS   read-only
    STATUS       current
    DESCRIPTION
        "Cisco Firepower ether:RxStats:timeCollected managed
        object property"
    ::= { cfprApEtherRxStatsEntry 22 }

cfprApEtherRxStatsTotalBytes OBJECT-TYPE
    SYNTAX       Unsigned64
    MAX-ACCESS   read-only
    STATUS       current
    DESCRIPTION
        "Cisco Firepower ether:RxStats:totalBytes managed object property"
    ::= { cfprApEtherRxStatsEntry 23 }

cfprApEtherRxStatsTotalBytesDelta OBJECT-TYPE
    SYNTAX       Counter64
    MAX-ACCESS   read-only
    STATUS       current
    DESCRIPTION
        "Cisco Firepower ether:RxStats:totalBytesDelta
        managed object property"
    ::= { cfprApEtherRxStatsEntry 24 }

cfprApEtherRxStatsTotalBytesDeltaAvg OBJECT-TYPE
    SYNTAX       Unsigned64
    MAX-ACCESS   read-only
    STATUS       current
    DESCRIPTION
        "Cisco Firepower ether:RxStats:totalBytesDeltaAvg
        managed object property"
    ::= { cfprApEtherRxStatsEntry 25 }

cfprApEtherRxStatsTotalBytesDeltaMax OBJECT-TYPE
    SYNTAX       Unsigned64
    MAX-ACCESS   read-only
    STATUS       current
    DESCRIPTION
        "Cisco Firepower ether:RxStats:totalBytesDeltaMax
        managed object property"
    ::= { cfprApEtherRxStatsEntry 26 }

cfprApEtherRxStatsTotalBytesDeltaMin OBJECT-TYPE
    SYNTAX       Unsigned64
    MAX-ACCESS   read-only
    STATUS       current
    DESCRIPTION
        "Cisco Firepower ether:RxStats:totalBytesDeltaMin
        managed object property"
    ::= { cfprApEtherRxStatsEntry 27 }

cfprApEtherRxStatsTotalPackets OBJECT-TYPE
    SYNTAX       Unsigned64
    MAX-ACCESS   read-only
    STATUS       current
    DESCRIPTION
        "Cisco Firepower ether:RxStats:totalPackets managed
        object property"
    ::= { cfprApEtherRxStatsEntry 28 }

cfprApEtherRxStatsTotalPacketsDelta OBJECT-TYPE
    SYNTAX       Counter64
    MAX-ACCESS   read-only
    STATUS       current
    DESCRIPTION
        "Cisco Firepower ether:RxStats:totalPacketsDelta
        managed object property"
    ::= { cfprApEtherRxStatsEntry 29 }

cfprApEtherRxStatsTotalPacketsDeltaAvg OBJECT-TYPE
    SYNTAX       Unsigned64
    MAX-ACCESS   read-only
    STATUS       current
    DESCRIPTION
        "Cisco Firepower ether:RxStats:totalPacketsDeltaAvg
        managed object property"
    ::= { cfprApEtherRxStatsEntry 30 }

cfprApEtherRxStatsTotalPacketsDeltaMax OBJECT-TYPE
    SYNTAX       Unsigned64
    MAX-ACCESS   read-only
    STATUS       current
    DESCRIPTION
        "Cisco Firepower ether:RxStats:totalPacketsDeltaMax
        managed object property"
    ::= { cfprApEtherRxStatsEntry 31 }

cfprApEtherRxStatsTotalPacketsDeltaMin OBJECT-TYPE
    SYNTAX       Unsigned64
    MAX-ACCESS   read-only
    STATUS       current
    DESCRIPTION
        "Cisco Firepower ether:RxStats:totalPacketsDeltaMin
        managed object property"
    ::= { cfprApEtherRxStatsEntry 32 }

cfprApEtherRxStatsUnicastPackets OBJECT-TYPE
    SYNTAX       Unsigned64
    MAX-ACCESS   read-only
    STATUS       current
    DESCRIPTION
        "Cisco Firepower ether:RxStats:unicastPackets managed
        object property"
    ::= { cfprApEtherRxStatsEntry 33 }

cfprApEtherRxStatsUnicastPacketsDelta OBJECT-TYPE
    SYNTAX       Counter64
    MAX-ACCESS   read-only
    STATUS       current
    DESCRIPTION
        "Cisco Firepower ether:RxStats:unicastPacketsDelta
        managed object property"
    ::= { cfprApEtherRxStatsEntry 34 }

cfprApEtherRxStatsUnicastPacketsDeltaAvg OBJECT-TYPE
    SYNTAX       Unsigned64
    MAX-ACCESS   read-only
    STATUS       current
    DESCRIPTION
        "Cisco Firepower ether:RxStats:unicastPacketsDeltaAvg
        managed object property"
    ::= { cfprApEtherRxStatsEntry 35 }

cfprApEtherRxStatsUnicastPacketsDeltaMax OBJECT-TYPE
    SYNTAX       Unsigned64
    MAX-ACCESS   read-only
    STATUS       current
    DESCRIPTION
        "Cisco Firepower ether:RxStats:unicastPacketsDeltaMax
        managed object property"
    ::= { cfprApEtherRxStatsEntry 36 }

cfprApEtherRxStatsUnicastPacketsDeltaMin OBJECT-TYPE
    SYNTAX       Unsigned64
    MAX-ACCESS   read-only
    STATUS       current
    DESCRIPTION
        "Cisco Firepower ether:RxStats:unicastPacketsDeltaMin
        managed object property"
    ::= { cfprApEtherRxStatsEntry 37 }

cfprApEtherRxStatsUpdate OBJECT-TYPE
    SYNTAX       Gauge32
    MAX-ACCESS   read-only
    STATUS       current
    DESCRIPTION
        "Cisco Firepower ether:RxStats:update managed object property"
    ::= { cfprApEtherRxStatsEntry 38 }

cfprApEtherRxStatsHistTable OBJECT-TYPE
    SYNTAX           SEQUENCE OF CfprApEtherRxStatsHistEntry
    MAX-ACCESS       not-accessible
    STATUS           current
    DESCRIPTION
        "Cisco Firepower ether:RxStatsHist managed object table"
    ::= { cfprApEtherObjects 24 }

cfprApEtherRxStatsHistEntry OBJECT-TYPE
    SYNTAX           CfprApEtherRxStatsHistEntry
    MAX-ACCESS       not-accessible
    STATUS           current
    DESCRIPTION
        "Entry for the cfprApEtherRxStatsHistTable table."
    INDEX { cfprApEtherRxStatsHistInstanceId }
    ::= { cfprApEtherRxStatsHistTable 1 }

CfprApEtherRxStatsHistEntry ::= SEQUENCE {
    cfprApEtherRxStatsHistInstanceId                                 CfprApManagedObjectId,
    cfprApEtherRxStatsHistDn                                         CfprApManagedObjectDn,
    cfprApEtherRxStatsHistRn                                         SnmpAdminString,
    cfprApEtherRxStatsHistBroadcastPackets                           Unsigned64,
    cfprApEtherRxStatsHistBroadcastPacketsDelta                      Unsigned64,
    cfprApEtherRxStatsHistBroadcastPacketsDeltaAvg                   Unsigned64,
    cfprApEtherRxStatsHistBroadcastPacketsDeltaMax                   Unsigned64,
    cfprApEtherRxStatsHistBroadcastPacketsDeltaMin                   Unsigned64,
    cfprApEtherRxStatsHistId                                         Unsigned64,
    cfprApEtherRxStatsHistJumboPackets                               Unsigned64,
    cfprApEtherRxStatsHistJumboPacketsDelta                          Unsigned64,
    cfprApEtherRxStatsHistJumboPacketsDeltaAvg                       Unsigned64,
    cfprApEtherRxStatsHistJumboPacketsDeltaMax                       Unsigned64,
    cfprApEtherRxStatsHistJumboPacketsDeltaMin                       Unsigned64,
    cfprApEtherRxStatsHistMostRecent                                 TruthValue,
    cfprApEtherRxStatsHistMulticastPackets                           Unsigned64,
    cfprApEtherRxStatsHistMulticastPacketsDelta                      Unsigned64,
    cfprApEtherRxStatsHistMulticastPacketsDeltaAvg                   Unsigned64,
    cfprApEtherRxStatsHistMulticastPacketsDeltaMax                   Unsigned64,
    cfprApEtherRxStatsHistMulticastPacketsDeltaMin                   Unsigned64,
    cfprApEtherRxStatsHistSuspect                                    TruthValue,
    cfprApEtherRxStatsHistThresholded                                CfprApEtherRxStatsHistThresholded,
    cfprApEtherRxStatsHistTimeCollected                              DateAndTime,
    cfprApEtherRxStatsHistTotalBytes                                 Unsigned64,
    cfprApEtherRxStatsHistTotalBytesDelta                            Unsigned64,
    cfprApEtherRxStatsHistTotalBytesDeltaAvg                         Unsigned64,
    cfprApEtherRxStatsHistTotalBytesDeltaMax                         Unsigned64,
    cfprApEtherRxStatsHistTotalBytesDeltaMin                         Unsigned64,
    cfprApEtherRxStatsHistTotalPackets                               Unsigned64,
    cfprApEtherRxStatsHistTotalPacketsDelta                          Unsigned64,
    cfprApEtherRxStatsHistTotalPacketsDeltaAvg                       Unsigned64,
    cfprApEtherRxStatsHistTotalPacketsDeltaMax                       Unsigned64,
    cfprApEtherRxStatsHistTotalPacketsDeltaMin                       Unsigned64,
    cfprApEtherRxStatsHistUnicastPackets                             Unsigned64,
    cfprApEtherRxStatsHistUnicastPacketsDelta                        Unsigned64,
    cfprApEtherRxStatsHistUnicastPacketsDeltaAvg                     Unsigned64,
    cfprApEtherRxStatsHistUnicastPacketsDeltaMax                     Unsigned64,
    cfprApEtherRxStatsHistUnicastPacketsDeltaMin                     Unsigned64
}

cfprApEtherRxStatsHistInstanceId OBJECT-TYPE
    SYNTAX       CfprApManagedObjectId
    MAX-ACCESS   not-accessible
    STATUS       current
    DESCRIPTION
        "Instance identifier of the managed object."
    ::= { cfprApEtherRxStatsHistEntry 1 }

cfprApEtherRxStatsHistDn OBJECT-TYPE
    SYNTAX       CfprApManagedObjectDn
    MAX-ACCESS   read-only
    STATUS       current
    DESCRIPTION
        "Cisco Firepower ether:RxStatsHist:dn managed object property"
    ::= { cfprApEtherRxStatsHistEntry 2 }

cfprApEtherRxStatsHistRn OBJECT-TYPE
    SYNTAX       SnmpAdminString
    MAX-ACCESS   read-only
    STATUS       current
    DESCRIPTION
        "Cisco Firepower ether:RxStatsHist:rn managed object property"
    ::= { cfprApEtherRxStatsHistEntry 3 }

cfprApEtherRxStatsHistBroadcastPackets OBJECT-TYPE
    SYNTAX       Unsigned64
    MAX-ACCESS   read-only
    STATUS       current
    DESCRIPTION
        "Cisco Firepower ether:RxStatsHist:broadcastPackets
        managed object property"
    ::= { cfprApEtherRxStatsHistEntry 4 }

cfprApEtherRxStatsHistBroadcastPacketsDelta OBJECT-TYPE
    SYNTAX       Unsigned64
    MAX-ACCESS   read-only
    STATUS       current
    DESCRIPTION
        "Cisco Firepower ether:RxStatsHist:broadcastPacketsDelta
        managed object property"
    ::= { cfprApEtherRxStatsHistEntry 5 }

cfprApEtherRxStatsHistBroadcastPacketsDeltaAvg OBJECT-TYPE
    SYNTAX       Unsigned64
    MAX-ACCESS   read-only
    STATUS       current
    DESCRIPTION
        "Cisco Firepower ether:RxStatsHist:broadcastPacketsDeltaAvg
        managed object property"
    ::= { cfprApEtherRxStatsHistEntry 6 }

cfprApEtherRxStatsHistBroadcastPacketsDeltaMax OBJECT-TYPE
    SYNTAX       Unsigned64
    MAX-ACCESS   read-only
    STATUS       current
    DESCRIPTION
        "Cisco Firepower ether:RxStatsHist:broadcastPacketsDeltaMax
        managed object property"
    ::= { cfprApEtherRxStatsHistEntry 7 }

cfprApEtherRxStatsHistBroadcastPacketsDeltaMin OBJECT-TYPE
    SYNTAX       Unsigned64
    MAX-ACCESS   read-only
    STATUS       current
    DESCRIPTION
        "Cisco Firepower ether:RxStatsHist:broadcastPacketsDeltaMin
        managed object property"
    ::= { cfprApEtherRxStatsHistEntry 8 }

cfprApEtherRxStatsHistId OBJECT-TYPE
    SYNTAX       Unsigned64
    MAX-ACCESS   read-only
    STATUS       current
    DESCRIPTION
        "Cisco Firepower ether:RxStatsHist:id managed object property"
    ::= { cfprApEtherRxStatsHistEntry 9 }

cfprApEtherRxStatsHistJumboPackets OBJECT-TYPE
    SYNTAX       Unsigned64
    MAX-ACCESS   read-only
    STATUS       current
    DESCRIPTION
        "Cisco Firepower ether:RxStatsHist:jumboPackets
        managed object property"
    ::= { cfprApEtherRxStatsHistEntry 10 }

cfprApEtherRxStatsHistJumboPacketsDelta OBJECT-TYPE
    SYNTAX       Unsigned64
    MAX-ACCESS   read-only
    STATUS       current
    DESCRIPTION
        "Cisco Firepower ether:RxStatsHist:jumboPacketsDelta
        managed object property"
    ::= { cfprApEtherRxStatsHistEntry 11 }

cfprApEtherRxStatsHistJumboPacketsDeltaAvg OBJECT-TYPE
    SYNTAX       Unsigned64
    MAX-ACCESS   read-only
    STATUS       current
    DESCRIPTION
        "Cisco Firepower ether:RxStatsHist:jumboPacketsDeltaAvg
        managed object property"
    ::= { cfprApEtherRxStatsHistEntry 12 }

cfprApEtherRxStatsHistJumboPacketsDeltaMax OBJECT-TYPE
    SYNTAX       Unsigned64
    MAX-ACCESS   read-only
    STATUS       current
    DESCRIPTION
        "Cisco Firepower ether:RxStatsHist:jumboPacketsDeltaMax
        managed object property"
    ::= { cfprApEtherRxStatsHistEntry 13 }

cfprApEtherRxStatsHistJumboPacketsDeltaMin OBJECT-TYPE
    SYNTAX       Unsigned64
    MAX-ACCESS   read-only
    STATUS       current
    DESCRIPTION
        "Cisco Firepower ether:RxStatsHist:jumboPacketsDeltaMin
        managed object property"
    ::= { cfprApEtherRxStatsHistEntry 14 }

cfprApEtherRxStatsHistMostRecent OBJECT-TYPE
    SYNTAX       TruthValue
    MAX-ACCESS   read-only
    STATUS       current
    DESCRIPTION
        "Cisco Firepower ether:RxStatsHist:mostRecent managed
        object property"
    ::= { cfprApEtherRxStatsHistEntry 15 }

cfprApEtherRxStatsHistMulticastPackets OBJECT-TYPE
    SYNTAX       Unsigned64
    MAX-ACCESS   read-only
    STATUS       current
    DESCRIPTION
        "Cisco Firepower ether:RxStatsHist:multicastPackets
        managed object property"
    ::= { cfprApEtherRxStatsHistEntry 16 }

cfprApEtherRxStatsHistMulticastPacketsDelta OBJECT-TYPE
    SYNTAX       Unsigned64
    MAX-ACCESS   read-only
    STATUS       current
    DESCRIPTION
        "Cisco Firepower ether:RxStatsHist:multicastPacketsDelta
        managed object property"
    ::= { cfprApEtherRxStatsHistEntry 17 }

cfprApEtherRxStatsHistMulticastPacketsDeltaAvg OBJECT-TYPE
    SYNTAX       Unsigned64
    MAX-ACCESS   read-only
    STATUS       current
    DESCRIPTION
        "Cisco Firepower ether:RxStatsHist:multicastPacketsDeltaAvg
        managed object property"
    ::= { cfprApEtherRxStatsHistEntry 18 }

cfprApEtherRxStatsHistMulticastPacketsDeltaMax OBJECT-TYPE
    SYNTAX       Unsigned64
    MAX-ACCESS   read-only
    STATUS       current
    DESCRIPTION
        "Cisco Firepower ether:RxStatsHist:multicastPacketsDeltaMax
        managed object property"
    ::= { cfprApEtherRxStatsHistEntry 19 }

cfprApEtherRxStatsHistMulticastPacketsDeltaMin OBJECT-TYPE
    SYNTAX       Unsigned64
    MAX-ACCESS   read-only
    STATUS       current
    DESCRIPTION
        "Cisco Firepower ether:RxStatsHist:multicastPacketsDeltaMin
        managed object property"
    ::= { cfprApEtherRxStatsHistEntry 20 }

cfprApEtherRxStatsHistSuspect OBJECT-TYPE
    SYNTAX       TruthValue
    MAX-ACCESS   read-only
    STATUS       current
    DESCRIPTION
        "Cisco Firepower ether:RxStatsHist:suspect managed
        object property"
    ::= { cfprApEtherRxStatsHistEntry 21 }

cfprApEtherRxStatsHistThresholded OBJECT-TYPE
    SYNTAX       CfprApEtherRxStatsHistThresholded
    MAX-ACCESS   read-only
    STATUS       current
    DESCRIPTION
        "Cisco Firepower ether:RxStatsHist:thresholded
        managed object property"
    ::= { cfprApEtherRxStatsHistEntry 22 }

cfprApEtherRxStatsHistTimeCollected OBJECT-TYPE
    SYNTAX       DateAndTime
    MAX-ACCESS   read-only
    STATUS       current
    DESCRIPTION
        "Cisco Firepower ether:RxStatsHist:timeCollected
        managed object property"
    ::= { cfprApEtherRxStatsHistEntry 23 }

cfprApEtherRxStatsHistTotalBytes OBJECT-TYPE
    SYNTAX       Unsigned64
    MAX-ACCESS   read-only
    STATUS       current
    DESCRIPTION
        "Cisco Firepower ether:RxStatsHist:totalBytes managed
        object property"
    ::= { cfprApEtherRxStatsHistEntry 24 }

cfprApEtherRxStatsHistTotalBytesDelta OBJECT-TYPE
    SYNTAX       Unsigned64
    MAX-ACCESS   read-only
    STATUS       current
    DESCRIPTION
        "Cisco Firepower ether:RxStatsHist:totalBytesDelta
        managed object property"
    ::= { cfprApEtherRxStatsHistEntry 25 }

cfprApEtherRxStatsHistTotalBytesDeltaAvg OBJECT-TYPE
    SYNTAX       Unsigned64
    MAX-ACCESS   read-only
    STATUS       current
    DESCRIPTION
        "Cisco Firepower ether:RxStatsHist:totalBytesDeltaAvg
        managed object property"
    ::= { cfprApEtherRxStatsHistEntry 26 }

cfprApEtherRxStatsHistTotalBytesDeltaMax OBJECT-TYPE
    SYNTAX       Unsigned64
    MAX-ACCESS   read-only
    STATUS       current
    DESCRIPTION
        "Cisco Firepower ether:RxStatsHist:totalBytesDeltaMax
        managed object property"
    ::= { cfprApEtherRxStatsHistEntry 27 }

cfprApEtherRxStatsHistTotalBytesDeltaMin OBJECT-TYPE
    SYNTAX       Unsigned64
    MAX-ACCESS   read-only
    STATUS       current
    DESCRIPTION
        "Cisco Firepower ether:RxStatsHist:totalBytesDeltaMin
        managed object property"
    ::= { cfprApEtherRxStatsHistEntry 28 }

cfprApEtherRxStatsHistTotalPackets OBJECT-TYPE
    SYNTAX       Unsigned64
    MAX-ACCESS   read-only
    STATUS       current
    DESCRIPTION
        "Cisco Firepower ether:RxStatsHist:totalPackets
        managed object property"
    ::= { cfprApEtherRxStatsHistEntry 29 }

cfprApEtherRxStatsHistTotalPacketsDelta OBJECT-TYPE
    SYNTAX       Unsigned64
    MAX-ACCESS   read-only
    STATUS       current
    DESCRIPTION
        "Cisco Firepower ether:RxStatsHist:totalPacketsDelta
        managed object property"
    ::= { cfprApEtherRxStatsHistEntry 30 }

cfprApEtherRxStatsHistTotalPacketsDeltaAvg OBJECT-TYPE
    SYNTAX       Unsigned64
    MAX-ACCESS   read-only
    STATUS       current
    DESCRIPTION
        "Cisco Firepower ether:RxStatsHist:totalPacketsDeltaAvg
        managed object property"
    ::= { cfprApEtherRxStatsHistEntry 31 }

cfprApEtherRxStatsHistTotalPacketsDeltaMax OBJECT-TYPE
    SYNTAX       Unsigned64
    MAX-ACCESS   read-only
    STATUS       current
    DESCRIPTION
        "Cisco Firepower ether:RxStatsHist:totalPacketsDeltaMax
        managed object property"
    ::= { cfprApEtherRxStatsHistEntry 32 }

cfprApEtherRxStatsHistTotalPacketsDeltaMin OBJECT-TYPE
    SYNTAX       Unsigned64
    MAX-ACCESS   read-only
    STATUS       current
    DESCRIPTION
        "Cisco Firepower ether:RxStatsHist:totalPacketsDeltaMin
        managed object property"
    ::= { cfprApEtherRxStatsHistEntry 33 }

cfprApEtherRxStatsHistUnicastPackets OBJECT-TYPE
    SYNTAX       Unsigned64
    MAX-ACCESS   read-only
    STATUS       current
    DESCRIPTION
        "Cisco Firepower ether:RxStatsHist:unicastPackets
        managed object property"
    ::= { cfprApEtherRxStatsHistEntry 34 }

cfprApEtherRxStatsHistUnicastPacketsDelta OBJECT-TYPE
    SYNTAX       Unsigned64
    MAX-ACCESS   read-only
    STATUS       current
    DESCRIPTION
        "Cisco Firepower ether:RxStatsHist:unicastPacketsDelta
        managed object property"
    ::= { cfprApEtherRxStatsHistEntry 35 }

cfprApEtherRxStatsHistUnicastPacketsDeltaAvg OBJECT-TYPE
    SYNTAX       Unsigned64
    MAX-ACCESS   read-only
    STATUS       current
    DESCRIPTION
        "Cisco Firepower ether:RxStatsHist:unicastPacketsDeltaAvg
        managed object property"
    ::= { cfprApEtherRxStatsHistEntry 36 }

cfprApEtherRxStatsHistUnicastPacketsDeltaMax OBJECT-TYPE
    SYNTAX       Unsigned64
    MAX-ACCESS   read-only
    STATUS       current
    DESCRIPTION
        "Cisco Firepower ether:RxStatsHist:unicastPacketsDeltaMax
        managed object property"
    ::= { cfprApEtherRxStatsHistEntry 37 }

cfprApEtherRxStatsHistUnicastPacketsDeltaMin OBJECT-TYPE
    SYNTAX       Unsigned64
    MAX-ACCESS   read-only
    STATUS       current
    DESCRIPTION
        "Cisco Firepower ether:RxStatsHist:unicastPacketsDeltaMin
        managed object property"
    ::= { cfprApEtherRxStatsHistEntry 38 }

cfprApEtherServerIntFIoTable OBJECT-TYPE
    SYNTAX           SEQUENCE OF CfprApEtherServerIntFIoEntry
    MAX-ACCESS       not-accessible
    STATUS           current
    DESCRIPTION
        "Cisco Firepower ether:ServerIntFIo managed object table"
    ::= { cfprApEtherObjects 25 }

cfprApEtherServerIntFIoEntry OBJECT-TYPE
    SYNTAX           CfprApEtherServerIntFIoEntry
    MAX-ACCESS       not-accessible
    STATUS           current
    DESCRIPTION
        "Entry for the cfprApEtherServerIntFIoTable table."
    INDEX { cfprApEtherServerIntFIoInstanceId }
    ::= { cfprApEtherServerIntFIoTable 1 }

CfprApEtherServerIntFIoEntry ::= SEQUENCE {
    cfprApEtherServerIntFIoInstanceId                                CfprApManagedObjectId,
    cfprApEtherServerIntFIoDn                                        CfprApManagedObjectDn,
    cfprApEtherServerIntFIoRn                                        SnmpAdminString,
    cfprApEtherServerIntFIoAdminSpeed                                CfprApPortEthSpeed,
    cfprApEtherServerIntFIoAdminState                                CfprApEtherServerIntFIoAdminState,
    cfprApEtherServerIntFIoAggrPortId                                Gauge32,
    cfprApEtherServerIntFIoChassisId                                 Gauge32,
    cfprApEtherServerIntFIoEncap                                     CfprApPortEncap,
    cfprApEtherServerIntFIoEpDn                                      SnmpAdminString,
    cfprApEtherServerIntFIoFltAggr                                   Unsigned64,
    cfprApEtherServerIntFIoFsmDescr                                  SnmpAdminString,
    cfprApEtherServerIntFIoFsmPrev                                   SnmpAdminString,
    cfprApEtherServerIntFIoFsmProgr                                  Gauge32,
    cfprApEtherServerIntFIoFsmRmtInvErrCode                          Gauge32,
    cfprApEtherServerIntFIoFsmRmtInvErrDescr                         SnmpAdminString,
    cfprApEtherServerIntFIoFsmRmtInvRslt                             CfprApConditionRemoteInvRslt,
    cfprApEtherServerIntFIoFsmStageDescr                             SnmpAdminString,
    cfprApEtherServerIntFIoFsmStamp                                  DateAndTime,
    cfprApEtherServerIntFIoFsmStatus                                 SnmpAdminString,
    cfprApEtherServerIntFIoFsmTry                                    Gauge32,
    cfprApEtherServerIntFIoIfRole                                    CfprApEtherServerIntFIoIfRole,
    cfprApEtherServerIntFIoIfType                                    CfprApNetworkPhysEpIfType,
    cfprApEtherServerIntFIoLocale                                    CfprApEtherServerIntFIoLocale,
    cfprApEtherServerIntFIoMac                                       MacAddress,
    cfprApEtherServerIntFIoMode                                      CfprApPortMode,
    cfprApEtherServerIntFIoModel                                     SnmpAdminString,
    cfprApEtherServerIntFIoName                                      SnmpAdminString,
    cfprApEtherServerIntFIoNsSize                                    Gauge32,
    cfprApEtherServerIntFIoOperBorderAggrPortId                      Gauge32,
    cfprApEtherServerIntFIoOperBorderPortId                          Gauge32,
    cfprApEtherServerIntFIoOperBorderSlotId                          Gauge32,
    cfprApEtherServerIntFIoOperState                                 CfprApNetworkPortOperState,
    cfprApEtherServerIntFIoPeerAggrPortId                            Gauge32,
    cfprApEtherServerIntFIoPeerChassisId                             Gauge32,
    cfprApEtherServerIntFIoPeerDn                                    SnmpAdminString,
    cfprApEtherServerIntFIoPeerEncap                                 Gauge32,
    cfprApEtherServerIntFIoPeerPortId                                Gauge32,
    cfprApEtherServerIntFIoPeerSlotId                                Gauge32,
    cfprApEtherServerIntFIoPortId                                    Gauge32,
    cfprApEtherServerIntFIoRevision                                  SnmpAdminString,
    cfprApEtherServerIntFIoSerial                                    SnmpAdminString,
    cfprApEtherServerIntFIoSlotId                                    Gauge32,
    cfprApEtherServerIntFIoStateQual                                 SnmpAdminString,
    cfprApEtherServerIntFIoSwitchId                                  CfprApNetworkSwitchId,
    cfprApEtherServerIntFIoTransport                                 CfprApEtherServerIntFIoTransport,
    cfprApEtherServerIntFIoTs                                        DateAndTime,
    cfprApEtherServerIntFIoType                                      CfprApEtherServerIntFIoType,
    cfprApEtherServerIntFIoVendor                                    SnmpAdminString,
    cfprApEtherServerIntFIoXcvrType                                  CfprApEquipmentXcvrType
}

cfprApEtherServerIntFIoInstanceId OBJECT-TYPE
    SYNTAX       CfprApManagedObjectId
    MAX-ACCESS   not-accessible
    STATUS       current
    DESCRIPTION
        "Instance identifier of the managed object."
    ::= { cfprApEtherServerIntFIoEntry 1 }

cfprApEtherServerIntFIoDn OBJECT-TYPE
    SYNTAX       CfprApManagedObjectDn
    MAX-ACCESS   read-only
    STATUS       current
    DESCRIPTION
        "Cisco Firepower ether:ServerIntFIo:dn managed object property"
    ::= { cfprApEtherServerIntFIoEntry 2 }

cfprApEtherServerIntFIoRn OBJECT-TYPE
    SYNTAX       SnmpAdminString
    MAX-ACCESS   read-only
    STATUS       current
    DESCRIPTION
        "Cisco Firepower ether:ServerIntFIo:rn managed object property"
    ::= { cfprApEtherServerIntFIoEntry 3 }

cfprApEtherServerIntFIoAdminSpeed OBJECT-TYPE
    SYNTAX       CfprApPortEthSpeed
    MAX-ACCESS   read-only
    STATUS       current
    DESCRIPTION
        "Cisco Firepower ether:ServerIntFIo:adminSpeed
        managed object property"
    ::= { cfprApEtherServerIntFIoEntry 4 }

cfprApEtherServerIntFIoAdminState OBJECT-TYPE
    SYNTAX       CfprApEtherServerIntFIoAdminState
    MAX-ACCESS   read-only
    STATUS       current
    DESCRIPTION
        "Cisco Firepower ether:ServerIntFIo:adminState
        managed object property"
    ::= { cfprApEtherServerIntFIoEntry 5 }

cfprApEtherServerIntFIoAggrPortId OBJECT-TYPE
    SYNTAX       Gauge32
    MAX-ACCESS   read-only
    STATUS       current
    DESCRIPTION
        "Cisco Firepower ether:ServerIntFIo:aggrPortId
        managed object property"
    ::= { cfprApEtherServerIntFIoEntry 6 }

cfprApEtherServerIntFIoChassisId OBJECT-TYPE
    SYNTAX       Gauge32
    MAX-ACCESS   read-only
    STATUS       current
    DESCRIPTION
        "Cisco Firepower ether:ServerIntFIo:chassisId managed
        object property"
    ::= { cfprApEtherServerIntFIoEntry 7 }

cfprApEtherServerIntFIoEncap OBJECT-TYPE
    SYNTAX       CfprApPortEncap
    MAX-ACCESS   read-only
    STATUS       current
    DESCRIPTION
        "Cisco Firepower ether:ServerIntFIo:encap managed object property"
    ::= { cfprApEtherServerIntFIoEntry 8 }

cfprApEtherServerIntFIoEpDn OBJECT-TYPE
    SYNTAX       SnmpAdminString
    MAX-ACCESS   read-only
    STATUS       current
    DESCRIPTION
        "Cisco Firepower ether:ServerIntFIo:epDn managed object property"
    ::= { cfprApEtherServerIntFIoEntry 9 }

cfprApEtherServerIntFIoFltAggr OBJECT-TYPE
    SYNTAX       Unsigned64
    MAX-ACCESS   read-only
    STATUS       current
    DESCRIPTION
        "Cisco Firepower ether:ServerIntFIo:fltAggr managed
        object property"
    ::= { cfprApEtherServerIntFIoEntry 10 }

cfprApEtherServerIntFIoFsmDescr OBJECT-TYPE
    SYNTAX       SnmpAdminString
    MAX-ACCESS   read-only
    STATUS       current
    DESCRIPTION
        "Cisco Firepower ether:ServerIntFIo:fsmDescr managed
        object property"
    ::= { cfprApEtherServerIntFIoEntry 11 }

cfprApEtherServerIntFIoFsmPrev OBJECT-TYPE
    SYNTAX       SnmpAdminString
    MAX-ACCESS   read-only
    STATUS       current
    DESCRIPTION
        "Cisco Firepower ether:ServerIntFIo:fsmPrev managed
        object property"
    ::= { cfprApEtherServerIntFIoEntry 12 }

cfprApEtherServerIntFIoFsmProgr OBJECT-TYPE
    SYNTAX       Gauge32
    MAX-ACCESS   read-only
    STATUS       current
    DESCRIPTION
        "Cisco Firepower ether:ServerIntFIo:fsmProgr managed
        object property"
    ::= { cfprApEtherServerIntFIoEntry 13 }

cfprApEtherServerIntFIoFsmRmtInvErrCode OBJECT-TYPE
    SYNTAX       Gauge32
    MAX-ACCESS   read-only
    STATUS       current
    DESCRIPTION
        "Cisco Firepower ether:ServerIntFIo:fsmRmtInvErrCode
        managed object property"
    ::= { cfprApEtherServerIntFIoEntry 14 }

cfprApEtherServerIntFIoFsmRmtInvErrDescr OBJECT-TYPE
    SYNTAX       SnmpAdminString
    MAX-ACCESS   read-only
    STATUS       current
    DESCRIPTION
        "Cisco Firepower ether:ServerIntFIo:fsmRmtInvErrDescr
        managed object property"
    ::= { cfprApEtherServerIntFIoEntry 15 }

cfprApEtherServerIntFIoFsmRmtInvRslt OBJECT-TYPE
    SYNTAX       CfprApConditionRemoteInvRslt
    MAX-ACCESS   read-only
    STATUS       current
    DESCRIPTION
        "Cisco Firepower ether:ServerIntFIo:fsmRmtInvRslt
        managed object property"
    ::= { cfprApEtherServerIntFIoEntry 16 }

cfprApEtherServerIntFIoFsmStageDescr OBJECT-TYPE
    SYNTAX       SnmpAdminString
    MAX-ACCESS   read-only
    STATUS       current
    DESCRIPTION
        "Cisco Firepower ether:ServerIntFIo:fsmStageDescr
        managed object property"
    ::= { cfprApEtherServerIntFIoEntry 17 }

cfprApEtherServerIntFIoFsmStamp OBJECT-TYPE
    SYNTAX       DateAndTime
    MAX-ACCESS   read-only
    STATUS       current
    DESCRIPTION
        "Cisco Firepower ether:ServerIntFIo:fsmStamp managed
        object property"
    ::= { cfprApEtherServerIntFIoEntry 18 }

cfprApEtherServerIntFIoFsmStatus OBJECT-TYPE
    SYNTAX       SnmpAdminString
    MAX-ACCESS   read-only
    STATUS       current
    DESCRIPTION
        "Cisco Firepower ether:ServerIntFIo:fsmStatus managed
        object property"
    ::= { cfprApEtherServerIntFIoEntry 19 }

cfprApEtherServerIntFIoFsmTry OBJECT-TYPE
    SYNTAX       Gauge32
    MAX-ACCESS   read-only
    STATUS       current
    DESCRIPTION
        "Cisco Firepower ether:ServerIntFIo:fsmTry managed
        object property"
    ::= { cfprApEtherServerIntFIoEntry 20 }

cfprApEtherServerIntFIoIfRole OBJECT-TYPE
    SYNTAX       CfprApEtherServerIntFIoIfRole
    MAX-ACCESS   read-only
    STATUS       current
    DESCRIPTION
        "Cisco Firepower ether:ServerIntFIo:ifRole managed
        object property"
    ::= { cfprApEtherServerIntFIoEntry 21 }

cfprApEtherServerIntFIoIfType OBJECT-TYPE
    SYNTAX       CfprApNetworkPhysEpIfType
    MAX-ACCESS   read-only
    STATUS       current
    DESCRIPTION
        "Cisco Firepower ether:ServerIntFIo:ifType managed
        object property"
    ::= { cfprApEtherServerIntFIoEntry 22 }

cfprApEtherServerIntFIoLocale OBJECT-TYPE
    SYNTAX       CfprApEtherServerIntFIoLocale
    MAX-ACCESS   read-only
    STATUS       current
    DESCRIPTION
        "Cisco Firepower ether:ServerIntFIo:locale managed
        object property"
    ::= { cfprApEtherServerIntFIoEntry 23 }

cfprApEtherServerIntFIoMac OBJECT-TYPE
    SYNTAX       MacAddress
    MAX-ACCESS   read-only
    STATUS       current
    DESCRIPTION
        "Cisco Firepower ether:ServerIntFIo:mac managed object property"
    ::= { cfprApEtherServerIntFIoEntry 24 }

cfprApEtherServerIntFIoMode OBJECT-TYPE
    SYNTAX       CfprApPortMode
    MAX-ACCESS   read-only
    STATUS       current
    DESCRIPTION
        "Cisco Firepower ether:ServerIntFIo:mode managed object property"
    ::= { cfprApEtherServerIntFIoEntry 25 }

cfprApEtherServerIntFIoModel OBJECT-TYPE
    SYNTAX       SnmpAdminString
    MAX-ACCESS   read-only
    STATUS       current
    DESCRIPTION
        "Cisco Firepower ether:ServerIntFIo:model managed object property"
    ::= { cfprApEtherServerIntFIoEntry 26 }

cfprApEtherServerIntFIoName OBJECT-TYPE
    SYNTAX       SnmpAdminString
    MAX-ACCESS   read-only
    STATUS       current
    DESCRIPTION
        "Cisco Firepower ether:ServerIntFIo:name managed object property"
    ::= { cfprApEtherServerIntFIoEntry 27 }

cfprApEtherServerIntFIoNsSize OBJECT-TYPE
    SYNTAX       Gauge32
    MAX-ACCESS   read-only
    STATUS       current
    DESCRIPTION
        "Cisco Firepower ether:ServerIntFIo:nsSize managed
        object property"
    ::= { cfprApEtherServerIntFIoEntry 28 }

cfprApEtherServerIntFIoOperBorderAggrPortId OBJECT-TYPE
    SYNTAX       Gauge32
    MAX-ACCESS   read-only
    STATUS       current
    DESCRIPTION
        "Cisco Firepower ether:ServerIntFIo:operBorderAggrPortId
        managed object property"
    ::= { cfprApEtherServerIntFIoEntry 29 }

cfprApEtherServerIntFIoOperBorderPortId OBJECT-TYPE
    SYNTAX       Gauge32
    MAX-ACCESS   read-only
    STATUS       current
    DESCRIPTION
        "Cisco Firepower ether:ServerIntFIo:operBorderPortId
        managed object property"
    ::= { cfprApEtherServerIntFIoEntry 30 }

cfprApEtherServerIntFIoOperBorderSlotId OBJECT-TYPE
    SYNTAX       Gauge32
    MAX-ACCESS   read-only
    STATUS       current
    DESCRIPTION
        "Cisco Firepower ether:ServerIntFIo:operBorderSlotId
        managed object property"
    ::= { cfprApEtherServerIntFIoEntry 31 }

cfprApEtherServerIntFIoOperState OBJECT-TYPE
    SYNTAX       CfprApNetworkPortOperState
    MAX-ACCESS   read-only
    STATUS       current
    DESCRIPTION
        "Cisco Firepower ether:ServerIntFIo:operState managed
        object property"
    ::= { cfprApEtherServerIntFIoEntry 32 }

cfprApEtherServerIntFIoPeerAggrPortId OBJECT-TYPE
    SYNTAX       Gauge32
    MAX-ACCESS   read-only
    STATUS       current
    DESCRIPTION
        "Cisco Firepower ether:ServerIntFIo:peerAggrPortId
        managed object property"
    ::= { cfprApEtherServerIntFIoEntry 33 }

cfprApEtherServerIntFIoPeerChassisId OBJECT-TYPE
    SYNTAX       Gauge32
    MAX-ACCESS   read-only
    STATUS       current
    DESCRIPTION
        "Cisco Firepower ether:ServerIntFIo:peerChassisId
        managed object property"
    ::= { cfprApEtherServerIntFIoEntry 34 }

cfprApEtherServerIntFIoPeerDn OBJECT-TYPE
    SYNTAX       SnmpAdminString
    MAX-ACCESS   read-only
    STATUS       current
    DESCRIPTION
        "Cisco Firepower ether:ServerIntFIo:peerDn managed
        object property"
    ::= { cfprApEtherServerIntFIoEntry 35 }

cfprApEtherServerIntFIoPeerEncap OBJECT-TYPE
    SYNTAX       Gauge32
    MAX-ACCESS   read-only
    STATUS       current
    DESCRIPTION
        "Cisco Firepower ether:ServerIntFIo:peerEncap managed
        object property"
    ::= { cfprApEtherServerIntFIoEntry 36 }

cfprApEtherServerIntFIoPeerPortId OBJECT-TYPE
    SYNTAX       Gauge32
    MAX-ACCESS   read-only
    STATUS       current
    DESCRIPTION
        "Cisco Firepower ether:ServerIntFIo:peerPortId
        managed object property"
    ::= { cfprApEtherServerIntFIoEntry 37 }

cfprApEtherServerIntFIoPeerSlotId OBJECT-TYPE
    SYNTAX       Gauge32
    MAX-ACCESS   read-only
    STATUS       current
    DESCRIPTION
        "Cisco Firepower ether:ServerIntFIo:peerSlotId
        managed object property"
    ::= { cfprApEtherServerIntFIoEntry 38 }

cfprApEtherServerIntFIoPortId OBJECT-TYPE
    SYNTAX       Gauge32
    MAX-ACCESS   read-only
    STATUS       current
    DESCRIPTION
        "Cisco Firepower ether:ServerIntFIo:portId managed
        object property"
    ::= { cfprApEtherServerIntFIoEntry 39 }

cfprApEtherServerIntFIoRevision OBJECT-TYPE
    SYNTAX       SnmpAdminString
    MAX-ACCESS   read-only
    STATUS       current
    DESCRIPTION
        "Cisco Firepower ether:ServerIntFIo:revision managed
        object property"
    ::= { cfprApEtherServerIntFIoEntry 40 }

cfprApEtherServerIntFIoSerial OBJECT-TYPE
    SYNTAX       SnmpAdminString
    MAX-ACCESS   read-only
    STATUS       current
    DESCRIPTION
        "Cisco Firepower ether:ServerIntFIo:serial managed
        object property"
    ::= { cfprApEtherServerIntFIoEntry 41 }

cfprApEtherServerIntFIoSlotId OBJECT-TYPE
    SYNTAX       Gauge32
    MAX-ACCESS   read-only
    STATUS       current
    DESCRIPTION
        "Cisco Firepower ether:ServerIntFIo:slotId managed
        object property"
    ::= { cfprApEtherServerIntFIoEntry 42 }

cfprApEtherServerIntFIoStateQual OBJECT-TYPE
    SYNTAX       SnmpAdminString
    MAX-ACCESS   read-only
    STATUS       current
    DESCRIPTION
        "Cisco Firepower ether:ServerIntFIo:stateQual managed
        object property"
    ::= { cfprApEtherServerIntFIoEntry 43 }

cfprApEtherServerIntFIoSwitchId OBJECT-TYPE
    SYNTAX       CfprApNetworkSwitchId
    MAX-ACCESS   read-only
    STATUS       current
    DESCRIPTION
        "Cisco Firepower ether:ServerIntFIo:switchId managed
        object property"
    ::= { cfprApEtherServerIntFIoEntry 44 }

cfprApEtherServerIntFIoTransport OBJECT-TYPE
    SYNTAX       CfprApEtherServerIntFIoTransport
    MAX-ACCESS   read-only
    STATUS       current
    DESCRIPTION
        "Cisco Firepower ether:ServerIntFIo:transport managed
        object property"
    ::= { cfprApEtherServerIntFIoEntry 45 }

cfprApEtherServerIntFIoTs OBJECT-TYPE
    SYNTAX       DateAndTime
    MAX-ACCESS   read-only
    STATUS       current
    DESCRIPTION
        "Cisco Firepower ether:ServerIntFIo:ts managed object property"
    ::= { cfprApEtherServerIntFIoEntry 46 }

cfprApEtherServerIntFIoType OBJECT-TYPE
    SYNTAX       CfprApEtherServerIntFIoType
    MAX-ACCESS   read-only
    STATUS       current
    DESCRIPTION
        "Cisco Firepower ether:ServerIntFIo:type managed object property"
    ::= { cfprApEtherServerIntFIoEntry 47 }

cfprApEtherServerIntFIoVendor OBJECT-TYPE
    SYNTAX       SnmpAdminString
    MAX-ACCESS   read-only
    STATUS       current
    DESCRIPTION
        "Cisco Firepower ether:ServerIntFIo:vendor managed
        object property"
    ::= { cfprApEtherServerIntFIoEntry 48 }

cfprApEtherServerIntFIoXcvrType OBJECT-TYPE
    SYNTAX       CfprApEquipmentXcvrType
    MAX-ACCESS   read-only
    STATUS       current
    DESCRIPTION
        "Cisco Firepower ether:ServerIntFIo:xcvrType managed
        object property"
    ::= { cfprApEtherServerIntFIoEntry 49 }

cfprApEtherServerIntFIoFsmTable OBJECT-TYPE
    SYNTAX           SEQUENCE OF CfprApEtherServerIntFIoFsmEntry
    MAX-ACCESS       not-accessible
    STATUS           current
    DESCRIPTION
        "Cisco Firepower ether:ServerIntFIoFsm managed object table"
    ::= { cfprApEtherObjects 26 }

cfprApEtherServerIntFIoFsmEntry OBJECT-TYPE
    SYNTAX           CfprApEtherServerIntFIoFsmEntry
    MAX-ACCESS       not-accessible
    STATUS           current
    DESCRIPTION
        "Entry for the cfprApEtherServerIntFIoFsmTable table."
    INDEX { cfprApEtherServerIntFIoFsmInstanceId }
    ::= { cfprApEtherServerIntFIoFsmTable 1 }

CfprApEtherServerIntFIoFsmEntry ::= SEQUENCE {
    cfprApEtherServerIntFIoFsmInstanceId                             CfprApManagedObjectId,
    cfprApEtherServerIntFIoFsmDn                                     CfprApManagedObjectDn,
    cfprApEtherServerIntFIoFsmRn                                     SnmpAdminString,
    cfprApEtherServerIntFIoFsmCompletionTime                         DateAndTime,
    cfprApEtherServerIntFIoFsmCurrentFsm                             CfprApEtherServerIntFIoFsmCurrentFsm,
    cfprApEtherServerIntFIoFsmDescrData                              SnmpAdminString,
    cfprApEtherServerIntFIoFsmFsmStatus                              CfprApFsmFsmStageStatus,
    cfprApEtherServerIntFIoFsmProgress                               Gauge32,
    cfprApEtherServerIntFIoFsmRmtErrCode                             Gauge32,
    cfprApEtherServerIntFIoFsmRmtErrDescr                            SnmpAdminString,
    cfprApEtherServerIntFIoFsmRmtRslt                                CfprApConditionRemoteInvRslt
}

cfprApEtherServerIntFIoFsmInstanceId OBJECT-TYPE
    SYNTAX       CfprApManagedObjectId
    MAX-ACCESS   not-accessible
    STATUS       current
    DESCRIPTION
        "Instance identifier of the managed object."
    ::= { cfprApEtherServerIntFIoFsmEntry 1 }

cfprApEtherServerIntFIoFsmDn OBJECT-TYPE
    SYNTAX       CfprApManagedObjectDn
    MAX-ACCESS   read-only
    STATUS       current
    DESCRIPTION
        "Cisco Firepower ether:ServerIntFIoFsm:dn managed object property"
    ::= { cfprApEtherServerIntFIoFsmEntry 2 }

cfprApEtherServerIntFIoFsmRn OBJECT-TYPE
    SYNTAX       SnmpAdminString
    MAX-ACCESS   read-only
    STATUS       current
    DESCRIPTION
        "Cisco Firepower ether:ServerIntFIoFsm:rn managed object property"
    ::= { cfprApEtherServerIntFIoFsmEntry 3 }

cfprApEtherServerIntFIoFsmCompletionTime OBJECT-TYPE
    SYNTAX       DateAndTime
    MAX-ACCESS   read-only
    STATUS       current
    DESCRIPTION
        "Cisco Firepower ether:ServerIntFIoFsm:completionTime
        managed object property"
    ::= { cfprApEtherServerIntFIoFsmEntry 4 }

cfprApEtherServerIntFIoFsmCurrentFsm OBJECT-TYPE
    SYNTAX       CfprApEtherServerIntFIoFsmCurrentFsm
    MAX-ACCESS   read-only
    STATUS       current
    DESCRIPTION
        "Cisco Firepower ether:ServerIntFIoFsm:currentFsm
        managed object property"
    ::= { cfprApEtherServerIntFIoFsmEntry 5 }

cfprApEtherServerIntFIoFsmDescrData OBJECT-TYPE
    SYNTAX       SnmpAdminString
    MAX-ACCESS   read-only
    STATUS       current
    DESCRIPTION
        "Cisco Firepower ether:ServerIntFIoFsm:descr managed
        object property"
    ::= { cfprApEtherServerIntFIoFsmEntry 6 }

cfprApEtherServerIntFIoFsmFsmStatus OBJECT-TYPE
    SYNTAX       CfprApFsmFsmStageStatus
    MAX-ACCESS   read-only
    STATUS       current
    DESCRIPTION
        "Cisco Firepower ether:ServerIntFIoFsm:fsmStatus
        managed object property"
    ::= { cfprApEtherServerIntFIoFsmEntry 7 }

cfprApEtherServerIntFIoFsmProgress OBJECT-TYPE
    SYNTAX       Gauge32
    MAX-ACCESS   read-only
    STATUS       current
    DESCRIPTION
        "Cisco Firepower ether:ServerIntFIoFsm:progress
        managed object property"
    ::= { cfprApEtherServerIntFIoFsmEntry 8 }

cfprApEtherServerIntFIoFsmRmtErrCode OBJECT-TYPE
    SYNTAX       Gauge32
    MAX-ACCESS   read-only
    STATUS       current
    DESCRIPTION
        "Cisco Firepower ether:ServerIntFIoFsm:rmtErrCode
        managed object property"
    ::= { cfprApEtherServerIntFIoFsmEntry 9 }

cfprApEtherServerIntFIoFsmRmtErrDescr OBJECT-TYPE
    SYNTAX       SnmpAdminString
    MAX-ACCESS   read-only
    STATUS       current
    DESCRIPTION
        "Cisco Firepower ether:ServerIntFIoFsm:rmtErrDescr
        managed object property"
    ::= { cfprApEtherServerIntFIoFsmEntry 10 }

cfprApEtherServerIntFIoFsmRmtRslt OBJECT-TYPE
    SYNTAX       CfprApConditionRemoteInvRslt
    MAX-ACCESS   read-only
    STATUS       current
    DESCRIPTION
        "Cisco Firepower ether:ServerIntFIoFsm:rmtRslt
        managed object property"
    ::= { cfprApEtherServerIntFIoFsmEntry 11 }

cfprApEtherServerIntFIoFsmStageTable OBJECT-TYPE
    SYNTAX           SEQUENCE OF CfprApEtherServerIntFIoFsmStageEntry
    MAX-ACCESS       not-accessible
    STATUS           current
    DESCRIPTION
        "Cisco Firepower ether:ServerIntFIoFsmStage managed object table"
    ::= { cfprApEtherObjects 27 }

cfprApEtherServerIntFIoFsmStageEntry OBJECT-TYPE
    SYNTAX           CfprApEtherServerIntFIoFsmStageEntry
    MAX-ACCESS       not-accessible
    STATUS           current
    DESCRIPTION
        "Entry for the cfprApEtherServerIntFIoFsmStageTable table."
    INDEX { cfprApEtherServerIntFIoFsmStageInstanceId }
    ::= { cfprApEtherServerIntFIoFsmStageTable 1 }

CfprApEtherServerIntFIoFsmStageEntry ::= SEQUENCE {
    cfprApEtherServerIntFIoFsmStageInstanceId                        CfprApManagedObjectId,
    cfprApEtherServerIntFIoFsmStageDn                                CfprApManagedObjectDn,
    cfprApEtherServerIntFIoFsmStageRn                                SnmpAdminString,
    cfprApEtherServerIntFIoFsmStageDescrData                         SnmpAdminString,
    cfprApEtherServerIntFIoFsmStageLastUpdateTime                    DateAndTime,
    cfprApEtherServerIntFIoFsmStageName                              CfprApEtherServerIntFIoFsmStageName,
    cfprApEtherServerIntFIoFsmStageOrder                             Gauge32,
    cfprApEtherServerIntFIoFsmStageRetry                             Gauge32,
    cfprApEtherServerIntFIoFsmStageStageStatus                       CfprApFsmFsmStageStatus
}

cfprApEtherServerIntFIoFsmStageInstanceId OBJECT-TYPE
    SYNTAX       CfprApManagedObjectId
    MAX-ACCESS   not-accessible
    STATUS       current
    DESCRIPTION
        "Instance identifier of the managed object."
    ::= { cfprApEtherServerIntFIoFsmStageEntry 1 }

cfprApEtherServerIntFIoFsmStageDn OBJECT-TYPE
    SYNTAX       CfprApManagedObjectDn
    MAX-ACCESS   read-only
    STATUS       current
    DESCRIPTION
        "Cisco Firepower ether:ServerIntFIoFsmStage:dn
        managed object property"
    ::= { cfprApEtherServerIntFIoFsmStageEntry 2 }

cfprApEtherServerIntFIoFsmStageRn OBJECT-TYPE
    SYNTAX       SnmpAdminString
    MAX-ACCESS   read-only
    STATUS       current
    DESCRIPTION
        "Cisco Firepower ether:ServerIntFIoFsmStage:rn
        managed object property"
    ::= { cfprApEtherServerIntFIoFsmStageEntry 3 }

cfprApEtherServerIntFIoFsmStageDescrData OBJECT-TYPE
    SYNTAX       SnmpAdminString
    MAX-ACCESS   read-only
    STATUS       current
    DESCRIPTION
        "Cisco Firepower ether:ServerIntFIoFsmStage:descr
        managed object property"
    ::= { cfprApEtherServerIntFIoFsmStageEntry 4 }

cfprApEtherServerIntFIoFsmStageLastUpdateTime OBJECT-TYPE
    SYNTAX       DateAndTime
    MAX-ACCESS   read-only
    STATUS       current
    DESCRIPTION
        "Cisco Firepower ether:ServerIntFIoFsmStage:lastUpdateTime
        managed object property"
    ::= { cfprApEtherServerIntFIoFsmStageEntry 5 }

cfprApEtherServerIntFIoFsmStageName OBJECT-TYPE
    SYNTAX       CfprApEtherServerIntFIoFsmStageName
    MAX-ACCESS   read-only
    STATUS       current
    DESCRIPTION
        "Cisco Firepower ether:ServerIntFIoFsmStage:name
        managed object property"
    ::= { cfprApEtherServerIntFIoFsmStageEntry 6 }

cfprApEtherServerIntFIoFsmStageOrder OBJECT-TYPE
    SYNTAX       Gauge32
    MAX-ACCESS   read-only
    STATUS       current
    DESCRIPTION
        "Cisco Firepower ether:ServerIntFIoFsmStage:order
        managed object property"
    ::= { cfprApEtherServerIntFIoFsmStageEntry 7 }

cfprApEtherServerIntFIoFsmStageRetry OBJECT-TYPE
    SYNTAX       Gauge32
    MAX-ACCESS   read-only
    STATUS       current
    DESCRIPTION
        "Cisco Firepower ether:ServerIntFIoFsmStage:retry
        managed object property"
    ::= { cfprApEtherServerIntFIoFsmStageEntry 8 }

cfprApEtherServerIntFIoFsmStageStageStatus OBJECT-TYPE
    SYNTAX       CfprApFsmFsmStageStatus
    MAX-ACCESS   read-only
    STATUS       current
    DESCRIPTION
        "Cisco Firepower ether:ServerIntFIoFsmStage:stageStatus
        managed object property"
    ::= { cfprApEtherServerIntFIoFsmStageEntry 9 }

cfprApEtherServerIntFIoFsmTaskTable OBJECT-TYPE
    SYNTAX           SEQUENCE OF CfprApEtherServerIntFIoFsmTaskEntry
    MAX-ACCESS       not-accessible
    STATUS           current
    DESCRIPTION
        "Cisco Firepower ether:ServerIntFIoFsmTask managed object table"
    ::= { cfprApEtherObjects 28 }

cfprApEtherServerIntFIoFsmTaskEntry OBJECT-TYPE
    SYNTAX           CfprApEtherServerIntFIoFsmTaskEntry
    MAX-ACCESS       not-accessible
    STATUS           current
    DESCRIPTION
        "Entry for the cfprApEtherServerIntFIoFsmTaskTable table."
    INDEX { cfprApEtherServerIntFIoFsmTaskInstanceId }
    ::= { cfprApEtherServerIntFIoFsmTaskTable 1 }

CfprApEtherServerIntFIoFsmTaskEntry ::= SEQUENCE {
    cfprApEtherServerIntFIoFsmTaskInstanceId                         CfprApManagedObjectId,
    cfprApEtherServerIntFIoFsmTaskDn                                 CfprApManagedObjectDn,
    cfprApEtherServerIntFIoFsmTaskRn                                 SnmpAdminString,
    cfprApEtherServerIntFIoFsmTaskCompletion                         CfprApFsmCompletion,
    cfprApEtherServerIntFIoFsmTaskFlags                              CfprApFsmFlags,
    cfprApEtherServerIntFIoFsmTaskItem                               CfprApEtherServerIntFIoFsmTaskItem,
    cfprApEtherServerIntFIoFsmTaskSeqId                              Gauge32
}

cfprApEtherServerIntFIoFsmTaskInstanceId OBJECT-TYPE
    SYNTAX       CfprApManagedObjectId
    MAX-ACCESS   not-accessible
    STATUS       current
    DESCRIPTION
        "Instance identifier of the managed object."
    ::= { cfprApEtherServerIntFIoFsmTaskEntry 1 }

cfprApEtherServerIntFIoFsmTaskDn OBJECT-TYPE
    SYNTAX       CfprApManagedObjectDn
    MAX-ACCESS   read-only
    STATUS       current
    DESCRIPTION
        "Cisco Firepower ether:ServerIntFIoFsmTask:dn managed
        object property"
    ::= { cfprApEtherServerIntFIoFsmTaskEntry 2 }

cfprApEtherServerIntFIoFsmTaskRn OBJECT-TYPE
    SYNTAX       SnmpAdminString
    MAX-ACCESS   read-only
    STATUS       current
    DESCRIPTION
        "Cisco Firepower ether:ServerIntFIoFsmTask:rn managed
        object property"
    ::= { cfprApEtherServerIntFIoFsmTaskEntry 3 }

cfprApEtherServerIntFIoFsmTaskCompletion OBJECT-TYPE
    SYNTAX       CfprApFsmCompletion
    MAX-ACCESS   read-only
    STATUS       current
    DESCRIPTION
        "Cisco Firepower ether:ServerIntFIoFsmTask:completion
        managed object property"
    ::= { cfprApEtherServerIntFIoFsmTaskEntry 4 }

cfprApEtherServerIntFIoFsmTaskFlags OBJECT-TYPE
    SYNTAX       CfprApFsmFlags
    MAX-ACCESS   read-only
    STATUS       current
    DESCRIPTION
        "Cisco Firepower ether:ServerIntFIoFsmTask:flags
        managed object property"
    ::= { cfprApEtherServerIntFIoFsmTaskEntry 5 }

cfprApEtherServerIntFIoFsmTaskItem OBJECT-TYPE
    SYNTAX       CfprApEtherServerIntFIoFsmTaskItem
    MAX-ACCESS   read-only
    STATUS       current
    DESCRIPTION
        "Cisco Firepower ether:ServerIntFIoFsmTask:item
        managed object property"
    ::= { cfprApEtherServerIntFIoFsmTaskEntry 6 }

cfprApEtherServerIntFIoFsmTaskSeqId OBJECT-TYPE
    SYNTAX       Gauge32
    MAX-ACCESS   read-only
    STATUS       current
    DESCRIPTION
        "Cisco Firepower ether:ServerIntFIoFsmTask:seqId
        managed object property"
    ::= { cfprApEtherServerIntFIoFsmTaskEntry 7 }

cfprApEtherServerIntFIoPcTable OBJECT-TYPE
    SYNTAX           SEQUENCE OF CfprApEtherServerIntFIoPcEntry
    MAX-ACCESS       not-accessible
    STATUS           current
    DESCRIPTION
        "Cisco Firepower ether:ServerIntFIoPc managed object table"
    ::= { cfprApEtherObjects 29 }

cfprApEtherServerIntFIoPcEntry OBJECT-TYPE
    SYNTAX           CfprApEtherServerIntFIoPcEntry
    MAX-ACCESS       not-accessible
    STATUS           current
    DESCRIPTION
        "Entry for the cfprApEtherServerIntFIoPcTable table."
    INDEX { cfprApEtherServerIntFIoPcInstanceId }
    ::= { cfprApEtherServerIntFIoPcTable 1 }

CfprApEtherServerIntFIoPcEntry ::= SEQUENCE {
    cfprApEtherServerIntFIoPcInstanceId                              CfprApManagedObjectId,
    cfprApEtherServerIntFIoPcDn                                      CfprApManagedObjectDn,
    cfprApEtherServerIntFIoPcRn                                      SnmpAdminString,
    cfprApEtherServerIntFIoPcChassisId                               Gauge32,
    cfprApEtherServerIntFIoPcEpDn                                    SnmpAdminString,
    cfprApEtherServerIntFIoPcFltAggr                                 Unsigned64,
    cfprApEtherServerIntFIoPcIfRole                                  CfprApEtherServerIntFIoPcIfRole,
    cfprApEtherServerIntFIoPcIfType                                  CfprApEtherCIoEpIfType,
    cfprApEtherServerIntFIoPcLocale                                  CfprApEtherInternalPcLocale,
    cfprApEtherServerIntFIoPcName                                    SnmpAdminString,
    cfprApEtherServerIntFIoPcOperSpeed                               CfprApPortEthSpeed,
    cfprApEtherServerIntFIoPcOperState                               CfprApNetworkPortOperState,
    cfprApEtherServerIntFIoPcPeerDn                                  SnmpAdminString,
    cfprApEtherServerIntFIoPcPortId                                  CfprApEtherServerIntFIoPcPortId,
    cfprApEtherServerIntFIoPcStateQual                               SnmpAdminString,
    cfprApEtherServerIntFIoPcSwitchId                                CfprApNetworkSwitchId,
    cfprApEtherServerIntFIoPcTransport                               CfprApEtherServerIntFIoPcTransport,
    cfprApEtherServerIntFIoPcType                                    CfprApEtherServerIntFIoPcType
}

cfprApEtherServerIntFIoPcInstanceId OBJECT-TYPE
    SYNTAX       CfprApManagedObjectId
    MAX-ACCESS   not-accessible
    STATUS       current
    DESCRIPTION
        "Instance identifier of the managed object."
    ::= { cfprApEtherServerIntFIoPcEntry 1 }

cfprApEtherServerIntFIoPcDn OBJECT-TYPE
    SYNTAX       CfprApManagedObjectDn
    MAX-ACCESS   read-only
    STATUS       current
    DESCRIPTION
        "Cisco Firepower ether:ServerIntFIoPc:dn managed object property"
    ::= { cfprApEtherServerIntFIoPcEntry 2 }

cfprApEtherServerIntFIoPcRn OBJECT-TYPE
    SYNTAX       SnmpAdminString
    MAX-ACCESS   read-only
    STATUS       current
    DESCRIPTION
        "Cisco Firepower ether:ServerIntFIoPc:rn managed object property"
    ::= { cfprApEtherServerIntFIoPcEntry 3 }

cfprApEtherServerIntFIoPcChassisId OBJECT-TYPE
    SYNTAX       Gauge32
    MAX-ACCESS   read-only
    STATUS       current
    DESCRIPTION
        "Cisco Firepower ether:ServerIntFIoPc:chassisId
        managed object property"
    ::= { cfprApEtherServerIntFIoPcEntry 4 }

cfprApEtherServerIntFIoPcEpDn OBJECT-TYPE
    SYNTAX       SnmpAdminString
    MAX-ACCESS   read-only
    STATUS       current
    DESCRIPTION
        "Cisco Firepower ether:ServerIntFIoPc:epDn managed
        object property"
    ::= { cfprApEtherServerIntFIoPcEntry 5 }

cfprApEtherServerIntFIoPcFltAggr OBJECT-TYPE
    SYNTAX       Unsigned64
    MAX-ACCESS   read-only
    STATUS       current
    DESCRIPTION
        "Cisco Firepower ether:ServerIntFIoPc:fltAggr managed
        object property"
    ::= { cfprApEtherServerIntFIoPcEntry 6 }

cfprApEtherServerIntFIoPcIfRole OBJECT-TYPE
    SYNTAX       CfprApEtherServerIntFIoPcIfRole
    MAX-ACCESS   read-only
    STATUS       current
    DESCRIPTION
        "Cisco Firepower ether:ServerIntFIoPc:ifRole managed
        object property"
    ::= { cfprApEtherServerIntFIoPcEntry 7 }

cfprApEtherServerIntFIoPcIfType OBJECT-TYPE
    SYNTAX       CfprApEtherCIoEpIfType
    MAX-ACCESS   read-only
    STATUS       current
    DESCRIPTION
        "Cisco Firepower ether:ServerIntFIoPc:ifType managed
        object property"
    ::= { cfprApEtherServerIntFIoPcEntry 8 }

cfprApEtherServerIntFIoPcLocale OBJECT-TYPE
    SYNTAX       CfprApEtherInternalPcLocale
    MAX-ACCESS   read-only
    STATUS       current
    DESCRIPTION
        "Cisco Firepower ether:ServerIntFIoPc:locale managed
        object property"
    ::= { cfprApEtherServerIntFIoPcEntry 9 }

cfprApEtherServerIntFIoPcName OBJECT-TYPE
    SYNTAX       SnmpAdminString
    MAX-ACCESS   read-only
    STATUS       current
    DESCRIPTION
        "Cisco Firepower ether:ServerIntFIoPc:name managed
        object property"
    ::= { cfprApEtherServerIntFIoPcEntry 10 }

cfprApEtherServerIntFIoPcOperSpeed OBJECT-TYPE
    SYNTAX       CfprApPortEthSpeed
    MAX-ACCESS   read-only
    STATUS       current
    DESCRIPTION
        "Cisco Firepower ether:ServerIntFIoPc:operSpeed
        managed object property"
    ::= { cfprApEtherServerIntFIoPcEntry 11 }

cfprApEtherServerIntFIoPcOperState OBJECT-TYPE
    SYNTAX       CfprApNetworkPortOperState
    MAX-ACCESS   read-only
    STATUS       current
    DESCRIPTION
        "Cisco Firepower ether:ServerIntFIoPc:operState
        managed object property"
    ::= { cfprApEtherServerIntFIoPcEntry 12 }

cfprApEtherServerIntFIoPcPeerDn OBJECT-TYPE
    SYNTAX       SnmpAdminString
    MAX-ACCESS   read-only
    STATUS       current
    DESCRIPTION
        "Cisco Firepower ether:ServerIntFIoPc:peerDn managed
        object property"
    ::= { cfprApEtherServerIntFIoPcEntry 13 }

cfprApEtherServerIntFIoPcPortId OBJECT-TYPE
    SYNTAX       CfprApEtherServerIntFIoPcPortId
    MAX-ACCESS   read-only
    STATUS       current
    DESCRIPTION
        "Cisco Firepower ether:ServerIntFIoPc:portId managed
        object property"
    ::= { cfprApEtherServerIntFIoPcEntry 14 }

cfprApEtherServerIntFIoPcStateQual OBJECT-TYPE
    SYNTAX       SnmpAdminString
    MAX-ACCESS   read-only
    STATUS       current
    DESCRIPTION
        "Cisco Firepower ether:ServerIntFIoPc:stateQual
        managed object property"
    ::= { cfprApEtherServerIntFIoPcEntry 15 }

cfprApEtherServerIntFIoPcSwitchId OBJECT-TYPE
    SYNTAX       CfprApNetworkSwitchId
    MAX-ACCESS   read-only
    STATUS       current
    DESCRIPTION
        "Cisco Firepower ether:ServerIntFIoPc:switchId
        managed object property"
    ::= { cfprApEtherServerIntFIoPcEntry 16 }

cfprApEtherServerIntFIoPcTransport OBJECT-TYPE
    SYNTAX       CfprApEtherServerIntFIoPcTransport
    MAX-ACCESS   read-only
    STATUS       current
    DESCRIPTION
        "Cisco Firepower ether:ServerIntFIoPc:transport
        managed object property"
    ::= { cfprApEtherServerIntFIoPcEntry 17 }

cfprApEtherServerIntFIoPcType OBJECT-TYPE
    SYNTAX       CfprApEtherServerIntFIoPcType
    MAX-ACCESS   read-only
    STATUS       current
    DESCRIPTION
        "Cisco Firepower ether:ServerIntFIoPc:type managed
        object property"
    ::= { cfprApEtherServerIntFIoPcEntry 18 }

cfprApEtherServerIntFIoPcEpTable OBJECT-TYPE
    SYNTAX           SEQUENCE OF CfprApEtherServerIntFIoPcEpEntry
    MAX-ACCESS       not-accessible
    STATUS           current
    DESCRIPTION
        "Cisco Firepower ether:ServerIntFIoPcEp managed object table"
    ::= { cfprApEtherObjects 30 }

cfprApEtherServerIntFIoPcEpEntry OBJECT-TYPE
    SYNTAX           CfprApEtherServerIntFIoPcEpEntry
    MAX-ACCESS       not-accessible
    STATUS           current
    DESCRIPTION
        "Entry for the cfprApEtherServerIntFIoPcEpTable table."
    INDEX { cfprApEtherServerIntFIoPcEpInstanceId }
    ::= { cfprApEtherServerIntFIoPcEpTable 1 }

CfprApEtherServerIntFIoPcEpEntry ::= SEQUENCE {
    cfprApEtherServerIntFIoPcEpInstanceId                            CfprApManagedObjectId,
    cfprApEtherServerIntFIoPcEpDnData                                CfprApManagedObjectDn,
    cfprApEtherServerIntFIoPcEpRn                                    SnmpAdminString,
    cfprApEtherServerIntFIoPcEpAdminState                            CfprApEtherExternalEpAdminState,
    cfprApEtherServerIntFIoPcEpAggrPortId                            Gauge32,
    cfprApEtherServerIntFIoPcEpChassisId                             Gauge32,
    cfprApEtherServerIntFIoPcEpEpDn                                  SnmpAdminString,
    cfprApEtherServerIntFIoPcEpIfRole                                CfprApEtherServerIntFIoPcEpIfRole,
    cfprApEtherServerIntFIoPcEpIfType                                CfprApEtherPIoEpIfType,
    cfprApEtherServerIntFIoPcEpLocale                                CfprApEtherExternalEpLocale,
    cfprApEtherServerIntFIoPcEpMembership                            CfprApFabricMembershipStatus,
    cfprApEtherServerIntFIoPcEpName                                  SnmpAdminString,
    cfprApEtherServerIntFIoPcEpPeerAggrPortId                        Gauge32,
    cfprApEtherServerIntFIoPcEpPeerChassisId                         Gauge32,
    cfprApEtherServerIntFIoPcEpPeerDn                                SnmpAdminString,
    cfprApEtherServerIntFIoPcEpPeerPortId                            Gauge32,
    cfprApEtherServerIntFIoPcEpPeerSlotId                            Gauge32,
    cfprApEtherServerIntFIoPcEpPortId                                CfprApEtherServerIntFIoPcEpPortId,
    cfprApEtherServerIntFIoPcEpSlotId                                Gauge32,
    cfprApEtherServerIntFIoPcEpSwitchId                              CfprApNetworkSwitchId,
    cfprApEtherServerIntFIoPcEpTransport                             CfprApNetworkTransport,
    cfprApEtherServerIntFIoPcEpType                                  CfprApEtherIntFIoEpType
}

cfprApEtherServerIntFIoPcEpInstanceId OBJECT-TYPE
    SYNTAX       CfprApManagedObjectId
    MAX-ACCESS   not-accessible
    STATUS       current
    DESCRIPTION
        "Instance identifier of the managed object."
    ::= { cfprApEtherServerIntFIoPcEpEntry 1 }

cfprApEtherServerIntFIoPcEpDnData OBJECT-TYPE
    SYNTAX       CfprApManagedObjectDn
    MAX-ACCESS   read-only
    STATUS       current
    DESCRIPTION
        "Cisco Firepower ether:ServerIntFIoPcEp:dn managed
        object property"
    ::= { cfprApEtherServerIntFIoPcEpEntry 2 }

cfprApEtherServerIntFIoPcEpRn OBJECT-TYPE
    SYNTAX       SnmpAdminString
    MAX-ACCESS   read-only
    STATUS       current
    DESCRIPTION
        "Cisco Firepower ether:ServerIntFIoPcEp:rn managed
        object property"
    ::= { cfprApEtherServerIntFIoPcEpEntry 3 }

cfprApEtherServerIntFIoPcEpAdminState OBJECT-TYPE
    SYNTAX       CfprApEtherExternalEpAdminState
    MAX-ACCESS   read-only
    STATUS       current
    DESCRIPTION
        "Cisco Firepower ether:ServerIntFIoPcEp:adminState
        managed object property"
    ::= { cfprApEtherServerIntFIoPcEpEntry 4 }

cfprApEtherServerIntFIoPcEpAggrPortId OBJECT-TYPE
    SYNTAX       Gauge32
    MAX-ACCESS   read-only
    STATUS       current
    DESCRIPTION
        "Cisco Firepower ether:ServerIntFIoPcEp:aggrPortId
        managed object property"
    ::= { cfprApEtherServerIntFIoPcEpEntry 5 }

cfprApEtherServerIntFIoPcEpChassisId OBJECT-TYPE
    SYNTAX       Gauge32
    MAX-ACCESS   read-only
    STATUS       current
    DESCRIPTION
        "Cisco Firepower ether:ServerIntFIoPcEp:chassisId
        managed object property"
    ::= { cfprApEtherServerIntFIoPcEpEntry 6 }

cfprApEtherServerIntFIoPcEpEpDn OBJECT-TYPE
    SYNTAX       SnmpAdminString
    MAX-ACCESS   read-only
    STATUS       current
    DESCRIPTION
        "Cisco Firepower ether:ServerIntFIoPcEp:epDn managed
        object property"
    ::= { cfprApEtherServerIntFIoPcEpEntry 7 }

cfprApEtherServerIntFIoPcEpIfRole OBJECT-TYPE
    SYNTAX       CfprApEtherServerIntFIoPcEpIfRole
    MAX-ACCESS   read-only
    STATUS       current
    DESCRIPTION
        "Cisco Firepower ether:ServerIntFIoPcEp:ifRole
        managed object property"
    ::= { cfprApEtherServerIntFIoPcEpEntry 8 }

cfprApEtherServerIntFIoPcEpIfType OBJECT-TYPE
    SYNTAX       CfprApEtherPIoEpIfType
    MAX-ACCESS   read-only
    STATUS       current
    DESCRIPTION
        "Cisco Firepower ether:ServerIntFIoPcEp:ifType
        managed object property"
    ::= { cfprApEtherServerIntFIoPcEpEntry 9 }

cfprApEtherServerIntFIoPcEpLocale OBJECT-TYPE
    SYNTAX       CfprApEtherExternalEpLocale
    MAX-ACCESS   read-only
    STATUS       current
    DESCRIPTION
        "Cisco Firepower ether:ServerIntFIoPcEp:locale
        managed object property"
    ::= { cfprApEtherServerIntFIoPcEpEntry 10 }

cfprApEtherServerIntFIoPcEpMembership OBJECT-TYPE
    SYNTAX       CfprApFabricMembershipStatus
    MAX-ACCESS   read-only
    STATUS       current
    DESCRIPTION
        "Cisco Firepower ether:ServerIntFIoPcEp:membership
        managed object property"
    ::= { cfprApEtherServerIntFIoPcEpEntry 11 }

cfprApEtherServerIntFIoPcEpName OBJECT-TYPE
    SYNTAX       SnmpAdminString
    MAX-ACCESS   read-only
    STATUS       current
    DESCRIPTION
        "Cisco Firepower ether:ServerIntFIoPcEp:name managed
        object property"
    ::= { cfprApEtherServerIntFIoPcEpEntry 12 }

cfprApEtherServerIntFIoPcEpPeerAggrPortId OBJECT-TYPE
    SYNTAX       Gauge32
    MAX-ACCESS   read-only
    STATUS       current
    DESCRIPTION
        "Cisco Firepower ether:ServerIntFIoPcEp:peerAggrPortId
        managed object property"
    ::= { cfprApEtherServerIntFIoPcEpEntry 13 }

cfprApEtherServerIntFIoPcEpPeerChassisId OBJECT-TYPE
    SYNTAX       Gauge32
    MAX-ACCESS   read-only
    STATUS       current
    DESCRIPTION
        "Cisco Firepower ether:ServerIntFIoPcEp:peerChassisId
        managed object property"
    ::= { cfprApEtherServerIntFIoPcEpEntry 14 }

cfprApEtherServerIntFIoPcEpPeerDn OBJECT-TYPE
    SYNTAX       SnmpAdminString
    MAX-ACCESS   read-only
    STATUS       current
    DESCRIPTION
        "Cisco Firepower ether:ServerIntFIoPcEp:peerDn
        managed object property"
    ::= { cfprApEtherServerIntFIoPcEpEntry 15 }

cfprApEtherServerIntFIoPcEpPeerPortId OBJECT-TYPE
    SYNTAX       Gauge32
    MAX-ACCESS   read-only
    STATUS       current
    DESCRIPTION
        "Cisco Firepower ether:ServerIntFIoPcEp:peerPortId
        managed object property"
    ::= { cfprApEtherServerIntFIoPcEpEntry 16 }

cfprApEtherServerIntFIoPcEpPeerSlotId OBJECT-TYPE
    SYNTAX       Gauge32
    MAX-ACCESS   read-only
    STATUS       current
    DESCRIPTION
        "Cisco Firepower ether:ServerIntFIoPcEp:peerSlotId
        managed object property"
    ::= { cfprApEtherServerIntFIoPcEpEntry 17 }

cfprApEtherServerIntFIoPcEpPortId OBJECT-TYPE
    SYNTAX       CfprApEtherServerIntFIoPcEpPortId
    MAX-ACCESS   read-only
    STATUS       current
    DESCRIPTION
        "Cisco Firepower ether:ServerIntFIoPcEp:portId
        managed object property"
    ::= { cfprApEtherServerIntFIoPcEpEntry 18 }

cfprApEtherServerIntFIoPcEpSlotId OBJECT-TYPE
    SYNTAX       Gauge32
    MAX-ACCESS   read-only
    STATUS       current
    DESCRIPTION
        "Cisco Firepower ether:ServerIntFIoPcEp:slotId
        managed object property"
    ::= { cfprApEtherServerIntFIoPcEpEntry 19 }

cfprApEtherServerIntFIoPcEpSwitchId OBJECT-TYPE
    SYNTAX       CfprApNetworkSwitchId
    MAX-ACCESS   read-only
    STATUS       current
    DESCRIPTION
        "Cisco Firepower ether:ServerIntFIoPcEp:switchId
        managed object property"
    ::= { cfprApEtherServerIntFIoPcEpEntry 20 }

cfprApEtherServerIntFIoPcEpTransport OBJECT-TYPE
    SYNTAX       CfprApNetworkTransport
    MAX-ACCESS   read-only
    STATUS       current
    DESCRIPTION
        "Cisco Firepower ether:ServerIntFIoPcEp:transport
        managed object property"
    ::= { cfprApEtherServerIntFIoPcEpEntry 21 }

cfprApEtherServerIntFIoPcEpType OBJECT-TYPE
    SYNTAX       CfprApEtherIntFIoEpType
    MAX-ACCESS   read-only
    STATUS       current
    DESCRIPTION
        "Cisco Firepower ether:ServerIntFIoPcEp:type managed
        object property"
    ::= { cfprApEtherServerIntFIoPcEpEntry 22 }

cfprApEtherSwIfConfigTable OBJECT-TYPE
    SYNTAX           SEQUENCE OF CfprApEtherSwIfConfigEntry
    MAX-ACCESS       not-accessible
    STATUS           current
    DESCRIPTION
        "Cisco Firepower ether:SwIfConfig managed object table"
    ::= { cfprApEtherObjects 31 }

cfprApEtherSwIfConfigEntry OBJECT-TYPE
    SYNTAX           CfprApEtherSwIfConfigEntry
    MAX-ACCESS       not-accessible
    STATUS           current
    DESCRIPTION
        "Entry for the cfprApEtherSwIfConfigTable table."
    INDEX { cfprApEtherSwIfConfigInstanceId }
    ::= { cfprApEtherSwIfConfigTable 1 }

CfprApEtherSwIfConfigEntry ::= SEQUENCE {
    cfprApEtherSwIfConfigInstanceId                                  CfprApManagedObjectId,
    cfprApEtherSwIfConfigDn                                          CfprApManagedObjectDn,
    cfprApEtherSwIfConfigRn                                          SnmpAdminString
}

cfprApEtherSwIfConfigInstanceId OBJECT-TYPE
    SYNTAX       CfprApManagedObjectId
    MAX-ACCESS   not-accessible
    STATUS       current
    DESCRIPTION
        "Instance identifier of the managed object."
    ::= { cfprApEtherSwIfConfigEntry 1 }

cfprApEtherSwIfConfigDn OBJECT-TYPE
    SYNTAX       CfprApManagedObjectDn
    MAX-ACCESS   read-only
    STATUS       current
    DESCRIPTION
        "Cisco Firepower ether:SwIfConfig:dn managed object property"
    ::= { cfprApEtherSwIfConfigEntry 2 }

cfprApEtherSwIfConfigRn OBJECT-TYPE
    SYNTAX       SnmpAdminString
    MAX-ACCESS   read-only
    STATUS       current
    DESCRIPTION
        "Cisco Firepower ether:SwIfConfig:rn managed object property"
    ::= { cfprApEtherSwIfConfigEntry 3 }

cfprApEtherSwitchIntFIoTable OBJECT-TYPE
    SYNTAX           SEQUENCE OF CfprApEtherSwitchIntFIoEntry
    MAX-ACCESS       not-accessible
    STATUS           current
    DESCRIPTION
        "Cisco Firepower ether:SwitchIntFIo managed object table"
    ::= { cfprApEtherObjects 32 }

cfprApEtherSwitchIntFIoEntry OBJECT-TYPE
    SYNTAX           CfprApEtherSwitchIntFIoEntry
    MAX-ACCESS       not-accessible
    STATUS           current
    DESCRIPTION
        "Entry for the cfprApEtherSwitchIntFIoTable table."
    INDEX { cfprApEtherSwitchIntFIoInstanceId }
    ::= { cfprApEtherSwitchIntFIoTable 1 }

CfprApEtherSwitchIntFIoEntry ::= SEQUENCE {
    cfprApEtherSwitchIntFIoInstanceId                                CfprApManagedObjectId,
    cfprApEtherSwitchIntFIoDn                                        CfprApManagedObjectDn,
    cfprApEtherSwitchIntFIoRn                                        SnmpAdminString,
    cfprApEtherSwitchIntFIoAck                                       CfprApEtherSwitchIntFIoAck,
    cfprApEtherSwitchIntFIoAdminState                                CfprApFabricAdminState,
    cfprApEtherSwitchIntFIoAggrPortId                                Gauge32,
    cfprApEtherSwitchIntFIoChassisId                                 Gauge32,
    cfprApEtherSwitchIntFIoDelFeTs                                   Unsigned64,
    cfprApEtherSwitchIntFIoDiscovery                                 CfprApEtherSatelliteConnectionDisc,
    cfprApEtherSwitchIntFIoEncap                                     CfprApPortEncap,
    cfprApEtherSwitchIntFIoEpDn                                      SnmpAdminString,
    cfprApEtherSwitchIntFIoFltAggr                                   Unsigned64,
    cfprApEtherSwitchIntFIoIfRole                                    CfprApEtherSwitchIntFIoIfRole,
    cfprApEtherSwitchIntFIoIfType                                    CfprApNetworkPhysEpIfType,
    cfprApEtherSwitchIntFIoLocale                                    CfprApEtherSwitchIntFIoLocale,
    cfprApEtherSwitchIntFIoMode                                      CfprApPortMode,
    cfprApEtherSwitchIntFIoModel                                     SnmpAdminString,
    cfprApEtherSwitchIntFIoName                                      SnmpAdminString,
    cfprApEtherSwitchIntFIoNewFeTs                                   Unsigned64,
    cfprApEtherSwitchIntFIoOperState                                 CfprApNetworkPortOperState,
    cfprApEtherSwitchIntFIoPeerAggrPortId                            Gauge32,
    cfprApEtherSwitchIntFIoPeerChassisId                             Gauge32,
    cfprApEtherSwitchIntFIoPeerDn                                    SnmpAdminString,
    cfprApEtherSwitchIntFIoPeerPortId                                Gauge32,
    cfprApEtherSwitchIntFIoPeerSlotId                                Gauge32,
    cfprApEtherSwitchIntFIoPortId                                    Gauge32,
    cfprApEtherSwitchIntFIoRevision                                  SnmpAdminString,
    cfprApEtherSwitchIntFIoSerial                                    SnmpAdminString,
    cfprApEtherSwitchIntFIoSlotId                                    Gauge32,
    cfprApEtherSwitchIntFIoStateQual                                 SnmpAdminString,
    cfprApEtherSwitchIntFIoSwitchId                                  CfprApNetworkSwitchId,
    cfprApEtherSwitchIntFIoTransport                                 CfprApEtherSwitchIntFIoTransport,
    cfprApEtherSwitchIntFIoTs                                        DateAndTime,
    cfprApEtherSwitchIntFIoType                                      CfprApEtherSwitchIntFIoType,
    cfprApEtherSwitchIntFIoVendor                                    SnmpAdminString,
    cfprApEtherSwitchIntFIoXcvrType                                  CfprApEquipmentXcvrType
}

cfprApEtherSwitchIntFIoInstanceId OBJECT-TYPE
    SYNTAX       CfprApManagedObjectId
    MAX-ACCESS   not-accessible
    STATUS       current
    DESCRIPTION
        "Instance identifier of the managed object."
    ::= { cfprApEtherSwitchIntFIoEntry 1 }

cfprApEtherSwitchIntFIoDn OBJECT-TYPE
    SYNTAX       CfprApManagedObjectDn
    MAX-ACCESS   read-only
    STATUS       current
    DESCRIPTION
        "Cisco Firepower ether:SwitchIntFIo:dn managed object property"
    ::= { cfprApEtherSwitchIntFIoEntry 2 }

cfprApEtherSwitchIntFIoRn OBJECT-TYPE
    SYNTAX       SnmpAdminString
    MAX-ACCESS   read-only
    STATUS       current
    DESCRIPTION
        "Cisco Firepower ether:SwitchIntFIo:rn managed object property"
    ::= { cfprApEtherSwitchIntFIoEntry 3 }

cfprApEtherSwitchIntFIoAck OBJECT-TYPE
    SYNTAX       CfprApEtherSwitchIntFIoAck
    MAX-ACCESS   read-only
    STATUS       current
    DESCRIPTION
        "Cisco Firepower ether:SwitchIntFIo:ack managed object property"
    ::= { cfprApEtherSwitchIntFIoEntry 4 }

cfprApEtherSwitchIntFIoAdminState OBJECT-TYPE
    SYNTAX       CfprApFabricAdminState
    MAX-ACCESS   read-only
    STATUS       current
    DESCRIPTION
        "Cisco Firepower ether:SwitchIntFIo:adminState
        managed object property"
    ::= { cfprApEtherSwitchIntFIoEntry 5 }

cfprApEtherSwitchIntFIoAggrPortId OBJECT-TYPE
    SYNTAX       Gauge32
    MAX-ACCESS   read-only
    STATUS       current
    DESCRIPTION
        "Cisco Firepower ether:SwitchIntFIo:aggrPortId
        managed object property"
    ::= { cfprApEtherSwitchIntFIoEntry 6 }

cfprApEtherSwitchIntFIoChassisId OBJECT-TYPE
    SYNTAX       Gauge32
    MAX-ACCESS   read-only
    STATUS       current
    DESCRIPTION
        "Cisco Firepower ether:SwitchIntFIo:chassisId managed
        object property"
    ::= { cfprApEtherSwitchIntFIoEntry 7 }

cfprApEtherSwitchIntFIoDelFeTs OBJECT-TYPE
    SYNTAX       Unsigned64
    MAX-ACCESS   read-only
    STATUS       current
    DESCRIPTION
        "Cisco Firepower ether:SwitchIntFIo:delFeTs managed
        object property"
    ::= { cfprApEtherSwitchIntFIoEntry 8 }

cfprApEtherSwitchIntFIoDiscovery OBJECT-TYPE
    SYNTAX       CfprApEtherSatelliteConnectionDisc
    MAX-ACCESS   read-only
    STATUS       current
    DESCRIPTION
        "Cisco Firepower ether:SwitchIntFIo:discovery managed
        object property"
    ::= { cfprApEtherSwitchIntFIoEntry 9 }

cfprApEtherSwitchIntFIoEncap OBJECT-TYPE
    SYNTAX       CfprApPortEncap
    MAX-ACCESS   read-only
    STATUS       current
    DESCRIPTION
        "Cisco Firepower ether:SwitchIntFIo:encap managed object property"
    ::= { cfprApEtherSwitchIntFIoEntry 10 }

cfprApEtherSwitchIntFIoEpDn OBJECT-TYPE
    SYNTAX       SnmpAdminString
    MAX-ACCESS   read-only
    STATUS       current
    DESCRIPTION
        "Cisco Firepower ether:SwitchIntFIo:epDn managed object property"
    ::= { cfprApEtherSwitchIntFIoEntry 11 }

cfprApEtherSwitchIntFIoFltAggr OBJECT-TYPE
    SYNTAX       Unsigned64
    MAX-ACCESS   read-only
    STATUS       current
    DESCRIPTION
        "Cisco Firepower ether:SwitchIntFIo:fltAggr managed
        object property"
    ::= { cfprApEtherSwitchIntFIoEntry 12 }

cfprApEtherSwitchIntFIoIfRole OBJECT-TYPE
    SYNTAX       CfprApEtherSwitchIntFIoIfRole
    MAX-ACCESS   read-only
    STATUS       current
    DESCRIPTION
        "Cisco Firepower ether:SwitchIntFIo:ifRole managed
        object property"
    ::= { cfprApEtherSwitchIntFIoEntry 13 }

cfprApEtherSwitchIntFIoIfType OBJECT-TYPE
    SYNTAX       CfprApNetworkPhysEpIfType
    MAX-ACCESS   read-only
    STATUS       current
    DESCRIPTION
        "Cisco Firepower ether:SwitchIntFIo:ifType managed
        object property"
    ::= { cfprApEtherSwitchIntFIoEntry 14 }

cfprApEtherSwitchIntFIoLocale OBJECT-TYPE
    SYNTAX       CfprApEtherSwitchIntFIoLocale
    MAX-ACCESS   read-only
    STATUS       current
    DESCRIPTION
        "Cisco Firepower ether:SwitchIntFIo:locale managed
        object property"
    ::= { cfprApEtherSwitchIntFIoEntry 15 }

cfprApEtherSwitchIntFIoMode OBJECT-TYPE
    SYNTAX       CfprApPortMode
    MAX-ACCESS   read-only
    STATUS       current
    DESCRIPTION
        "Cisco Firepower ether:SwitchIntFIo:mode managed object property"
    ::= { cfprApEtherSwitchIntFIoEntry 16 }

cfprApEtherSwitchIntFIoModel OBJECT-TYPE
    SYNTAX       SnmpAdminString
    MAX-ACCESS   read-only
    STATUS       current
    DESCRIPTION
        "Cisco Firepower ether:SwitchIntFIo:model managed object property"
    ::= { cfprApEtherSwitchIntFIoEntry 17 }

cfprApEtherSwitchIntFIoName OBJECT-TYPE
    SYNTAX       SnmpAdminString
    MAX-ACCESS   read-only
    STATUS       current
    DESCRIPTION
        "Cisco Firepower ether:SwitchIntFIo:name managed object property"
    ::= { cfprApEtherSwitchIntFIoEntry 18 }

cfprApEtherSwitchIntFIoNewFeTs OBJECT-TYPE
    SYNTAX       Unsigned64
    MAX-ACCESS   read-only
    STATUS       current
    DESCRIPTION
        "Cisco Firepower ether:SwitchIntFIo:newFeTs managed
        object property"
    ::= { cfprApEtherSwitchIntFIoEntry 19 }

cfprApEtherSwitchIntFIoOperState OBJECT-TYPE
    SYNTAX       CfprApNetworkPortOperState
    MAX-ACCESS   read-only
    STATUS       current
    DESCRIPTION
        "Cisco Firepower ether:SwitchIntFIo:operState managed
        object property"
    ::= { cfprApEtherSwitchIntFIoEntry 20 }

cfprApEtherSwitchIntFIoPeerAggrPortId OBJECT-TYPE
    SYNTAX       Gauge32
    MAX-ACCESS   read-only
    STATUS       current
    DESCRIPTION
        "Cisco Firepower ether:SwitchIntFIo:peerAggrPortId
        managed object property"
    ::= { cfprApEtherSwitchIntFIoEntry 21 }

cfprApEtherSwitchIntFIoPeerChassisId OBJECT-TYPE
    SYNTAX       Gauge32
    MAX-ACCESS   read-only
    STATUS       current
    DESCRIPTION
        "Cisco Firepower ether:SwitchIntFIo:peerChassisId
        managed object property"
    ::= { cfprApEtherSwitchIntFIoEntry 22 }

cfprApEtherSwitchIntFIoPeerDn OBJECT-TYPE
    SYNTAX       SnmpAdminString
    MAX-ACCESS   read-only
    STATUS       current
    DESCRIPTION
        "Cisco Firepower ether:SwitchIntFIo:peerDn managed
        object property"
    ::= { cfprApEtherSwitchIntFIoEntry 23 }

cfprApEtherSwitchIntFIoPeerPortId OBJECT-TYPE
    SYNTAX       Gauge32
    MAX-ACCESS   read-only
    STATUS       current
    DESCRIPTION
        "Cisco Firepower ether:SwitchIntFIo:peerPortId
        managed object property"
    ::= { cfprApEtherSwitchIntFIoEntry 24 }

cfprApEtherSwitchIntFIoPeerSlotId OBJECT-TYPE
    SYNTAX       Gauge32
    MAX-ACCESS   read-only
    STATUS       current
    DESCRIPTION
        "Cisco Firepower ether:SwitchIntFIo:peerSlotId
        managed object property"
    ::= { cfprApEtherSwitchIntFIoEntry 25 }

cfprApEtherSwitchIntFIoPortId OBJECT-TYPE
    SYNTAX       Gauge32
    MAX-ACCESS   read-only
    STATUS       current
    DESCRIPTION
        "Cisco Firepower ether:SwitchIntFIo:portId managed
        object property"
    ::= { cfprApEtherSwitchIntFIoEntry 26 }

cfprApEtherSwitchIntFIoRevision OBJECT-TYPE
    SYNTAX       SnmpAdminString
    MAX-ACCESS   read-only
    STATUS       current
    DESCRIPTION
        "Cisco Firepower ether:SwitchIntFIo:revision managed
        object property"
    ::= { cfprApEtherSwitchIntFIoEntry 27 }

cfprApEtherSwitchIntFIoSerial OBJECT-TYPE
    SYNTAX       SnmpAdminString
    MAX-ACCESS   read-only
    STATUS       current
    DESCRIPTION
        "Cisco Firepower ether:SwitchIntFIo:serial managed
        object property"
    ::= { cfprApEtherSwitchIntFIoEntry 28 }

cfprApEtherSwitchIntFIoSlotId OBJECT-TYPE
    SYNTAX       Gauge32
    MAX-ACCESS   read-only
    STATUS       current
    DESCRIPTION
        "Cisco Firepower ether:SwitchIntFIo:slotId managed
        object property"
    ::= { cfprApEtherSwitchIntFIoEntry 29 }

cfprApEtherSwitchIntFIoStateQual OBJECT-TYPE
    SYNTAX       SnmpAdminString
    MAX-ACCESS   read-only
    STATUS       current
    DESCRIPTION
        "Cisco Firepower ether:SwitchIntFIo:stateQual managed
        object property"
    ::= { cfprApEtherSwitchIntFIoEntry 30 }

cfprApEtherSwitchIntFIoSwitchId OBJECT-TYPE
    SYNTAX       CfprApNetworkSwitchId
    MAX-ACCESS   read-only
    STATUS       current
    DESCRIPTION
        "Cisco Firepower ether:SwitchIntFIo:switchId managed
        object property"
    ::= { cfprApEtherSwitchIntFIoEntry 31 }

cfprApEtherSwitchIntFIoTransport OBJECT-TYPE
    SYNTAX       CfprApEtherSwitchIntFIoTransport
    MAX-ACCESS   read-only
    STATUS       current
    DESCRIPTION
        "Cisco Firepower ether:SwitchIntFIo:transport managed
        object property"
    ::= { cfprApEtherSwitchIntFIoEntry 32 }

cfprApEtherSwitchIntFIoTs OBJECT-TYPE
    SYNTAX       DateAndTime
    MAX-ACCESS   read-only
    STATUS       current
    DESCRIPTION
        "Cisco Firepower ether:SwitchIntFIo:ts managed object property"
    ::= { cfprApEtherSwitchIntFIoEntry 33 }

cfprApEtherSwitchIntFIoType OBJECT-TYPE
    SYNTAX       CfprApEtherSwitchIntFIoType
    MAX-ACCESS   read-only
    STATUS       current
    DESCRIPTION
        "Cisco Firepower ether:SwitchIntFIo:type managed object property"
    ::= { cfprApEtherSwitchIntFIoEntry 34 }

cfprApEtherSwitchIntFIoVendor OBJECT-TYPE
    SYNTAX       SnmpAdminString
    MAX-ACCESS   read-only
    STATUS       current
    DESCRIPTION
        "Cisco Firepower ether:SwitchIntFIo:vendor managed
        object property"
    ::= { cfprApEtherSwitchIntFIoEntry 35 }

cfprApEtherSwitchIntFIoXcvrType OBJECT-TYPE
    SYNTAX       CfprApEquipmentXcvrType
    MAX-ACCESS   read-only
    STATUS       current
    DESCRIPTION
        "Cisco Firepower ether:SwitchIntFIo:xcvrType managed
        object property"
    ::= { cfprApEtherSwitchIntFIoEntry 36 }

cfprApEtherSwitchIntFIoPcTable OBJECT-TYPE
    SYNTAX           SEQUENCE OF CfprApEtherSwitchIntFIoPcEntry
    MAX-ACCESS       not-accessible
    STATUS           current
    DESCRIPTION
        "Cisco Firepower ether:SwitchIntFIoPc managed object table"
    ::= { cfprApEtherObjects 33 }

cfprApEtherSwitchIntFIoPcEntry OBJECT-TYPE
    SYNTAX           CfprApEtherSwitchIntFIoPcEntry
    MAX-ACCESS       not-accessible
    STATUS           current
    DESCRIPTION
        "Entry for the cfprApEtherSwitchIntFIoPcTable table."
    INDEX { cfprApEtherSwitchIntFIoPcInstanceId }
    ::= { cfprApEtherSwitchIntFIoPcTable 1 }

CfprApEtherSwitchIntFIoPcEntry ::= SEQUENCE {
    cfprApEtherSwitchIntFIoPcInstanceId                              CfprApManagedObjectId,
    cfprApEtherSwitchIntFIoPcDn                                      CfprApManagedObjectDn,
    cfprApEtherSwitchIntFIoPcRn                                      SnmpAdminString,
    cfprApEtherSwitchIntFIoPcAdminState                              CfprApEtherExternalPcAdminState,
    cfprApEtherSwitchIntFIoPcChassisId                               Gauge32,
    cfprApEtherSwitchIntFIoPcEpDn                                    SnmpAdminString,
    cfprApEtherSwitchIntFIoPcFltAggr                                 Unsigned64,
    cfprApEtherSwitchIntFIoPcIfRole                                  CfprApEtherSwitchIntFIoPcIfRole,
    cfprApEtherSwitchIntFIoPcIfType                                  CfprApEtherCIoEpIfType,
    cfprApEtherSwitchIntFIoPcLocale                                  CfprApEtherExternalPcLocale,
    cfprApEtherSwitchIntFIoPcName                                    SnmpAdminString,
    cfprApEtherSwitchIntFIoPcOperSpeed                               CfprApPortEthSpeed,
    cfprApEtherSwitchIntFIoPcOperState                               CfprApNetworkPortOperState,
    cfprApEtherSwitchIntFIoPcPeerDn                                  SnmpAdminString,
    cfprApEtherSwitchIntFIoPcPortId                                  CfprApEtherSwitchIntFIoPcPortId,
    cfprApEtherSwitchIntFIoPcStateQual                               SnmpAdminString,
    cfprApEtherSwitchIntFIoPcSwitchId                                CfprApNetworkSwitchId,
    cfprApEtherSwitchIntFIoPcTransport                               CfprApEtherSwitchIntFIoPcTransport,
    cfprApEtherSwitchIntFIoPcType                                    CfprApEtherSwitchIntFIoPcType
}

cfprApEtherSwitchIntFIoPcInstanceId OBJECT-TYPE
    SYNTAX       CfprApManagedObjectId
    MAX-ACCESS   not-accessible
    STATUS       current
    DESCRIPTION
        "Instance identifier of the managed object."
    ::= { cfprApEtherSwitchIntFIoPcEntry 1 }

cfprApEtherSwitchIntFIoPcDn OBJECT-TYPE
    SYNTAX       CfprApManagedObjectDn
    MAX-ACCESS   read-only
    STATUS       current
    DESCRIPTION
        "Cisco Firepower ether:SwitchIntFIoPc:dn managed object property"
    ::= { cfprApEtherSwitchIntFIoPcEntry 2 }

cfprApEtherSwitchIntFIoPcRn OBJECT-TYPE
    SYNTAX       SnmpAdminString
    MAX-ACCESS   read-only
    STATUS       current
    DESCRIPTION
        "Cisco Firepower ether:SwitchIntFIoPc:rn managed object property"
    ::= { cfprApEtherSwitchIntFIoPcEntry 3 }

cfprApEtherSwitchIntFIoPcAdminState OBJECT-TYPE
    SYNTAX       CfprApEtherExternalPcAdminState
    MAX-ACCESS   read-only
    STATUS       current
    DESCRIPTION
        "Cisco Firepower ether:SwitchIntFIoPc:adminState
        managed object property"
    ::= { cfprApEtherSwitchIntFIoPcEntry 4 }

cfprApEtherSwitchIntFIoPcChassisId OBJECT-TYPE
    SYNTAX       Gauge32
    MAX-ACCESS   read-only
    STATUS       current
    DESCRIPTION
        "Cisco Firepower ether:SwitchIntFIoPc:chassisId
        managed object property"
    ::= { cfprApEtherSwitchIntFIoPcEntry 5 }

cfprApEtherSwitchIntFIoPcEpDn OBJECT-TYPE
    SYNTAX       SnmpAdminString
    MAX-ACCESS   read-only
    STATUS       current
    DESCRIPTION
        "Cisco Firepower ether:SwitchIntFIoPc:epDn managed
        object property"
    ::= { cfprApEtherSwitchIntFIoPcEntry 6 }

cfprApEtherSwitchIntFIoPcFltAggr OBJECT-TYPE
    SYNTAX       Unsigned64
    MAX-ACCESS   read-only
    STATUS       current
    DESCRIPTION
        "Cisco Firepower ether:SwitchIntFIoPc:fltAggr managed
        object property"
    ::= { cfprApEtherSwitchIntFIoPcEntry 7 }

cfprApEtherSwitchIntFIoPcIfRole OBJECT-TYPE
    SYNTAX       CfprApEtherSwitchIntFIoPcIfRole
    MAX-ACCESS   read-only
    STATUS       current
    DESCRIPTION
        "Cisco Firepower ether:SwitchIntFIoPc:ifRole managed
        object property"
    ::= { cfprApEtherSwitchIntFIoPcEntry 8 }

cfprApEtherSwitchIntFIoPcIfType OBJECT-TYPE
    SYNTAX       CfprApEtherCIoEpIfType
    MAX-ACCESS   read-only
    STATUS       current
    DESCRIPTION
        "Cisco Firepower ether:SwitchIntFIoPc:ifType managed
        object property"
    ::= { cfprApEtherSwitchIntFIoPcEntry 9 }

cfprApEtherSwitchIntFIoPcLocale OBJECT-TYPE
    SYNTAX       CfprApEtherExternalPcLocale
    MAX-ACCESS   read-only
    STATUS       current
    DESCRIPTION
        "Cisco Firepower ether:SwitchIntFIoPc:locale managed
        object property"
    ::= { cfprApEtherSwitchIntFIoPcEntry 10 }

cfprApEtherSwitchIntFIoPcName OBJECT-TYPE
    SYNTAX       SnmpAdminString
    MAX-ACCESS   read-only
    STATUS       current
    DESCRIPTION
        "Cisco Firepower ether:SwitchIntFIoPc:name managed
        object property"
    ::= { cfprApEtherSwitchIntFIoPcEntry 11 }

cfprApEtherSwitchIntFIoPcOperSpeed OBJECT-TYPE
    SYNTAX       CfprApPortEthSpeed
    MAX-ACCESS   read-only
    STATUS       current
    DESCRIPTION
        "Cisco Firepower ether:SwitchIntFIoPc:operSpeed
        managed object property"
    ::= { cfprApEtherSwitchIntFIoPcEntry 12 }

cfprApEtherSwitchIntFIoPcOperState OBJECT-TYPE
    SYNTAX       CfprApNetworkPortOperState
    MAX-ACCESS   read-only
    STATUS       current
    DESCRIPTION
        "Cisco Firepower ether:SwitchIntFIoPc:operState
        managed object property"
    ::= { cfprApEtherSwitchIntFIoPcEntry 13 }

cfprApEtherSwitchIntFIoPcPeerDn OBJECT-TYPE
    SYNTAX       SnmpAdminString
    MAX-ACCESS   read-only
    STATUS       current
    DESCRIPTION
        "Cisco Firepower ether:SwitchIntFIoPc:peerDn managed
        object property"
    ::= { cfprApEtherSwitchIntFIoPcEntry 14 }

cfprApEtherSwitchIntFIoPcPortId OBJECT-TYPE
    SYNTAX       CfprApEtherSwitchIntFIoPcPortId
    MAX-ACCESS   read-only
    STATUS       current
    DESCRIPTION
        "Cisco Firepower ether:SwitchIntFIoPc:portId managed
        object property"
    ::= { cfprApEtherSwitchIntFIoPcEntry 15 }

cfprApEtherSwitchIntFIoPcStateQual OBJECT-TYPE
    SYNTAX       SnmpAdminString
    MAX-ACCESS   read-only
    STATUS       current
    DESCRIPTION
        "Cisco Firepower ether:SwitchIntFIoPc:stateQual
        managed object property"
    ::= { cfprApEtherSwitchIntFIoPcEntry 16 }

cfprApEtherSwitchIntFIoPcSwitchId OBJECT-TYPE
    SYNTAX       CfprApNetworkSwitchId
    MAX-ACCESS   read-only
    STATUS       current
    DESCRIPTION
        "Cisco Firepower ether:SwitchIntFIoPc:switchId
        managed object property"
    ::= { cfprApEtherSwitchIntFIoPcEntry 17 }

cfprApEtherSwitchIntFIoPcTransport OBJECT-TYPE
    SYNTAX       CfprApEtherSwitchIntFIoPcTransport
    MAX-ACCESS   read-only
    STATUS       current
    DESCRIPTION
        "Cisco Firepower ether:SwitchIntFIoPc:transport
        managed object property"
    ::= { cfprApEtherSwitchIntFIoPcEntry 18 }

cfprApEtherSwitchIntFIoPcType OBJECT-TYPE
    SYNTAX       CfprApEtherSwitchIntFIoPcType
    MAX-ACCESS   read-only
    STATUS       current
    DESCRIPTION
        "Cisco Firepower ether:SwitchIntFIoPc:type managed
        object property"
    ::= { cfprApEtherSwitchIntFIoPcEntry 19 }

cfprApEtherSwitchIntFIoPcEpTable OBJECT-TYPE
    SYNTAX           SEQUENCE OF CfprApEtherSwitchIntFIoPcEpEntry
    MAX-ACCESS       not-accessible
    STATUS           current
    DESCRIPTION
        "Cisco Firepower ether:SwitchIntFIoPcEp managed object table"
    ::= { cfprApEtherObjects 34 }

cfprApEtherSwitchIntFIoPcEpEntry OBJECT-TYPE
    SYNTAX           CfprApEtherSwitchIntFIoPcEpEntry
    MAX-ACCESS       not-accessible
    STATUS           current
    DESCRIPTION
        "Entry for the cfprApEtherSwitchIntFIoPcEpTable table."
    INDEX { cfprApEtherSwitchIntFIoPcEpInstanceId }
    ::= { cfprApEtherSwitchIntFIoPcEpTable 1 }

CfprApEtherSwitchIntFIoPcEpEntry ::= SEQUENCE {
    cfprApEtherSwitchIntFIoPcEpInstanceId                            CfprApManagedObjectId,
    cfprApEtherSwitchIntFIoPcEpDnData                                CfprApManagedObjectDn,
    cfprApEtherSwitchIntFIoPcEpRn                                    SnmpAdminString,
    cfprApEtherSwitchIntFIoPcEpAckState                              CfprApEquipmentChassisConfigState,
    cfprApEtherSwitchIntFIoPcEpAdminState                            CfprApEtherExternalEpAdminState,
    cfprApEtherSwitchIntFIoPcEpAggrPortId                            Gauge32,
    cfprApEtherSwitchIntFIoPcEpChassisId                             Gauge32,
    cfprApEtherSwitchIntFIoPcEpEpDn                                  SnmpAdminString,
    cfprApEtherSwitchIntFIoPcEpIfRole                                CfprApEtherSwitchIntFIoPcEpIfRole,
    cfprApEtherSwitchIntFIoPcEpIfType                                CfprApEtherPIoEpIfType,
    cfprApEtherSwitchIntFIoPcEpLocale                                CfprApEtherExternalEpLocale,
    cfprApEtherSwitchIntFIoPcEpMembership                            CfprApFabricMembershipStatus,
    cfprApEtherSwitchIntFIoPcEpName                                  SnmpAdminString,
    cfprApEtherSwitchIntFIoPcEpPeerAggrPortId                        Gauge32,
    cfprApEtherSwitchIntFIoPcEpPeerChassisId                         Gauge32,
    cfprApEtherSwitchIntFIoPcEpPeerDn                                SnmpAdminString,
    cfprApEtherSwitchIntFIoPcEpPeerPortId                            Gauge32,
    cfprApEtherSwitchIntFIoPcEpPeerSlotId                            Gauge32,
    cfprApEtherSwitchIntFIoPcEpPortId                                CfprApEtherSwitchIntFIoPcEpPortId,
    cfprApEtherSwitchIntFIoPcEpSlotId                                Gauge32,
    cfprApEtherSwitchIntFIoPcEpStatusChangeTs                        DateAndTime,
    cfprApEtherSwitchIntFIoPcEpSwitchId                              CfprApNetworkSwitchId,
    cfprApEtherSwitchIntFIoPcEpTransport                             CfprApNetworkTransport,
    cfprApEtherSwitchIntFIoPcEpType                                  CfprApEtherIntFIoEpType
}

cfprApEtherSwitchIntFIoPcEpInstanceId OBJECT-TYPE
    SYNTAX       CfprApManagedObjectId
    MAX-ACCESS   not-accessible
    STATUS       current
    DESCRIPTION
        "Instance identifier of the managed object."
    ::= { cfprApEtherSwitchIntFIoPcEpEntry 1 }

cfprApEtherSwitchIntFIoPcEpDnData OBJECT-TYPE
    SYNTAX       CfprApManagedObjectDn
    MAX-ACCESS   read-only
    STATUS       current
    DESCRIPTION
        "Cisco Firepower ether:SwitchIntFIoPcEp:dn managed
        object property"
    ::= { cfprApEtherSwitchIntFIoPcEpEntry 2 }

cfprApEtherSwitchIntFIoPcEpRn OBJECT-TYPE
    SYNTAX       SnmpAdminString
    MAX-ACCESS   read-only
    STATUS       current
    DESCRIPTION
        "Cisco Firepower ether:SwitchIntFIoPcEp:rn managed
        object property"
    ::= { cfprApEtherSwitchIntFIoPcEpEntry 3 }

cfprApEtherSwitchIntFIoPcEpAckState OBJECT-TYPE
    SYNTAX       CfprApEquipmentChassisConfigState
    MAX-ACCESS   read-only
    STATUS       current
    DESCRIPTION
        "Cisco Firepower ether:SwitchIntFIoPcEp:ackState
        managed object property"
    ::= { cfprApEtherSwitchIntFIoPcEpEntry 4 }

cfprApEtherSwitchIntFIoPcEpAdminState OBJECT-TYPE
    SYNTAX       CfprApEtherExternalEpAdminState
    MAX-ACCESS   read-only
    STATUS       current
    DESCRIPTION
        "Cisco Firepower ether:SwitchIntFIoPcEp:adminState
        managed object property"
    ::= { cfprApEtherSwitchIntFIoPcEpEntry 5 }

cfprApEtherSwitchIntFIoPcEpAggrPortId OBJECT-TYPE
    SYNTAX       Gauge32
    MAX-ACCESS   read-only
    STATUS       current
    DESCRIPTION
        "Cisco Firepower ether:SwitchIntFIoPcEp:aggrPortId
        managed object property"
    ::= { cfprApEtherSwitchIntFIoPcEpEntry 6 }

cfprApEtherSwitchIntFIoPcEpChassisId OBJECT-TYPE
    SYNTAX       Gauge32
    MAX-ACCESS   read-only
    STATUS       current
    DESCRIPTION
        "Cisco Firepower ether:SwitchIntFIoPcEp:chassisId
        managed object property"
    ::= { cfprApEtherSwitchIntFIoPcEpEntry 7 }

cfprApEtherSwitchIntFIoPcEpEpDn OBJECT-TYPE
    SYNTAX       SnmpAdminString
    MAX-ACCESS   read-only
    STATUS       current
    DESCRIPTION
        "Cisco Firepower ether:SwitchIntFIoPcEp:epDn managed
        object property"
    ::= { cfprApEtherSwitchIntFIoPcEpEntry 8 }

cfprApEtherSwitchIntFIoPcEpIfRole OBJECT-TYPE
    SYNTAX       CfprApEtherSwitchIntFIoPcEpIfRole
    MAX-ACCESS   read-only
    STATUS       current
    DESCRIPTION
        "Cisco Firepower ether:SwitchIntFIoPcEp:ifRole
        managed object property"
    ::= { cfprApEtherSwitchIntFIoPcEpEntry 9 }

cfprApEtherSwitchIntFIoPcEpIfType OBJECT-TYPE
    SYNTAX       CfprApEtherPIoEpIfType
    MAX-ACCESS   read-only
    STATUS       current
    DESCRIPTION
        "Cisco Firepower ether:SwitchIntFIoPcEp:ifType
        managed object property"
    ::= { cfprApEtherSwitchIntFIoPcEpEntry 10 }

cfprApEtherSwitchIntFIoPcEpLocale OBJECT-TYPE
    SYNTAX       CfprApEtherExternalEpLocale
    MAX-ACCESS   read-only
    STATUS       current
    DESCRIPTION
        "Cisco Firepower ether:SwitchIntFIoPcEp:locale
        managed object property"
    ::= { cfprApEtherSwitchIntFIoPcEpEntry 11 }

cfprApEtherSwitchIntFIoPcEpMembership OBJECT-TYPE
    SYNTAX       CfprApFabricMembershipStatus
    MAX-ACCESS   read-only
    STATUS       current
    DESCRIPTION
        "Cisco Firepower ether:SwitchIntFIoPcEp:membership
        managed object property"
    ::= { cfprApEtherSwitchIntFIoPcEpEntry 12 }

cfprApEtherSwitchIntFIoPcEpName OBJECT-TYPE
    SYNTAX       SnmpAdminString
    MAX-ACCESS   read-only
    STATUS       current
    DESCRIPTION
        "Cisco Firepower ether:SwitchIntFIoPcEp:name managed
        object property"
    ::= { cfprApEtherSwitchIntFIoPcEpEntry 13 }

cfprApEtherSwitchIntFIoPcEpPeerAggrPortId OBJECT-TYPE
    SYNTAX       Gauge32
    MAX-ACCESS   read-only
    STATUS       current
    DESCRIPTION
        "Cisco Firepower ether:SwitchIntFIoPcEp:peerAggrPortId
        managed object property"
    ::= { cfprApEtherSwitchIntFIoPcEpEntry 14 }

cfprApEtherSwitchIntFIoPcEpPeerChassisId OBJECT-TYPE
    SYNTAX       Gauge32
    MAX-ACCESS   read-only
    STATUS       current
    DESCRIPTION
        "Cisco Firepower ether:SwitchIntFIoPcEp:peerChassisId
        managed object property"
    ::= { cfprApEtherSwitchIntFIoPcEpEntry 15 }

cfprApEtherSwitchIntFIoPcEpPeerDn OBJECT-TYPE
    SYNTAX       SnmpAdminString
    MAX-ACCESS   read-only
    STATUS       current
    DESCRIPTION
        "Cisco Firepower ether:SwitchIntFIoPcEp:peerDn
        managed object property"
    ::= { cfprApEtherSwitchIntFIoPcEpEntry 16 }

cfprApEtherSwitchIntFIoPcEpPeerPortId OBJECT-TYPE
    SYNTAX       Gauge32
    MAX-ACCESS   read-only
    STATUS       current
    DESCRIPTION
        "Cisco Firepower ether:SwitchIntFIoPcEp:peerPortId
        managed object property"
    ::= { cfprApEtherSwitchIntFIoPcEpEntry 17 }

cfprApEtherSwitchIntFIoPcEpPeerSlotId OBJECT-TYPE
    SYNTAX       Gauge32
    MAX-ACCESS   read-only
    STATUS       current
    DESCRIPTION
        "Cisco Firepower ether:SwitchIntFIoPcEp:peerSlotId
        managed object property"
    ::= { cfprApEtherSwitchIntFIoPcEpEntry 18 }

cfprApEtherSwitchIntFIoPcEpPortId OBJECT-TYPE
    SYNTAX       CfprApEtherSwitchIntFIoPcEpPortId
    MAX-ACCESS   read-only
    STATUS       current
    DESCRIPTION
        "Cisco Firepower ether:SwitchIntFIoPcEp:portId
        managed object property"
    ::= { cfprApEtherSwitchIntFIoPcEpEntry 19 }

cfprApEtherSwitchIntFIoPcEpSlotId OBJECT-TYPE
    SYNTAX       Gauge32
    MAX-ACCESS   read-only
    STATUS       current
    DESCRIPTION
        "Cisco Firepower ether:SwitchIntFIoPcEp:slotId
        managed object property"
    ::= { cfprApEtherSwitchIntFIoPcEpEntry 20 }

cfprApEtherSwitchIntFIoPcEpStatusChangeTs OBJECT-TYPE
    SYNTAX       DateAndTime
    MAX-ACCESS   read-only
    STATUS       current
    DESCRIPTION
        "Cisco Firepower ether:SwitchIntFIoPcEp:statusChangeTs
        managed object property"
    ::= { cfprApEtherSwitchIntFIoPcEpEntry 21 }

cfprApEtherSwitchIntFIoPcEpSwitchId OBJECT-TYPE
    SYNTAX       CfprApNetworkSwitchId
    MAX-ACCESS   read-only
    STATUS       current
    DESCRIPTION
        "Cisco Firepower ether:SwitchIntFIoPcEp:switchId
        managed object property"
    ::= { cfprApEtherSwitchIntFIoPcEpEntry 22 }

cfprApEtherSwitchIntFIoPcEpTransport OBJECT-TYPE
    SYNTAX       CfprApNetworkTransport
    MAX-ACCESS   read-only
    STATUS       current
    DESCRIPTION
        "Cisco Firepower ether:SwitchIntFIoPcEp:transport
        managed object property"
    ::= { cfprApEtherSwitchIntFIoPcEpEntry 23 }

cfprApEtherSwitchIntFIoPcEpType OBJECT-TYPE
    SYNTAX       CfprApEtherIntFIoEpType
    MAX-ACCESS   read-only
    STATUS       current
    DESCRIPTION
        "Cisco Firepower ether:SwitchIntFIoPcEp:type managed
        object property"
    ::= { cfprApEtherSwitchIntFIoPcEpEntry 24 }

cfprApEtherTxStatsTable OBJECT-TYPE
    SYNTAX           SEQUENCE OF CfprApEtherTxStatsEntry
    MAX-ACCESS       not-accessible
    STATUS           current
    DESCRIPTION
        "Cisco Firepower ether:TxStats managed object table"
    ::= { cfprApEtherObjects 35 }

cfprApEtherTxStatsEntry OBJECT-TYPE
    SYNTAX           CfprApEtherTxStatsEntry
    MAX-ACCESS       not-accessible
    STATUS           current
    DESCRIPTION
        "Entry for the cfprApEtherTxStatsTable table."
    INDEX { cfprApEtherTxStatsInstanceId }
    ::= { cfprApEtherTxStatsTable 1 }

CfprApEtherTxStatsEntry ::= SEQUENCE {
    cfprApEtherTxStatsInstanceId                                     CfprApManagedObjectId,
    cfprApEtherTxStatsDn                                             CfprApManagedObjectDn,
    cfprApEtherTxStatsRn                                             SnmpAdminString,
    cfprApEtherTxStatsBroadcastPackets                               Unsigned64,
    cfprApEtherTxStatsBroadcastPacketsDelta                          Counter64,
    cfprApEtherTxStatsBroadcastPacketsDeltaAvg                       Unsigned64,
    cfprApEtherTxStatsBroadcastPacketsDeltaMax                       Unsigned64,
    cfprApEtherTxStatsBroadcastPacketsDeltaMin                       Unsigned64,
    cfprApEtherTxStatsIntervals                                      Gauge32,
    cfprApEtherTxStatsJumboPackets                                   Unsigned64,
    cfprApEtherTxStatsJumboPacketsDelta                              Counter64,
    cfprApEtherTxStatsJumboPacketsDeltaAvg                           Unsigned64,
    cfprApEtherTxStatsJumboPacketsDeltaMax                           Unsigned64,
    cfprApEtherTxStatsJumboPacketsDeltaMin                           Unsigned64,
    cfprApEtherTxStatsMulticastPackets                               Unsigned64,
    cfprApEtherTxStatsMulticastPacketsDelta                          Counter64,
    cfprApEtherTxStatsMulticastPacketsDeltaAvg                       Unsigned64,
    cfprApEtherTxStatsMulticastPacketsDeltaMax                       Unsigned64,
    cfprApEtherTxStatsMulticastPacketsDeltaMin                       Unsigned64,
    cfprApEtherTxStatsSuspect                                        TruthValue,
    cfprApEtherTxStatsThresholded                                    CfprApEtherTxStatsThresholded,
    cfprApEtherTxStatsTimeCollected                                  DateAndTime,
    cfprApEtherTxStatsTotalBytes                                     Unsigned64,
    cfprApEtherTxStatsTotalBytesDelta                                Counter64,
    cfprApEtherTxStatsTotalBytesDeltaAvg                             Unsigned64,
    cfprApEtherTxStatsTotalBytesDeltaMax                             Unsigned64,
    cfprApEtherTxStatsTotalBytesDeltaMin                             Unsigned64,
    cfprApEtherTxStatsTotalPackets                                   Unsigned64,
    cfprApEtherTxStatsTotalPacketsDelta                              Counter64,
    cfprApEtherTxStatsTotalPacketsDeltaAvg                           Unsigned64,
    cfprApEtherTxStatsTotalPacketsDeltaMax                           Unsigned64,
    cfprApEtherTxStatsTotalPacketsDeltaMin                           Unsigned64,
    cfprApEtherTxStatsUnicastPackets                                 Unsigned64,
    cfprApEtherTxStatsUnicastPacketsDelta                            Counter64,
    cfprApEtherTxStatsUnicastPacketsDeltaAvg                         Unsigned64,
    cfprApEtherTxStatsUnicastPacketsDeltaMax                         Unsigned64,
    cfprApEtherTxStatsUnicastPacketsDeltaMin                         Unsigned64,
    cfprApEtherTxStatsUpdate                                         Gauge32
}

cfprApEtherTxStatsInstanceId OBJECT-TYPE
    SYNTAX       CfprApManagedObjectId
    MAX-ACCESS   not-accessible
    STATUS       current
    DESCRIPTION
        "Instance identifier of the managed object."
    ::= { cfprApEtherTxStatsEntry 1 }

cfprApEtherTxStatsDn OBJECT-TYPE
    SYNTAX       CfprApManagedObjectDn
    MAX-ACCESS   read-only
    STATUS       current
    DESCRIPTION
        "Cisco Firepower ether:TxStats:dn managed object property"
    ::= { cfprApEtherTxStatsEntry 2 }

cfprApEtherTxStatsRn OBJECT-TYPE
    SYNTAX       SnmpAdminString
    MAX-ACCESS   read-only
    STATUS       current
    DESCRIPTION
        "Cisco Firepower ether:TxStats:rn managed object property"
    ::= { cfprApEtherTxStatsEntry 3 }

cfprApEtherTxStatsBroadcastPackets OBJECT-TYPE
    SYNTAX       Unsigned64
    MAX-ACCESS   read-only
    STATUS       current
    DESCRIPTION
        "Cisco Firepower ether:TxStats:broadcastPackets
        managed object property"
    ::= { cfprApEtherTxStatsEntry 4 }

cfprApEtherTxStatsBroadcastPacketsDelta OBJECT-TYPE
    SYNTAX       Counter64
    MAX-ACCESS   read-only
    STATUS       current
    DESCRIPTION
        "Cisco Firepower ether:TxStats:broadcastPacketsDelta
        managed object property"
    ::= { cfprApEtherTxStatsEntry 5 }

cfprApEtherTxStatsBroadcastPacketsDeltaAvg OBJECT-TYPE
    SYNTAX       Unsigned64
    MAX-ACCESS   read-only
    STATUS       current
    DESCRIPTION
        "Cisco Firepower ether:TxStats:broadcastPacketsDeltaAvg
        managed object property"
    ::= { cfprApEtherTxStatsEntry 6 }

cfprApEtherTxStatsBroadcastPacketsDeltaMax OBJECT-TYPE
    SYNTAX       Unsigned64
    MAX-ACCESS   read-only
    STATUS       current
    DESCRIPTION
        "Cisco Firepower ether:TxStats:broadcastPacketsDeltaMax
        managed object property"
    ::= { cfprApEtherTxStatsEntry 7 }

cfprApEtherTxStatsBroadcastPacketsDeltaMin OBJECT-TYPE
    SYNTAX       Unsigned64
    MAX-ACCESS   read-only
    STATUS       current
    DESCRIPTION
        "Cisco Firepower ether:TxStats:broadcastPacketsDeltaMin
        managed object property"
    ::= { cfprApEtherTxStatsEntry 8 }

cfprApEtherTxStatsIntervals OBJECT-TYPE
    SYNTAX       Gauge32
    MAX-ACCESS   read-only
    STATUS       current
    DESCRIPTION
        "Cisco Firepower ether:TxStats:intervals managed object property"
    ::= { cfprApEtherTxStatsEntry 9 }

cfprApEtherTxStatsJumboPackets OBJECT-TYPE
    SYNTAX       Unsigned64
    MAX-ACCESS   read-only
    STATUS       current
    DESCRIPTION
        "Cisco Firepower ether:TxStats:jumboPackets managed
        object property"
    ::= { cfprApEtherTxStatsEntry 10 }

cfprApEtherTxStatsJumboPacketsDelta OBJECT-TYPE
    SYNTAX       Counter64
    MAX-ACCESS   read-only
    STATUS       current
    DESCRIPTION
        "Cisco Firepower ether:TxStats:jumboPacketsDelta
        managed object property"
    ::= { cfprApEtherTxStatsEntry 11 }

cfprApEtherTxStatsJumboPacketsDeltaAvg OBJECT-TYPE
    SYNTAX       Unsigned64
    MAX-ACCESS   read-only
    STATUS       current
    DESCRIPTION
        "Cisco Firepower ether:TxStats:jumboPacketsDeltaAvg
        managed object property"
    ::= { cfprApEtherTxStatsEntry 12 }

cfprApEtherTxStatsJumboPacketsDeltaMax OBJECT-TYPE
    SYNTAX       Unsigned64
    MAX-ACCESS   read-only
    STATUS       current
    DESCRIPTION
        "Cisco Firepower ether:TxStats:jumboPacketsDeltaMax
        managed object property"
    ::= { cfprApEtherTxStatsEntry 13 }

cfprApEtherTxStatsJumboPacketsDeltaMin OBJECT-TYPE
    SYNTAX       Unsigned64
    MAX-ACCESS   read-only
    STATUS       current
    DESCRIPTION
        "Cisco Firepower ether:TxStats:jumboPacketsDeltaMin
        managed object property"
    ::= { cfprApEtherTxStatsEntry 14 }

cfprApEtherTxStatsMulticastPackets OBJECT-TYPE
    SYNTAX       Unsigned64
    MAX-ACCESS   read-only
    STATUS       current
    DESCRIPTION
        "Cisco Firepower ether:TxStats:multicastPackets
        managed object property"
    ::= { cfprApEtherTxStatsEntry 15 }

cfprApEtherTxStatsMulticastPacketsDelta OBJECT-TYPE
    SYNTAX       Counter64
    MAX-ACCESS   read-only
    STATUS       current
    DESCRIPTION
        "Cisco Firepower ether:TxStats:multicastPacketsDelta
        managed object property"
    ::= { cfprApEtherTxStatsEntry 16 }

cfprApEtherTxStatsMulticastPacketsDeltaAvg OBJECT-TYPE
    SYNTAX       Unsigned64
    MAX-ACCESS   read-only
    STATUS       current
    DESCRIPTION
        "Cisco Firepower ether:TxStats:multicastPacketsDeltaAvg
        managed object property"
    ::= { cfprApEtherTxStatsEntry 17 }

cfprApEtherTxStatsMulticastPacketsDeltaMax OBJECT-TYPE
    SYNTAX       Unsigned64
    MAX-ACCESS   read-only
    STATUS       current
    DESCRIPTION
        "Cisco Firepower ether:TxStats:multicastPacketsDeltaMax
        managed object property"
    ::= { cfprApEtherTxStatsEntry 18 }

cfprApEtherTxStatsMulticastPacketsDeltaMin OBJECT-TYPE
    SYNTAX       Unsigned64
    MAX-ACCESS   read-only
    STATUS       current
    DESCRIPTION
        "Cisco Firepower ether:TxStats:multicastPacketsDeltaMin
        managed object property"
    ::= { cfprApEtherTxStatsEntry 19 }

cfprApEtherTxStatsSuspect OBJECT-TYPE
    SYNTAX       TruthValue
    MAX-ACCESS   read-only
    STATUS       current
    DESCRIPTION
        "Cisco Firepower ether:TxStats:suspect managed object property"
    ::= { cfprApEtherTxStatsEntry 20 }

cfprApEtherTxStatsThresholded OBJECT-TYPE
    SYNTAX       CfprApEtherTxStatsThresholded
    MAX-ACCESS   read-only
    STATUS       current
    DESCRIPTION
        "Cisco Firepower ether:TxStats:thresholded managed
        object property"
    ::= { cfprApEtherTxStatsEntry 21 }

cfprApEtherTxStatsTimeCollected OBJECT-TYPE
    SYNTAX       DateAndTime
    MAX-ACCESS   read-only
    STATUS       current
    DESCRIPTION
        "Cisco Firepower ether:TxStats:timeCollected managed
        object property"
    ::= { cfprApEtherTxStatsEntry 22 }

cfprApEtherTxStatsTotalBytes OBJECT-TYPE
    SYNTAX       Unsigned64
    MAX-ACCESS   read-only
    STATUS       current
    DESCRIPTION
        "Cisco Firepower ether:TxStats:totalBytes managed object property"
    ::= { cfprApEtherTxStatsEntry 23 }

cfprApEtherTxStatsTotalBytesDelta OBJECT-TYPE
    SYNTAX       Counter64
    MAX-ACCESS   read-only
    STATUS       current
    DESCRIPTION
        "Cisco Firepower ether:TxStats:totalBytesDelta
        managed object property"
    ::= { cfprApEtherTxStatsEntry 24 }

cfprApEtherTxStatsTotalBytesDeltaAvg OBJECT-TYPE
    SYNTAX       Unsigned64
    MAX-ACCESS   read-only
    STATUS       current
    DESCRIPTION
        "Cisco Firepower ether:TxStats:totalBytesDeltaAvg
        managed object property"
    ::= { cfprApEtherTxStatsEntry 25 }

cfprApEtherTxStatsTotalBytesDeltaMax OBJECT-TYPE
    SYNTAX       Unsigned64
    MAX-ACCESS   read-only
    STATUS       current
    DESCRIPTION
        "Cisco Firepower ether:TxStats:totalBytesDeltaMax
        managed object property"
    ::= { cfprApEtherTxStatsEntry 26 }

cfprApEtherTxStatsTotalBytesDeltaMin OBJECT-TYPE
    SYNTAX       Unsigned64
    MAX-ACCESS   read-only
    STATUS       current
    DESCRIPTION
        "Cisco Firepower ether:TxStats:totalBytesDeltaMin
        managed object property"
    ::= { cfprApEtherTxStatsEntry 27 }

cfprApEtherTxStatsTotalPackets OBJECT-TYPE
    SYNTAX       Unsigned64
    MAX-ACCESS   read-only
    STATUS       current
    DESCRIPTION
        "Cisco Firepower ether:TxStats:totalPackets managed
        object property"
    ::= { cfprApEtherTxStatsEntry 28 }

cfprApEtherTxStatsTotalPacketsDelta OBJECT-TYPE
    SYNTAX       Counter64
    MAX-ACCESS   read-only
    STATUS       current
    DESCRIPTION
        "Cisco Firepower ether:TxStats:totalPacketsDelta
        managed object property"
    ::= { cfprApEtherTxStatsEntry 29 }

cfprApEtherTxStatsTotalPacketsDeltaAvg OBJECT-TYPE
    SYNTAX       Unsigned64
    MAX-ACCESS   read-only
    STATUS       current
    DESCRIPTION
        "Cisco Firepower ether:TxStats:totalPacketsDeltaAvg
        managed object property"
    ::= { cfprApEtherTxStatsEntry 30 }

cfprApEtherTxStatsTotalPacketsDeltaMax OBJECT-TYPE
    SYNTAX       Unsigned64
    MAX-ACCESS   read-only
    STATUS       current
    DESCRIPTION
        "Cisco Firepower ether:TxStats:totalPacketsDeltaMax
        managed object property"
    ::= { cfprApEtherTxStatsEntry 31 }

cfprApEtherTxStatsTotalPacketsDeltaMin OBJECT-TYPE
    SYNTAX       Unsigned64
    MAX-ACCESS   read-only
    STATUS       current
    DESCRIPTION
        "Cisco Firepower ether:TxStats:totalPacketsDeltaMin
        managed object property"
    ::= { cfprApEtherTxStatsEntry 32 }

cfprApEtherTxStatsUnicastPackets OBJECT-TYPE
    SYNTAX       Unsigned64
    MAX-ACCESS   read-only
    STATUS       current
    DESCRIPTION
        "Cisco Firepower ether:TxStats:unicastPackets managed
        object property"
    ::= { cfprApEtherTxStatsEntry 33 }

cfprApEtherTxStatsUnicastPacketsDelta OBJECT-TYPE
    SYNTAX       Counter64
    MAX-ACCESS   read-only
    STATUS       current
    DESCRIPTION
        "Cisco Firepower ether:TxStats:unicastPacketsDelta
        managed object property"
    ::= { cfprApEtherTxStatsEntry 34 }

cfprApEtherTxStatsUnicastPacketsDeltaAvg OBJECT-TYPE
    SYNTAX       Unsigned64
    MAX-ACCESS   read-only
    STATUS       current
    DESCRIPTION
        "Cisco Firepower ether:TxStats:unicastPacketsDeltaAvg
        managed object property"
    ::= { cfprApEtherTxStatsEntry 35 }

cfprApEtherTxStatsUnicastPacketsDeltaMax OBJECT-TYPE
    SYNTAX       Unsigned64
    MAX-ACCESS   read-only
    STATUS       current
    DESCRIPTION
        "Cisco Firepower ether:TxStats:unicastPacketsDeltaMax
        managed object property"
    ::= { cfprApEtherTxStatsEntry 36 }

cfprApEtherTxStatsUnicastPacketsDeltaMin OBJECT-TYPE
    SYNTAX       Unsigned64
    MAX-ACCESS   read-only
    STATUS       current
    DESCRIPTION
        "Cisco Firepower ether:TxStats:unicastPacketsDeltaMin
        managed object property"
    ::= { cfprApEtherTxStatsEntry 37 }

cfprApEtherTxStatsUpdate OBJECT-TYPE
    SYNTAX       Gauge32
    MAX-ACCESS   read-only
    STATUS       current
    DESCRIPTION
        "Cisco Firepower ether:TxStats:update managed object property"
    ::= { cfprApEtherTxStatsEntry 38 }

cfprApEtherTxStatsHistTable OBJECT-TYPE
    SYNTAX           SEQUENCE OF CfprApEtherTxStatsHistEntry
    MAX-ACCESS       not-accessible
    STATUS           current
    DESCRIPTION
        "Cisco Firepower ether:TxStatsHist managed object table"
    ::= { cfprApEtherObjects 36 }

cfprApEtherTxStatsHistEntry OBJECT-TYPE
    SYNTAX           CfprApEtherTxStatsHistEntry
    MAX-ACCESS       not-accessible
    STATUS           current
    DESCRIPTION
        "Entry for the cfprApEtherTxStatsHistTable table."
    INDEX { cfprApEtherTxStatsHistInstanceId }
    ::= { cfprApEtherTxStatsHistTable 1 }

CfprApEtherTxStatsHistEntry ::= SEQUENCE {
    cfprApEtherTxStatsHistInstanceId                                 CfprApManagedObjectId,
    cfprApEtherTxStatsHistDn                                         CfprApManagedObjectDn,
    cfprApEtherTxStatsHistRn                                         SnmpAdminString,
    cfprApEtherTxStatsHistBroadcastPackets                           Unsigned64,
    cfprApEtherTxStatsHistBroadcastPacketsDelta                      Unsigned64,
    cfprApEtherTxStatsHistBroadcastPacketsDeltaAvg                   Unsigned64,
    cfprApEtherTxStatsHistBroadcastPacketsDeltaMax                   Unsigned64,
    cfprApEtherTxStatsHistBroadcastPacketsDeltaMin                   Unsigned64,
    cfprApEtherTxStatsHistId                                         Unsigned64,
    cfprApEtherTxStatsHistJumboPackets                               Unsigned64,
    cfprApEtherTxStatsHistJumboPacketsDelta                          Unsigned64,
    cfprApEtherTxStatsHistJumboPacketsDeltaAvg                       Unsigned64,
    cfprApEtherTxStatsHistJumboPacketsDeltaMax                       Unsigned64,
    cfprApEtherTxStatsHistJumboPacketsDeltaMin                       Unsigned64,
    cfprApEtherTxStatsHistMostRecent                                 TruthValue,
    cfprApEtherTxStatsHistMulticastPackets                           Unsigned64,
    cfprApEtherTxStatsHistMulticastPacketsDelta                      Unsigned64,
    cfprApEtherTxStatsHistMulticastPacketsDeltaAvg                   Unsigned64,
    cfprApEtherTxStatsHistMulticastPacketsDeltaMax                   Unsigned64,
    cfprApEtherTxStatsHistMulticastPacketsDeltaMin                   Unsigned64,
    cfprApEtherTxStatsHistSuspect                                    TruthValue,
    cfprApEtherTxStatsHistThresholded                                CfprApEtherTxStatsHistThresholded,
    cfprApEtherTxStatsHistTimeCollected                              DateAndTime,
    cfprApEtherTxStatsHistTotalBytes                                 Unsigned64,
    cfprApEtherTxStatsHistTotalBytesDelta                            Unsigned64,
    cfprApEtherTxStatsHistTotalBytesDeltaAvg                         Unsigned64,
    cfprApEtherTxStatsHistTotalBytesDeltaMax                         Unsigned64,
    cfprApEtherTxStatsHistTotalBytesDeltaMin                         Unsigned64,
    cfprApEtherTxStatsHistTotalPackets                               Unsigned64,
    cfprApEtherTxStatsHistTotalPacketsDelta                          Unsigned64,
    cfprApEtherTxStatsHistTotalPacketsDeltaAvg                       Unsigned64,
    cfprApEtherTxStatsHistTotalPacketsDeltaMax                       Unsigned64,
    cfprApEtherTxStatsHistTotalPacketsDeltaMin                       Unsigned64,
    cfprApEtherTxStatsHistUnicastPackets                             Unsigned64,
    cfprApEtherTxStatsHistUnicastPacketsDelta                        Unsigned64,
    cfprApEtherTxStatsHistUnicastPacketsDeltaAvg                     Unsigned64,
    cfprApEtherTxStatsHistUnicastPacketsDeltaMax                     Unsigned64,
    cfprApEtherTxStatsHistUnicastPacketsDeltaMin                     Unsigned64
}

cfprApEtherTxStatsHistInstanceId OBJECT-TYPE
    SYNTAX       CfprApManagedObjectId
    MAX-ACCESS   not-accessible
    STATUS       current
    DESCRIPTION
        "Instance identifier of the managed object."
    ::= { cfprApEtherTxStatsHistEntry 1 }

cfprApEtherTxStatsHistDn OBJECT-TYPE
    SYNTAX       CfprApManagedObjectDn
    MAX-ACCESS   read-only
    STATUS       current
    DESCRIPTION
        "Cisco Firepower ether:TxStatsHist:dn managed object property"
    ::= { cfprApEtherTxStatsHistEntry 2 }

cfprApEtherTxStatsHistRn OBJECT-TYPE
    SYNTAX       SnmpAdminString
    MAX-ACCESS   read-only
    STATUS       current
    DESCRIPTION
        "Cisco Firepower ether:TxStatsHist:rn managed object property"
    ::= { cfprApEtherTxStatsHistEntry 3 }

cfprApEtherTxStatsHistBroadcastPackets OBJECT-TYPE
    SYNTAX       Unsigned64
    MAX-ACCESS   read-only
    STATUS       current
    DESCRIPTION
        "Cisco Firepower ether:TxStatsHist:broadcastPackets
        managed object property"
    ::= { cfprApEtherTxStatsHistEntry 4 }

cfprApEtherTxStatsHistBroadcastPacketsDelta OBJECT-TYPE
    SYNTAX       Unsigned64
    MAX-ACCESS   read-only
    STATUS       current
    DESCRIPTION
        "Cisco Firepower ether:TxStatsHist:broadcastPacketsDelta
        managed object property"
    ::= { cfprApEtherTxStatsHistEntry 5 }

cfprApEtherTxStatsHistBroadcastPacketsDeltaAvg OBJECT-TYPE
    SYNTAX       Unsigned64
    MAX-ACCESS   read-only
    STATUS       current
    DESCRIPTION
        "Cisco Firepower ether:TxStatsHist:broadcastPacketsDeltaAvg
        managed object property"
    ::= { cfprApEtherTxStatsHistEntry 6 }

cfprApEtherTxStatsHistBroadcastPacketsDeltaMax OBJECT-TYPE
    SYNTAX       Unsigned64
    MAX-ACCESS   read-only
    STATUS       current
    DESCRIPTION
        "Cisco Firepower ether:TxStatsHist:broadcastPacketsDeltaMax
        managed object property"
    ::= { cfprApEtherTxStatsHistEntry 7 }

cfprApEtherTxStatsHistBroadcastPacketsDeltaMin OBJECT-TYPE
    SYNTAX       Unsigned64
    MAX-ACCESS   read-only
    STATUS       current
    DESCRIPTION
        "Cisco Firepower ether:TxStatsHist:broadcastPacketsDeltaMin
        managed object property"
    ::= { cfprApEtherTxStatsHistEntry 8 }

cfprApEtherTxStatsHistId OBJECT-TYPE
    SYNTAX       Unsigned64
    MAX-ACCESS   read-only
    STATUS       current
    DESCRIPTION
        "Cisco Firepower ether:TxStatsHist:id managed object property"
    ::= { cfprApEtherTxStatsHistEntry 9 }

cfprApEtherTxStatsHistJumboPackets OBJECT-TYPE
    SYNTAX       Unsigned64
    MAX-ACCESS   read-only
    STATUS       current
    DESCRIPTION
        "Cisco Firepower ether:TxStatsHist:jumboPackets
        managed object property"
    ::= { cfprApEtherTxStatsHistEntry 10 }

cfprApEtherTxStatsHistJumboPacketsDelta OBJECT-TYPE
    SYNTAX       Unsigned64
    MAX-ACCESS   read-only
    STATUS       current
    DESCRIPTION
        "Cisco Firepower ether:TxStatsHist:jumboPacketsDelta
        managed object property"
    ::= { cfprApEtherTxStatsHistEntry 11 }

cfprApEtherTxStatsHistJumboPacketsDeltaAvg OBJECT-TYPE
    SYNTAX       Unsigned64
    MAX-ACCESS   read-only
    STATUS       current
    DESCRIPTION
        "Cisco Firepower ether:TxStatsHist:jumboPacketsDeltaAvg
        managed object property"
    ::= { cfprApEtherTxStatsHistEntry 12 }

cfprApEtherTxStatsHistJumboPacketsDeltaMax OBJECT-TYPE
    SYNTAX       Unsigned64
    MAX-ACCESS   read-only
    STATUS       current
    DESCRIPTION
        "Cisco Firepower ether:TxStatsHist:jumboPacketsDeltaMax
        managed object property"
    ::= { cfprApEtherTxStatsHistEntry 13 }

cfprApEtherTxStatsHistJumboPacketsDeltaMin OBJECT-TYPE
    SYNTAX       Unsigned64
    MAX-ACCESS   read-only
    STATUS       current
    DESCRIPTION
        "Cisco Firepower ether:TxStatsHist:jumboPacketsDeltaMin
        managed object property"
    ::= { cfprApEtherTxStatsHistEntry 14 }

cfprApEtherTxStatsHistMostRecent OBJECT-TYPE
    SYNTAX       TruthValue
    MAX-ACCESS   read-only
    STATUS       current
    DESCRIPTION
        "Cisco Firepower ether:TxStatsHist:mostRecent managed
        object property"
    ::= { cfprApEtherTxStatsHistEntry 15 }

cfprApEtherTxStatsHistMulticastPackets OBJECT-TYPE
    SYNTAX       Unsigned64
    MAX-ACCESS   read-only
    STATUS       current
    DESCRIPTION
        "Cisco Firepower ether:TxStatsHist:multicastPackets
        managed object property"
    ::= { cfprApEtherTxStatsHistEntry 16 }

cfprApEtherTxStatsHistMulticastPacketsDelta OBJECT-TYPE
    SYNTAX       Unsigned64
    MAX-ACCESS   read-only
    STATUS       current
    DESCRIPTION
        "Cisco Firepower ether:TxStatsHist:multicastPacketsDelta
        managed object property"
    ::= { cfprApEtherTxStatsHistEntry 17 }

cfprApEtherTxStatsHistMulticastPacketsDeltaAvg OBJECT-TYPE
    SYNTAX       Unsigned64
    MAX-ACCESS   read-only
    STATUS       current
    DESCRIPTION
        "Cisco Firepower ether:TxStatsHist:multicastPacketsDeltaAvg
        managed object property"
    ::= { cfprApEtherTxStatsHistEntry 18 }

cfprApEtherTxStatsHistMulticastPacketsDeltaMax OBJECT-TYPE
    SYNTAX       Unsigned64
    MAX-ACCESS   read-only
    STATUS       current
    DESCRIPTION
        "Cisco Firepower ether:TxStatsHist:multicastPacketsDeltaMax
        managed object property"
    ::= { cfprApEtherTxStatsHistEntry 19 }

cfprApEtherTxStatsHistMulticastPacketsDeltaMin OBJECT-TYPE
    SYNTAX       Unsigned64
    MAX-ACCESS   read-only
    STATUS       current
    DESCRIPTION
        "Cisco Firepower ether:TxStatsHist:multicastPacketsDeltaMin
        managed object property"
    ::= { cfprApEtherTxStatsHistEntry 20 }

cfprApEtherTxStatsHistSuspect OBJECT-TYPE
    SYNTAX       TruthValue
    MAX-ACCESS   read-only
    STATUS       current
    DESCRIPTION
        "Cisco Firepower ether:TxStatsHist:suspect managed
        object property"
    ::= { cfprApEtherTxStatsHistEntry 21 }

cfprApEtherTxStatsHistThresholded OBJECT-TYPE
    SYNTAX       CfprApEtherTxStatsHistThresholded
    MAX-ACCESS   read-only
    STATUS       current
    DESCRIPTION
        "Cisco Firepower ether:TxStatsHist:thresholded
        managed object property"
    ::= { cfprApEtherTxStatsHistEntry 22 }

cfprApEtherTxStatsHistTimeCollected OBJECT-TYPE
    SYNTAX       DateAndTime
    MAX-ACCESS   read-only
    STATUS       current
    DESCRIPTION
        "Cisco Firepower ether:TxStatsHist:timeCollected
        managed object property"
    ::= { cfprApEtherTxStatsHistEntry 23 }

cfprApEtherTxStatsHistTotalBytes OBJECT-TYPE
    SYNTAX       Unsigned64
    MAX-ACCESS   read-only
    STATUS       current
    DESCRIPTION
        "Cisco Firepower ether:TxStatsHist:totalBytes managed
        object property"
    ::= { cfprApEtherTxStatsHistEntry 24 }

cfprApEtherTxStatsHistTotalBytesDelta OBJECT-TYPE
    SYNTAX       Unsigned64
    MAX-ACCESS   read-only
    STATUS       current
    DESCRIPTION
        "Cisco Firepower ether:TxStatsHist:totalBytesDelta
        managed object property"
    ::= { cfprApEtherTxStatsHistEntry 25 }

cfprApEtherTxStatsHistTotalBytesDeltaAvg OBJECT-TYPE
    SYNTAX       Unsigned64
    MAX-ACCESS   read-only
    STATUS       current
    DESCRIPTION
        "Cisco Firepower ether:TxStatsHist:totalBytesDeltaAvg
        managed object property"
    ::= { cfprApEtherTxStatsHistEntry 26 }

cfprApEtherTxStatsHistTotalBytesDeltaMax OBJECT-TYPE
    SYNTAX       Unsigned64
    MAX-ACCESS   read-only
    STATUS       current
    DESCRIPTION
        "Cisco Firepower ether:TxStatsHist:totalBytesDeltaMax
        managed object property"
    ::= { cfprApEtherTxStatsHistEntry 27 }

cfprApEtherTxStatsHistTotalBytesDeltaMin OBJECT-TYPE
    SYNTAX       Unsigned64
    MAX-ACCESS   read-only
    STATUS       current
    DESCRIPTION
        "Cisco Firepower ether:TxStatsHist:totalBytesDeltaMin
        managed object property"
    ::= { cfprApEtherTxStatsHistEntry 28 }

cfprApEtherTxStatsHistTotalPackets OBJECT-TYPE
    SYNTAX       Unsigned64
    MAX-ACCESS   read-only
    STATUS       current
    DESCRIPTION
        "Cisco Firepower ether:TxStatsHist:totalPackets
        managed object property"
    ::= { cfprApEtherTxStatsHistEntry 29 }

cfprApEtherTxStatsHistTotalPacketsDelta OBJECT-TYPE
    SYNTAX       Unsigned64
    MAX-ACCESS   read-only
    STATUS       current
    DESCRIPTION
        "Cisco Firepower ether:TxStatsHist:totalPacketsDelta
        managed object property"
    ::= { cfprApEtherTxStatsHistEntry 30 }

cfprApEtherTxStatsHistTotalPacketsDeltaAvg OBJECT-TYPE
    SYNTAX       Unsigned64
    MAX-ACCESS   read-only
    STATUS       current
    DESCRIPTION
        "Cisco Firepower ether:TxStatsHist:totalPacketsDeltaAvg
        managed object property"
    ::= { cfprApEtherTxStatsHistEntry 31 }

cfprApEtherTxStatsHistTotalPacketsDeltaMax OBJECT-TYPE
    SYNTAX       Unsigned64
    MAX-ACCESS   read-only
    STATUS       current
    DESCRIPTION
        "Cisco Firepower ether:TxStatsHist:totalPacketsDeltaMax
        managed object property"
    ::= { cfprApEtherTxStatsHistEntry 32 }

cfprApEtherTxStatsHistTotalPacketsDeltaMin OBJECT-TYPE
    SYNTAX       Unsigned64
    MAX-ACCESS   read-only
    STATUS       current
    DESCRIPTION
        "Cisco Firepower ether:TxStatsHist:totalPacketsDeltaMin
        managed object property"
    ::= { cfprApEtherTxStatsHistEntry 33 }

cfprApEtherTxStatsHistUnicastPackets OBJECT-TYPE
    SYNTAX       Unsigned64
    MAX-ACCESS   read-only
    STATUS       current
    DESCRIPTION
        "Cisco Firepower ether:TxStatsHist:unicastPackets
        managed object property"
    ::= { cfprApEtherTxStatsHistEntry 34 }

cfprApEtherTxStatsHistUnicastPacketsDelta OBJECT-TYPE
    SYNTAX       Unsigned64
    MAX-ACCESS   read-only
    STATUS       current
    DESCRIPTION
        "Cisco Firepower ether:TxStatsHist:unicastPacketsDelta
        managed object property"
    ::= { cfprApEtherTxStatsHistEntry 35 }

cfprApEtherTxStatsHistUnicastPacketsDeltaAvg OBJECT-TYPE
    SYNTAX       Unsigned64
    MAX-ACCESS   read-only
    STATUS       current
    DESCRIPTION
        "Cisco Firepower ether:TxStatsHist:unicastPacketsDeltaAvg
        managed object property"
    ::= { cfprApEtherTxStatsHistEntry 36 }

cfprApEtherTxStatsHistUnicastPacketsDeltaMax OBJECT-TYPE
    SYNTAX       Unsigned64
    MAX-ACCESS   read-only
    STATUS       current
    DESCRIPTION
        "Cisco Firepower ether:TxStatsHist:unicastPacketsDeltaMax
        managed object property"
    ::= { cfprApEtherTxStatsHistEntry 37 }

cfprApEtherTxStatsHistUnicastPacketsDeltaMin OBJECT-TYPE
    SYNTAX       Unsigned64
    MAX-ACCESS   read-only
    STATUS       current
    DESCRIPTION
        "Cisco Firepower ether:TxStatsHist:unicastPacketsDeltaMin
        managed object property"
    ::= { cfprApEtherTxStatsHistEntry 38 }

END
