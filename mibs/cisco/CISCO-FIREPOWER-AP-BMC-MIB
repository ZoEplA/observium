-- *********************************************************************
-- CISCO-FIREPOWER-AP-BMC-MIB.my
-- 
-- MIB representation of the Cisco Firepower
-- BMC management information model package
-- 
-- Created August 2017 by Charles Bullis
-- 
-- Copyright (c) 2005-2017 Cisco Systems, Inc. All rights reserved.
-- 
-- *********************************************************************

CISCO-FIREPOWER-AP-BMC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApBmcSELCntEqptClassId,
    CfprApBmcSELCntEqptInstIdPropId,
    CfprApBmcSELCntStatsClassId
        FROM CISCO-FIREPOWER-AP-TC-MIB;

cfprApBmcObjects MODULE-IDENTITY
    LAST-UPDATED    "201708230000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        BMC management information model package"
    ::= { ciscoFirepowerApMIBObjects 6 }

cfprApBmcSELCounterTable OBJECT-TYPE
    SYNTAX           SEQUENCE OF CfprApBmcSELCounterEntry
    MAX-ACCESS       not-accessible
    STATUS           current
    DESCRIPTION
        "Cisco Firepower bmc:SELCounter managed object table"
    ::= { cfprApBmcObjects 1 }

cfprApBmcSELCounterEntry OBJECT-TYPE
    SYNTAX           CfprApBmcSELCounterEntry
    MAX-ACCESS       not-accessible
    STATUS           current
    DESCRIPTION
        "Entry for the cfprApBmcSELCounterTable table."
    INDEX { cfprApBmcSELCounterInstanceId }
    ::= { cfprApBmcSELCounterTable 1 }

CfprApBmcSELCounterEntry ::= SEQUENCE {
    cfprApBmcSELCounterInstanceId                                    CfprApManagedObjectId,
    cfprApBmcSELCounterDn                                            CfprApManagedObjectDn,
    cfprApBmcSELCounterRn                                            SnmpAdminString,
    cfprApBmcSELCounterBitmask                                       SnmpAdminString,
    cfprApBmcSELCounterCollInterval                                  Gauge32,
    cfprApBmcSELCounterContClassId                                   CfprApBmcSELCntEqptClassId,
    cfprApBmcSELCounterContInstId                                    SnmpAdminString,
    cfprApBmcSELCounterContInstIdPropId                              CfprApBmcSELCntEqptInstIdPropId,
    cfprApBmcSELCounterEqptClassId                                   CfprApBmcSELCntEqptClassId,
    cfprApBmcSELCounterEqptInstId                                    SnmpAdminString,
    cfprApBmcSELCounterEqptInstIdPropId                              CfprApBmcSELCntEqptInstIdPropId,
    cfprApBmcSELCounterGlobalId                                      SnmpAdminString,
    cfprApBmcSELCounterLocalId                                       SnmpAdminString,
    cfprApBmcSELCounterPcGlobalId                                    SnmpAdminString,
    cfprApBmcSELCounterPcLocalId                                     SnmpAdminString,
    cfprApBmcSELCounterStatsClassId                                  CfprApBmcSELCntStatsClassId,
    cfprApBmcSELCounterStatsPropId                                   INTEGER,
    cfprApBmcSELCounterThreshold                                     Gauge32,
    cfprApBmcSELCounterValue                                         SnmpAdminString
}

cfprApBmcSELCounterInstanceId OBJECT-TYPE
    SYNTAX       CfprApManagedObjectId
    MAX-ACCESS   not-accessible
    STATUS       current
    DESCRIPTION
        "Instance identifier of the managed object."
    ::= { cfprApBmcSELCounterEntry 1 }

cfprApBmcSELCounterDn OBJECT-TYPE
    SYNTAX       CfprApManagedObjectDn
    MAX-ACCESS   read-only
    STATUS       current
    DESCRIPTION
        "Cisco Firepower bmc:SELCounter:dn managed object property"
    ::= { cfprApBmcSELCounterEntry 2 }

cfprApBmcSELCounterRn OBJECT-TYPE
    SYNTAX       SnmpAdminString
    MAX-ACCESS   read-only
    STATUS       current
    DESCRIPTION
        "Cisco Firepower bmc:SELCounter:rn managed object property"
    ::= { cfprApBmcSELCounterEntry 3 }

cfprApBmcSELCounterBitmask OBJECT-TYPE
    SYNTAX       SnmpAdminString
    MAX-ACCESS   read-only
    STATUS       current
    DESCRIPTION
        "Cisco Firepower bmc:SELCounter:bitmask managed object property"
    ::= { cfprApBmcSELCounterEntry 4 }

cfprApBmcSELCounterCollInterval OBJECT-TYPE
    SYNTAX       Gauge32
    MAX-ACCESS   read-only
    STATUS       current
    DESCRIPTION
        "Cisco Firepower bmc:SELCounter:collInterval managed
        object property"
    ::= { cfprApBmcSELCounterEntry 5 }

cfprApBmcSELCounterContClassId OBJECT-TYPE
    SYNTAX       CfprApBmcSELCntEqptClassId
    MAX-ACCESS   read-only
    STATUS       current
    DESCRIPTION
        "Cisco Firepower bmc:SELCounter:contClassId managed
        object property"
    ::= { cfprApBmcSELCounterEntry 6 }

cfprApBmcSELCounterContInstId OBJECT-TYPE
    SYNTAX       SnmpAdminString
    MAX-ACCESS   read-only
    STATUS       current
    DESCRIPTION
        "Cisco Firepower bmc:SELCounter:contInstId managed
        object property"
    ::= { cfprApBmcSELCounterEntry 7 }

cfprApBmcSELCounterContInstIdPropId OBJECT-TYPE
    SYNTAX       CfprApBmcSELCntEqptInstIdPropId
    MAX-ACCESS   read-only
    STATUS       current
    DESCRIPTION
        "Cisco Firepower bmc:SELCounter:contInstIdPropId
        managed object property"
    ::= { cfprApBmcSELCounterEntry 8 }

cfprApBmcSELCounterEqptClassId OBJECT-TYPE
    SYNTAX       CfprApBmcSELCntEqptClassId
    MAX-ACCESS   read-only
    STATUS       current
    DESCRIPTION
        "Cisco Firepower bmc:SELCounter:eqptClassId managed
        object property"
    ::= { cfprApBmcSELCounterEntry 9 }

cfprApBmcSELCounterEqptInstId OBJECT-TYPE
    SYNTAX       SnmpAdminString
    MAX-ACCESS   read-only
    STATUS       current
    DESCRIPTION
        "Cisco Firepower bmc:SELCounter:eqptInstId managed
        object property"
    ::= { cfprApBmcSELCounterEntry 10 }

cfprApBmcSELCounterEqptInstIdPropId OBJECT-TYPE
    SYNTAX       CfprApBmcSELCntEqptInstIdPropId
    MAX-ACCESS   read-only
    STATUS       current
    DESCRIPTION
        "Cisco Firepower bmc:SELCounter:eqptInstIdPropId
        managed object property"
    ::= { cfprApBmcSELCounterEntry 11 }

cfprApBmcSELCounterGlobalId OBJECT-TYPE
    SYNTAX       SnmpAdminString
    MAX-ACCESS   read-only
    STATUS       current
    DESCRIPTION
        "Cisco Firepower bmc:SELCounter:globalId managed object property"
    ::= { cfprApBmcSELCounterEntry 12 }

cfprApBmcSELCounterLocalId OBJECT-TYPE
    SYNTAX       SnmpAdminString
    MAX-ACCESS   read-only
    STATUS       current
    DESCRIPTION
        "Cisco Firepower bmc:SELCounter:localId managed object property"
    ::= { cfprApBmcSELCounterEntry 13 }

cfprApBmcSELCounterPcGlobalId OBJECT-TYPE
    SYNTAX       SnmpAdminString
    MAX-ACCESS   read-only
    STATUS       current
    DESCRIPTION
        "Cisco Firepower bmc:SELCounter:pcGlobalId managed
        object property"
    ::= { cfprApBmcSELCounterEntry 14 }

cfprApBmcSELCounterPcLocalId OBJECT-TYPE
    SYNTAX       SnmpAdminString
    MAX-ACCESS   read-only
    STATUS       current
    DESCRIPTION
        "Cisco Firepower bmc:SELCounter:pcLocalId managed object property"
    ::= { cfprApBmcSELCounterEntry 15 }

cfprApBmcSELCounterStatsClassId OBJECT-TYPE
    SYNTAX       CfprApBmcSELCntStatsClassId
    MAX-ACCESS   read-only
    STATUS       current
    DESCRIPTION
        "Cisco Firepower bmc:SELCounter:statsClassId managed
        object property"
    ::= { cfprApBmcSELCounterEntry 16 }

cfprApBmcSELCounterStatsPropId OBJECT-TYPE
    SYNTAX       INTEGER
    MAX-ACCESS   read-only
    STATUS       current
    DESCRIPTION
        "Cisco Firepower bmc:SELCounter:statsPropId managed
        object property"
    ::= { cfprApBmcSELCounterEntry 17 }

cfprApBmcSELCounterThreshold OBJECT-TYPE
    SYNTAX       Gauge32
    MAX-ACCESS   read-only
    STATUS       current
    DESCRIPTION
        "Cisco Firepower bmc:SELCounter:threshold managed object property"
    ::= { cfprApBmcSELCounterEntry 18 }

cfprApBmcSELCounterValue OBJECT-TYPE
    SYNTAX       SnmpAdminString
    MAX-ACCESS   read-only
    STATUS       current
    DESCRIPTION
        "Cisco Firepower bmc:SELCounter:value managed object property"
    ::= { cfprApBmcSELCounterEntry 19 }

END
