-- *********************************************************************
-- CISCO-FIREPOWER-AP-TC-MIB.my
-- 
-- MIB representation of the Cisco Firepower
-- TEXTUALCONVENTIONS management information model package
-- 
-- Created August 2017 by Charles Bullis
-- 
-- Copyright (c) 2005-2017 Cisco Systems, Inc. All rights reserved.
-- 
-- *********************************************************************

CISCO-FIREPOWER-AP-TC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIB,
    CfprApManagedObjectId,
    CfprApManagedObjectDn
        FROM CISCO-FIREPOWER-AP-MIB;

cfprApTextualConventionsObjects MODULE-IDENTITY
    LAST-UPDATED    "201708230000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        TEXTUALCONVENTIONS management information model package"
    ::= { ciscoFirepowerApMIB 4 }

CfprApAaaAccess ::= TEXTUAL-CONVENTION
    STATUS        current
    DESCRIPTION
        ""
    SYNTAX        BITS
    {
        readOnly(0),
        admin(1),
        operations(2),
        fault(3),
        aaa(4),
        podConfig(5),
        podPolicy(6),
        podSecurity(7),
        podQos(8),
        extLanConfig(9),
        extLanPolicy(10),
        extLanSecurity(11),
        extLanQos(12),
        extSanConfig(13),
        extSanPolicy(14),
        extSanSecurity(15),
        extSanQos(16),
        pnEquipment(17),
        pnPolicy(18),
        pnSecurity(19),
        pnMaintenance(20),
        lsConfig(21),
        lsStorage(22),
        lsNetwork(23),
        lsSecurity(24),
        lsServer(25),
        lsQos(26),
        lsConfigPolicy(27),
        lsStoragePolicy(28),
        lsNetworkPolicy(29),
        lsSecurityPolicy(30),
        lsServerPolicy(31),
        lsQosPolicy(32),
        lsExtAccess(33),
        powerMgmt(34),
        lsServerOper(36),
        lsCompute(37),
        orgManagement(38)
    }

CfprApAaaAccountStatus ::= TEXTUAL-CONVENTION
    STATUS        current
    DESCRIPTION
        ""
    SYNTAX        INTEGER
    {
        active(0),
        inactive(1)
    }

CfprApAaaAuthRealmFsmCurrentFsm ::= TEXTUAL-CONVENTION
    STATUS        current
    DESCRIPTION
        ""
    SYNTAX        INTEGER
    {
        nop(0),
        updateRealm(352)
    }

CfprApAaaAuthRealmFsmStageName ::= TEXTUAL-CONVENTION
    STATUS        current
    DESCRIPTION
        ""
    SYNTAX        INTEGER
    {
        nop(0),
        updateRealmBegin(352),
        updateRealmSetRealmLocal(353),
        updateRealmSetRealmPeer(354),
        updateRealmFail(538),
        updateRealmSuccess(539)
    }

CfprApAaaCimcSessionType ::= TEXTUAL-CONVENTION
    STATUS        current
    DESCRIPTION
        ""
    SYNTAX        INTEGER
    {
        all(0),
        kvm(1),
        vmedia(2),
        sol(3)
    }

CfprApAaaClear ::= TEXTUAL-CONVENTION
    STATUS        current
    DESCRIPTION
        ""
    SYNTAX        INTEGER
    {
        no(0),
        yes(1)
    }

CfprApAaaConfigState ::= TEXTUAL-CONVENTION
    STATUS        current
    DESCRIPTION
        ""
    SYNTAX        INTEGER
    {
        ok(0),
        notApplied(1)
    }

CfprApAaaDomainAuthRealm ::= TEXTUAL-CONVENTION
    STATUS        current
    DESCRIPTION
        ""
    SYNTAX        INTEGER
    {
        local(0),
        radius(1),
        tacacs(2),
        ldap(3),
        none(4)
    }

CfprApAaaEpAccess ::= TEXTUAL-CONVENTION
    STATUS        current
    DESCRIPTION
        ""
    SYNTAX        INTEGER
    {
        readonly(1),
        admin(2)
    }

CfprApAaaEpFsmCurrentFsm ::= TEXTUAL-CONVENTION
    STATUS        current
    DESCRIPTION
        ""
    SYNTAX        INTEGER
    {
        nop(0),
        updateEp(349)
    }

CfprApAaaEpFsmStageName ::= TEXTUAL-CONVENTION
    STATUS        current
    DESCRIPTION
        ""
    SYNTAX        INTEGER
    {
        nop(0),
        updateEpBegin(349),
        updateEpSetEpLocal(350),
        updateEpSetEpPeer(351),
        updateEpFail(536),
        updateEpSuccess(537)
    }

CfprApAaaEpFsmTaskItem ::= TEXTUAL-CONVENTION
    STATUS        current
    DESCRIPTION
        ""
    SYNTAX        INTEGER
    {
        nop(0),
        updateEp(349)
    }

CfprApAaaExtMgmtAccess ::= TEXTUAL-CONVENTION
    STATUS        current
    DESCRIPTION
        ""
    SYNTAX        INTEGER
    {
        kvm(1)
    }

CfprApAaaIpmiOverLan ::= TEXTUAL-CONVENTION
    STATUS        current
    DESCRIPTION
        ""
    SYNTAX        INTEGER
    {
        disable(0),
        enable(1)
    }

CfprApAaaLdapEpFsmCurrentFsm ::= TEXTUAL-CONVENTION
    STATUS        current
    DESCRIPTION
        ""
    SYNTAX        INTEGER
    {
        nop(0),
        updateEp(349)
    }

CfprApAaaLdapEpFsmStageName ::= TEXTUAL-CONVENTION
    STATUS        current
    DESCRIPTION
        ""
    SYNTAX        INTEGER
    {
        nop(0),
        updateEpBegin(349),
        updateEpSetEpLocal(350),
        updateEpSetEpPeer(351),
        updateEpFail(536),
        updateEpSuccess(537)
    }

CfprApAaaLdapGroupRuleAuthorization ::= TEXTUAL-CONVENTION
    STATUS        current
    DESCRIPTION
        ""
    SYNTAX        INTEGER
    {
        disable(0),
        enable(1)
    }

CfprApAaaLdapGroupRuleTraversal ::= TEXTUAL-CONVENTION
    STATUS        current
    DESCRIPTION
        ""
    SYNTAX        INTEGER
    {
        nonRecursive(0),
        recursive(1)
    }

CfprApAaaLdapVendor ::= TEXTUAL-CONVENTION
    STATUS        current
    DESCRIPTION
        ""
    SYNTAX        INTEGER
    {
        openLdap(0),
        msAd(1)
    }

CfprApAaaNoRolePolicy ::= TEXTUAL-CONVENTION
    STATUS        current
    DESCRIPTION
        ""
    SYNTAX        INTEGER
    {
        noLogin(0),
        assignDefaultRole(1)
    }

CfprApAaaPwdPolicy ::= TEXTUAL-CONVENTION
    STATUS        current
    DESCRIPTION
        ""
    SYNTAX        INTEGER
    {
        enable(0),
        disable(1)
    }

CfprApAaaRadiusEpFsmCurrentFsm ::= TEXTUAL-CONVENTION
    STATUS        current
    DESCRIPTION
        ""
    SYNTAX        INTEGER
    {
        nop(0),
        updateEp(349)
    }

CfprApAaaRadiusEpFsmStageName ::= TEXTUAL-CONVENTION
    STATUS        current
    DESCRIPTION
        ""
    SYNTAX        INTEGER
    {
        nop(0),
        updateEpBegin(349),
        updateEpSetEpLocal(350),
        updateEpSetEpPeer(351),
        updateEpFail(536),
        updateEpSuccess(537)
    }

CfprApAaaRadiusService ::= TEXTUAL-CONVENTION
    STATUS        current
    DESCRIPTION
        ""
    SYNTAX        INTEGER
    {
        all(0),
        authorization(1),
        accounting(2)
    }

CfprApAaaRealm ::= TEXTUAL-CONVENTION
    STATUS        current
    DESCRIPTION
        ""
    SYNTAX        INTEGER
    {
        local(0),
        radius(1),
        tacacs(2),
        ldap(3),
        none(4)
    }

CfprApAaaRealmFsmCurrentFsm ::= TEXTUAL-CONVENTION
    STATUS        current
    DESCRIPTION
        ""
    SYNTAX        INTEGER
    {
        nop(0),
        updateRealm(352)
    }

CfprApAaaRealmFsmStageName ::= TEXTUAL-CONVENTION
    STATUS        current
    DESCRIPTION
        ""
    SYNTAX        INTEGER
    {
        nop(0),
        updateRealmBegin(352),
        updateRealmSetRealmLocal(353),
        updateRealmSetRealmPeer(354),
        updateRealmFail(538),
        updateRealmSuccess(539)
    }

CfprApAaaRealmFsmTaskItem ::= TEXTUAL-CONVENTION
    STATUS        current
    DESCRIPTION
        ""
    SYNTAX        INTEGER
    {
        nop(0),
        updateRealm(352)
    }

CfprApAaaSession ::= TEXTUAL-CONVENTION
    STATUS        current
    DESCRIPTION
        ""
    SYNTAX        INTEGER
    {
        local(0),
        remote(1),
        ipmi(2)
    }

CfprApAaaSessionState ::= TEXTUAL-CONVENTION
    STATUS        current
    DESCRIPTION
        ""
    SYNTAX        INTEGER
    {
        active(0),
        inactive(1)
    }

CfprApAaaSshStr ::= TEXTUAL-CONVENTION
    STATUS        current
    DESCRIPTION
        ""
    SYNTAX        INTEGER
    {
        none(0),
        key(1)
    }

CfprApAaaTacacsPlusEpFsmCurrentFsm ::= TEXTUAL-CONVENTION
    STATUS        current
    DESCRIPTION
        ""
    SYNTAX        INTEGER
    {
        nop(0),
        updateEp(349)
    }

CfprApAaaTacacsPlusEpFsmStageName ::= TEXTUAL-CONVENTION
    STATUS        current
    DESCRIPTION
        ""
    SYNTAX        INTEGER
    {
        nop(0),
        updateEpBegin(349),
        updateEpSetEpLocal(350),
        updateEpSetEpPeer(351),
        updateEpFail(536),
        updateEpSuccess(537)
    }

CfprApAaaUserEpFsmCurrentFsm ::= TEXTUAL-CONVENTION
    STATUS        current
    DESCRIPTION
        ""
    SYNTAX        INTEGER
    {
        nop(0),
        updateUserEp(355)
    }

CfprApAaaUserEpFsmStageName ::= TEXTUAL-CONVENTION
    STATUS        current
    DESCRIPTION
        ""
    SYNTAX        INTEGER
    {
        nop(0),
        updateUserEpBegin(355),
        updateUserEpSetUserLocal(356),
        updateUserEpSetUserPeer(357),
        updateUserEpFail(540),
        updateUserEpSuccess(541)
    }

CfprApAaaUserEpFsmTaskItem ::= TEXTUAL-CONVENTION
    STATUS        current
    DESCRIPTION
        ""
    SYNTAX        INTEGER
    {
        nop(0),
        updateUserEp(355)
    }

CfprApAaaUserInterface ::= TEXTUAL-CONVENTION
    STATUS        current
    DESCRIPTION
        ""
    SYNTAX        INTEGER
    {
        none(0),
        shell(1),
        web(2),
        ep(3),
        kvm(4),
        vmedia(5),
        sol(6)
    }

CfprApAdaptorAdapterStatsTrafficDir ::= TEXTUAL-CONVENTION
    STATUS        current
    DESCRIPTION
        ""
    SYNTAX        INTEGER
    {
        unknown(0),
        tx(1),
        rx(2)
    }

CfprApAdaptorAdminPowerState ::= TEXTUAL-CONVENTION
    STATUS        current
    DESCRIPTION
        ""
    SYNTAX        INTEGER
    {
        none(0),
        resetPower(1)
    }

CfprApAdaptorCIoEpIfType ::= TEXTUAL-CONVENTION
    STATUS        current
    DESCRIPTION
        ""
    SYNTAX        INTEGER
    {
        unknown(0),
        physical(1),
        aggregation(2),
        virtual(3),
        fabric(4)
    }

CfprApAdaptorCapDefFwVersionOpr ::= TEXTUAL-CONVENTION
    STATUS        current
    DESCRIPTION
        ""
    SYNTAX        INTEGER
    {
        none(0),
        gt(1),
        lt(2),
        range(3)
    }

CfprApAdaptorCapDefType ::= TEXTUAL-CONVENTION
    STATUS        current
    DESCRIPTION
        ""
    SYNTAX        INTEGER
    {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11),
        uplinkAggregation(12),
        virtualizedEthSriov(13),
        virtualizedFcSriov(14),
        virtualizedEthSriovUsnic(15),
        virtualizedEthVmq(16),
        ethFlowMonitoringNetflow(17),
        ethRoce(18),
        ethVxlan(19),
        ethNvgre(20)
    }

CfprApAdaptorCapSpecType ::= TEXTUAL-CONVENTION
    STATUS        current
    DESCRIPTION
        ""
    SYNTAX        INTEGER
    {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11),
        uplinkAggregation(12),
        virtualizedEthSriov(13),
        virtualizedFcSriov(14),
        virtualizedEthSriovUsnic(15),
        virtualizedEthVmq(16),
        ethFlowMonitoringNetflow(17),
        ethRoce(18),
        ethVxlan(19),
        ethNvgre(20)
    }

CfprApAdaptorDefaultAction ::= TEXTUAL-CONVENTION
    STATUS        current
    DESCRIPTION
        ""
    SYNTAX        INTEGER
    {
        no(0),
        yes(1)
    }

CfprApAdaptorEthArfsProfileAccelaratedRFS ::= TEXTUAL-CONVENTION
    STATUS        current
    DESCRIPTION
        ""
    SYNTAX        INTEGER
    {
        disabled(0),
        enabled(1)
    }

CfprApAdaptorEthInterruptProfileCoalescingType ::= TEXTUAL-CONVENTION
    STATUS        current
    DESCRIPTION
        ""
    SYNTAX        INTEGER
    {
        min(0),
        idle(1)
    }

CfprApAdaptorEthNVGREProfileAdminState ::= TEXTUAL-CONVENTION
    STATUS        current
    DESCRIPTION
        ""
    SYNTAX        INTEGER
    {
        disabled(0),
        enabled(1)
    }

CfprApAdaptorEthOffloadProfileLargeReceive ::= TEXTUAL-CONVENTION
    STATUS        current
    DESCRIPTION
        ""
    SYNTAX        INTEGER
    {
        disabled(0),
        enabled(1)
    }

CfprApAdaptorEthOffloadProfileTcpRxChecksum ::= TEXTUAL-CONVENTION
    STATUS        current
    DESCRIPTION
        ""
    SYNTAX        INTEGER
    {
        disabled(0),
        enabled(1)
    }

CfprApAdaptorEthOffloadProfileTcpSegment ::= TEXTUAL-CONVENTION
    STATUS        current
    DESCRIPTION
        ""
    SYNTAX        INTEGER
    {
        disabled(0),
        enabled(1)
    }

CfprApAdaptorEthOffloadProfileTcpTxChecksum ::= TEXTUAL-CONVENTION
    STATUS        current
    DESCRIPTION
        ""
    SYNTAX        INTEGER
    {
        disabled(0),
        enabled(1)
    }

CfprApAdaptorEthPortBySizeLargeStatsThresholded ::= TEXTUAL-CONVENTION
    STATUS        current
    DESCRIPTION
        ""
    SYNTAX        BITS
    {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CfprApAdaptorEthPortBySizeLargeStatsHistThresholded ::= TEXTUAL-CONVENTION
    STATUS        current
    DESCRIPTION
        ""
    SYNTAX        BITS
    {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CfprApAdaptorEthPortBySizeSmallStatsThresholded ::= TEXTUAL-CONVENTION
    STATUS        current
    DESCRIPTION
        ""
    SYNTAX        BITS
    {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CfprApAdaptorEthPortBySizeSmallStatsHistThresholded ::= TEXTUAL-CONVENTION
    STATUS        current
    DESCRIPTION
        ""
    SYNTAX        BITS
    {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CfprApAdaptorEthPortErrStatsThresholded ::= TEXTUAL-CONVENTION
    STATUS        current
    DESCRIPTION
        ""
    SYNTAX        BITS
    {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11)
    }

CfprApAdaptorEthPortErrStatsHistThresholded ::= TEXTUAL-CONVENTION
    STATUS        current
    DESCRIPTION
        ""
    SYNTAX        BITS
    {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11)
    }

CfprApAdaptorEthPortMcastStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CfprApAdaptorEthPortMcastStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CfprApAdaptorEthPortOutsizedStatsThresholded ::= TEXTUAL-CONVENTION
    STATUS        current
    DESCRIPTION
        ""
    SYNTAX        BITS
    {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CfprApAdaptorEthPortOutsizedStatsHistThresholded ::= TEXTUAL-CONVENTION
    STATUS        current
    DESCRIPTION
        ""
    SYNTAX        BITS
    {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CfprApAdaptorEthPortStatsThresholded ::= TEXTUAL-CONVENTION
    STATUS        current
    DESCRIPTION
        ""
    SYNTAX        BITS
    {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CfprApAdaptorEthPortStatsHistThresholded ::= TEXTUAL-CONVENTION
    STATUS        current
    DESCRIPTION
        ""
    SYNTAX        BITS
    {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CfprApAdaptorEthRoCEProfileAdminState ::= TEXTUAL-CONVENTION
    STATUS        current
    DESCRIPTION
        ""
    SYNTAX        INTEGER
    {
        disabled(0),
        enabled(1)
    }

CfprApAdaptorEthVxLANProfileAdminState ::= TEXTUAL-CONVENTION
    STATUS        current
    DESCRIPTION
        ""
    SYNTAX        INTEGER
    {
        disabled(0),
        enabled(1)
    }

CfprApAdaptorEtherIfStatsThresholded ::= TEXTUAL-CONVENTION
    STATUS        current
    DESCRIPTION
        ""
    SYNTAX        BITS
    {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CfprApAdaptorEtherIfStatsHistThresholded ::= TEXTUAL-CONVENTION
    STATUS        current
    DESCRIPTION
        ""
    SYNTAX        BITS
    {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CfprApAdaptorExtEthIfFsmCurrentFsm ::= TEXTUAL-CONVENTION
    STATUS        current
    DESCRIPTION
        ""
    SYNTAX        INTEGER
    {
        nop(0),
        pathReset(127)
    }

CfprApAdaptorExtEthIfFsmStageName ::= TEXTUAL-CONVENTION
    STATUS        current
    DESCRIPTION
        ""
    SYNTAX        INTEGER
    {
        nop(0),
        pathResetBegin(127),
        pathResetDisable(128),
        pathResetEnable(129),
        pathResetFail(542),
        pathResetSuccess(543)
    }

CfprApAdaptorExtEthIfFsmTaskItem ::= TEXTUAL-CONVENTION
    STATUS        current
    DESCRIPTION
        ""
    SYNTAX        INTEGER
    {
        nop(0),
        pathReset(127)
    }

CfprApAdaptorExtEthIfPcPortId ::= TEXTUAL-CONVENTION
    STATUS        current
    DESCRIPTION
        ""
    SYNTAX        Gauge32 (1024..4096)

CfprApAdaptorExtEthIfPcTransport ::= TEXTUAL-CONVENTION
    STATUS        current
    DESCRIPTION
        ""
    SYNTAX        BITS
    {
        ether(0),
        dce(1),
        fc(2)
    }

CfprApAdaptorExtEthIfPcEpPortId ::= TEXTUAL-CONVENTION
    STATUS        current
    DESCRIPTION
        ""
    SYNTAX        Gauge32 (1..8)

CfprApAdaptorExtEthIfPcEpSlotId ::= TEXTUAL-CONVENTION
    STATUS        current
    DESCRIPTION
        ""
    SYNTAX        Gauge32 (1..8)

CfprApAdaptorExtIfAdminState ::= TEXTUAL-CONVENTION
    STATUS        current
    DESCRIPTION
        ""
    SYNTAX        INTEGER
    {
        enabled(0),
        resetConnectivity(44)
    }

CfprApAdaptorExtIfEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApAdaptorExtIfEpType ::= TEXTUAL-CONVENTION
    STATUS        current
    DESCRIPTION
        ""
    SYNTAX        BITS
    {
        lan(0),
        san(1),
        ipc(2)
    }

CfprApAdaptorExtIfPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApAdaptorExtIfPcType ::= TEXTUAL-CONVENTION
    STATUS        current
    DESCRIPTION
        ""
    SYNTAX        BITS
    {
        lan(0),
        san(1),
        ipc(2)
    }

CfprApAdaptorExtIpV6RssHashProfileIpHash ::= TEXTUAL-CONVENTION
    STATUS        current
    DESCRIPTION
        ""
    SYNTAX        INTEGER
    {
        disabled(0),
        enabled(1)
    }

CfprApAdaptorExtIpV6RssHashProfileTcpHash ::= TEXTUAL-CONVENTION
    STATUS        current
    DESCRIPTION
        ""
    SYNTAX        INTEGER
    {
        disabled(0),
        enabled(1)
    }

CfprApAdaptorExternalEpLocale ::= TEXTUAL-CONVENTION
    STATUS        current
    DESCRIPTION
        ""
    SYNTAX        BITS
    {
        server(0),
        chassis(1),
        internal(2),
        external(3)
    }

CfprApAdaptorExternalPcLocale ::= TEXTUAL-CONVENTION
    STATUS        current
    DESCRIPTION
        ""
    SYNTAX        BITS
    {
        server(0),
        chassis(1),
        internal(2),
        external(3)
    }

CfprApAdaptorFcErrorRecoveryProfileFcpErrorRecovery ::= TEXTUAL-CONVENTION
    STATUS        current
    DESCRIPTION
        ""
    SYNTAX        INTEGER
    {
        disabled(0),
        enabled(1)
    }

CfprApAdaptorFcIfEventStatsThresholded ::= TEXTUAL-CONVENTION
    STATUS        current
    DESCRIPTION
        ""
    SYNTAX        BITS
    {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CfprApAdaptorFcIfEventStatsHistThresholded ::= TEXTUAL-CONVENTION
    STATUS        current
    DESCRIPTION
        ""
    SYNTAX        BITS
    {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CfprApAdaptorFcIfFC4StatsThresholded ::= TEXTUAL-CONVENTION
    STATUS        current
    DESCRIPTION
        ""
    SYNTAX        BITS
    {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CfprApAdaptorFcIfFC4StatsHistThresholded ::= TEXTUAL-CONVENTION
    STATUS        current
    DESCRIPTION
        ""
    SYNTAX        BITS
    {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CfprApAdaptorFcIfFrameStatsThresholded ::= TEXTUAL-CONVENTION
    STATUS        current
    DESCRIPTION
        ""
    SYNTAX        BITS
    {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CfprApAdaptorFcIfFrameStatsHistThresholded ::= TEXTUAL-CONVENTION
    STATUS        current
    DESCRIPTION
        ""
    SYNTAX        BITS
    {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CfprApAdaptorFcPortStatsThresholded ::= TEXTUAL-CONVENTION
    STATUS        current
    DESCRIPTION
        ""
    SYNTAX        BITS
    {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CfprApAdaptorFcPortStatsHistThresholded ::= TEXTUAL-CONVENTION
    STATUS        current
    DESCRIPTION
        ""
    SYNTAX        BITS
    {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CfprApAdaptorHostEthIfHostPort ::= TEXTUAL-CONVENTION
    STATUS        current
    DESCRIPTION
        ""
    SYNTAX        INTEGER
    {
        any(0),
        n1(1),
        n2(2),
        none(10)
    }

CfprApAdaptorHostEthIfFsmCurrentFsm ::= TEXTUAL-CONVENTION
    STATUS        current
    DESCRIPTION
        ""
    SYNTAX        INTEGER
    {
        nop(0),
        circuitReset(130)
    }

CfprApAdaptorHostEthIfFsmStageName ::= TEXTUAL-CONVENTION
    STATUS        current
    DESCRIPTION
        ""
    SYNTAX        INTEGER
    {
        nop(0),
        circuitResetBegin(130),
        circuitResetDisableA(131),
        circuitResetEnableA(132),
        circuitResetDisableB(133),
        circuitResetEnableB(134),
        circuitResetFail(544),
        circuitResetSuccess(545)
    }

CfprApAdaptorHostEthIfFsmTaskItem ::= TEXTUAL-CONVENTION
    STATUS        current
    DESCRIPTION
        ""
    SYNTAX        INTEGER
    {
        nop(0),
        circuitReset(130)
    }

CfprApAdaptorHostFcIfAdminState ::= TEXTUAL-CONVENTION
    STATUS        current
    DESCRIPTION
        ""
    SYNTAX        INTEGER
    {
        enabled(0),
        resetConnectivityActive(44),
        resetConnectivityPassive(45),
        resetConnectivity(46),
        disabled(47),
        disabledPassive(48),
        disabledActive(49),
        enabledPassive(50),
        enabledActive(51)
    }

CfprApAdaptorHostFcIfHostPort ::= TEXTUAL-CONVENTION
    STATUS        current
    DESCRIPTION
        ""
    SYNTAX        INTEGER
    {
        any(0),
        n1(1),
        n2(2),
        none(10)
    }

CfprApAdaptorHostFcIfPersBind ::= TEXTUAL-CONVENTION
    STATUS        current
    DESCRIPTION
        ""
    SYNTAX        INTEGER
    {
        disabled(0),
        enabled(4)
    }

CfprApAdaptorHostFcIfFsmCurrentFsm ::= TEXTUAL-CONVENTION
    STATUS        current
    DESCRIPTION
        ""
    SYNTAX        INTEGER
    {
        nop(0),
        circuitReset(135)
    }

CfprApAdaptorHostFcIfFsmStageName ::= TEXTUAL-CONVENTION
    STATUS        current
    DESCRIPTION
        ""
    SYNTAX        INTEGER
    {
        nop(0),
        circuitResetBegin(135),
        circuitResetDisableA(136),
        circuitResetEnableA(137),
        circuitResetDisableB(138),
        circuitResetEnableB(139),
        circuitResetFail(546),
        circuitResetSuccess(547)
    }

CfprApAdaptorHostFcIfFsmTaskItem ::= TEXTUAL-CONVENTION
    STATUS        current
    DESCRIPTION
        ""
    SYNTAX        INTEGER
    {
        nop(0),
        circuitReset(135)
    }

CfprApAdaptorHostIfAdminState ::= TEXTUAL-CONVENTION
    STATUS        current
    DESCRIPTION
        ""
    SYNTAX        INTEGER
    {
        enabled(0),
        resetConnectivityActive(44),
        resetConnectivityPassive(45),
        resetConnectivity(46),
        disabled(47),
        disabledPassive(48),
        disabledActive(49),
        enabledPassive(50),
        enabledActive(51)
    }

CfprApAdaptorHostIfBootDev ::= TEXTUAL-CONVENTION
    STATUS        current
    DESCRIPTION
        ""
    SYNTAX        INTEGER
    {
        disabled(0),
        enabled(1)
    }

CfprApAdaptorHostMgmtCapPreboot ::= TEXTUAL-CONVENTION
    STATUS        current
    DESCRIPTION
        ""
    SYNTAX        INTEGER
    {
        none(0),
        pnuOS(1),
        efi(2)
    }

CfprApAdaptorHostMgmtCapPresence ::= TEXTUAL-CONVENTION
    STATUS        current
    DESCRIPTION
        ""
    SYNTAX        INTEGER
    {
        unspecified(0),
        host(1),
        cimc(2)
    }

CfprApAdaptorHostPortId ::= TEXTUAL-CONVENTION
    STATUS        current
    DESCRIPTION
        ""
    SYNTAX        Gauge32 (1..5000)

CfprApAdaptorHostServiceEthIfIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApAdaptorHostVisibility ::= TEXTUAL-CONVENTION
    STATUS        current
    DESCRIPTION
        ""
    SYNTAX        INTEGER
    {
        no(0),
        yes(1),
        osDependent(2)
    }

CfprApAdaptorIScsiCapBootOrderType ::= TEXTUAL-CONVENTION
    STATUS        current
    DESCRIPTION
        ""
    SYNTAX        INTEGER
    {
        systemBootOrder(0),
        fddOrder(1),
        hddOrder(2),
        cdOrder(3),
        networkDeviceOrder(6),
        internalEfiShell(16),
        unknownDeviceOrder(99),
        localStorageAnyDeviceOrder(100),
        sanDeviceOrder(101),
        sanAnyDeviceOrder(102),
        internalUsbDeviceOrder(103),
        externalUsbDeviceOrder(104),
        sdcardDeviceOrder(105),
        lanAnyDeviceOrder(106),
        uefiTargetDeviceOrder(107),
        iscsiDeviceOrder(108),
        iscsiAnyDeviceOrder(109),
        cimcVmediaCddDeviceOrder(110),
        cimcVmediaHddDeviceOrder(111),
        cimcVmediaFddDeviceOrder(112),
        kvmVmediaCddDeviceOrder(113),
        kvmVmediaHddDeviceOrder(114),
        kvmVmediaFddDeviceOrder(115),
        bevOrder(128)
    }

CfprApAdaptorInterruptMode ::= TEXTUAL-CONVENTION
    STATUS        current
    DESCRIPTION
        ""
    SYNTAX        INTEGER
    {
        msiX(1),
        msi(2),
        intx(3)
    }

CfprApAdaptorIpV4RssHashProfileIpHash ::= TEXTUAL-CONVENTION
    STATUS        current
    DESCRIPTION
        ""
    SYNTAX        INTEGER
    {
        disabled(0),
        enabled(1)
    }

CfprApAdaptorIpV4RssHashProfileTcpHash ::= TEXTUAL-CONVENTION
    STATUS        current
    DESCRIPTION
        ""
    SYNTAX        INTEGER
    {
        disabled(0),
        enabled(1)
    }

CfprApAdaptorIpV6RssHashProfileIpHash ::= TEXTUAL-CONVENTION
    STATUS        current
    DESCRIPTION
        ""
    SYNTAX        INTEGER
    {
        disabled(0),
        enabled(1)
    }

CfprApAdaptorIpV6RssHashProfileTcpHash ::= TEXTUAL-CONVENTION
    STATUS        current
    DESCRIPTION
        ""
    SYNTAX        INTEGER
    {
        disabled(0),
        enabled(1)
    }

CfprApAdaptorIscsiProtConnectionTimeOut ::= TEXTUAL-CONVENTION
    STATUS        current
    DESCRIPTION
        ""
    SYNTAX        Gauge32 (0..255)

CfprApAdaptorIscsiProtDhcpTimeOut ::= TEXTUAL-CONVENTION
    STATUS        current
    DESCRIPTION
        ""
    SYNTAX        Gauge32 (60..300)

CfprApAdaptorIscsiProtLunBusyRetryCount ::= TEXTUAL-CONVENTION
    STATUS        current
    DESCRIPTION
        ""
    SYNTAX        Gauge32 (0..60)

CfprApAdaptorLanCapDefaultVlan ::= TEXTUAL-CONVENTION
    STATUS        current
    DESCRIPTION
        ""
    SYNTAX        INTEGER
    {
        nativeVlan(1),
        defaultVlan(2)
    }

CfprApAdaptorLinkState ::= TEXTUAL-CONVENTION
    STATUS        current
    DESCRIPTION
        ""
    SYNTAX        INTEGER
    {
        unknown(0),
        adminDown(1),
        down(2),
        error(3),
        up(4),
        unallocated(5),
        unavailable(6)
    }

CfprApAdaptorLldpCapSupport ::= TEXTUAL-CONVENTION
    STATUS        current
    DESCRIPTION
        ""
    SYNTAX        INTEGER
    {
        none(1),
        full(2)
    }

CfprApAdaptorMenloBaseErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CfprApAdaptorMenloBaseErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CfprApAdaptorMenloDcePortStatsThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprApAdaptorMenloDcePortStatsHistThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprApAdaptorMenloEthErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CfprApAdaptorMenloEthErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CfprApAdaptorMenloEthStatsThresholded ::= TEXTUAL-CONVENTION
    STATUS        current
    DESCRIPTION
        ""
    SYNTAX        BITS
    {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CfprApAdaptorMenloEthStatsHistThresholded ::= TEXTUAL-CONVENTION
    STATUS        current
    DESCRIPTION
        ""
    SYNTAX        BITS
    {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CfprApAdaptorMenloFcErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprApAdaptorMenloFcErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprApAdaptorMenloFcStatsThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprApAdaptorMenloFcStatsHistThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprApAdaptorMenloHostPortStatsThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprApAdaptorMenloHostPortStatsHistThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprApAdaptorMenloMcpuErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprApAdaptorMenloMcpuErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprApAdaptorMenloMcpuStatsThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprApAdaptorMenloMcpuStatsHistThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprApAdaptorMenloNetEgStatsThresholded ::= TEXTUAL-CONVENTION
    STATUS        current
    DESCRIPTION
        ""
    SYNTAX        BITS
    {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CfprApAdaptorMenloNetEgStatsHistThresholded ::= TEXTUAL-CONVENTION
    STATUS        current
    DESCRIPTION
        ""
    SYNTAX        BITS
    {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CfprApAdaptorMenloNetInStatsThresholded ::= TEXTUAL-CONVENTION
    STATUS        current
    DESCRIPTION
        ""
    SYNTAX        BITS
    {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CfprApAdaptorMenloNetInStatsHistThresholded ::= TEXTUAL-CONVENTION
    STATUS        current
    DESCRIPTION
        ""
    SYNTAX        BITS
    {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CfprApAdaptorMenloQErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprApAdaptorMenloQErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprApAdaptorMenloQStatsThresholded ::= TEXTUAL-CONVENTION
    STATUS        current
    DESCRIPTION
        ""
    SYNTAX        BITS
    {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CfprApAdaptorMenloQStatsHistThresholded ::= TEXTUAL-CONVENTION
    STATUS        current
    DESCRIPTION
        ""
    SYNTAX        BITS
    {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CfprApAdaptorMenloQueueStatsComponent ::= TEXTUAL-CONVENTION
    STATUS        current
    DESCRIPTION
        ""
    SYNTAX        INTEGER
    {
        unknown(0),
        cpu(1),
        eth(2),
        fc(3),
        n(4)
    }

CfprApAdaptorMenloStatsIndex ::= TEXTUAL-CONVENTION
    STATUS        current
    DESCRIPTION
        ""
    SYNTAX        INTEGER
    {
        unknown(0),
        n0(1),
        n1(2),
        n0A(3),
        n0B(4),
        n1A(5),
        n1B(6)
    }

CfprApAdaptorMgmtCapMode ::= TEXTUAL-CONVENTION
    STATUS        current
    DESCRIPTION
        ""
    SYNTAX        INTEGER
    {
        full(1),
        partial(2)
    }

CfprApAdaptorMgmtCapOperPowerRequirement ::= TEXTUAL-CONVENTION
    STATUS        current
    DESCRIPTION
        ""
    SYNTAX        INTEGER
    {
        none(0),
        standby(1),
        full(2)
    }

CfprApAdaptorMgmtCapRebootActionOnDestructive ::= TEXTUAL-CONVENTION
    STATUS        current
    DESCRIPTION
        ""
    SYNTAX        INTEGER
    {
        none(0),
        host(1),
        adaptor(2)
    }

CfprApAdaptorNwMgmtCapApi ::= TEXTUAL-CONVENTION
    STATUS        current
    DESCRIPTION
        ""
    SYNTAX        INTEGER
    {
        none(0),
        menlo(1),
        palo(2)
    }

CfprApAdaptorNwMgmtCapMgmtTransport ::= TEXTUAL-CONVENTION
    STATUS        current
    DESCRIPTION
        ""
    SYNTAX        INTEGER
    {
        l2(0),
        l3(1)
    }

CfprApAdaptorOffloadMethod ::= TEXTUAL-CONVENTION
    STATUS        current
    DESCRIPTION
        ""
    SYNTAX        INTEGER
    {
        virtual(0),
        physical(1),
        none(2)
    }

CfprApAdaptorPIoEpIfType ::= TEXTUAL-CONVENTION
    STATUS        current
    DESCRIPTION
        ""
    SYNTAX        INTEGER
    {
        unknown(0),
        physical(1),
        aggregation(2),
        virtual(3),
        fabric(4)
    }

CfprApAdaptorProtocolProfileConnectionTimeOut ::= TEXTUAL-CONVENTION
    STATUS        current
    DESCRIPTION
        ""
    SYNTAX        Gauge32 (0..255)

CfprApAdaptorProtocolProfileLunBusyRetryCount ::= TEXTUAL-CONVENTION
    STATUS        current
    DESCRIPTION
        ""
    SYNTAX        Gauge32 (0..60)

CfprApAdaptorPurpose ::= TEXTUAL-CONVENTION
    STATUS        current
    DESCRIPTION
        ""
    SYNTAX        INTEGER
    {
        unused(0),
        general(1),
        management(2),
        utility(3)
    }

CfprApAdaptorReachability ::= TEXTUAL-CONVENTION
    STATUS        current
    DESCRIPTION
        ""
    SYNTAX        BITS
    {
        a(0),
        b(1),
        unmanaged(7)
    }

CfprApAdaptorRssProfileReceiveSideScaling ::= TEXTUAL-CONVENTION
    STATUS        current
    DESCRIPTION
        ""
    SYNTAX        INTEGER
    {
        disabled(0),
        enabled(1)
    }

CfprApAdaptorSanCapHostNvram ::= TEXTUAL-CONVENTION
    STATUS        current
    DESCRIPTION
        ""
    SYNTAX        INTEGER
    {
        none(1),
        full(2)
    }

CfprApAdaptorServiceState ::= TEXTUAL-CONVENTION
    STATUS        current
    DESCRIPTION
        ""
    SYNTAX        INTEGER
    {
        outOfService(0),
        inService(1)
    }

CfprApAdaptorUnitId ::= TEXTUAL-CONVENTION
    STATUS        current
    DESCRIPTION
        ""
    SYNTAX        Gauge32 (1..5000)

CfprApAdaptorUnitExtnId ::= TEXTUAL-CONVENTION
    STATUS        current
    DESCRIPTION
        ""
    SYNTAX        Gauge32 (1..5000)

CfprApAdaptorVnicStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprApAdaptorVnicStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprApAddressMACMask ::= TEXTUAL-CONVENTION
    STATUS        current
    DESCRIPTION
        ""
    SYNTAX        Counter64

CfprApAddressType ::= TEXTUAL-CONVENTION
    STATUS        current
    DESCRIPTION
        ""
    SYNTAX        INTEGER
    {
        unknown(0),
        operational(1),
        floating(2)
    }

CfprApAddressUIDSuffxMask ::= TEXTUAL-CONVENTION
    STATUS        current
    DESCRIPTION
        ""
    SYNTAX        Counter64

CfprApAddressWWNMask ::= TEXTUAL-CONVENTION
    STATUS        current
    DESCRIPTION
        ""
    SYNTAX        Counter64

CfprApApplicationDownloaderFsmCurrentFsm ::= TEXTUAL-CONVENTION
    STATUS        current
    DESCRIPTION
        ""
    SYNTAX        INTEGER
    {
        nop(0),
        download(332)
    }

CfprApApplicationDownloaderFsmStageName ::= TEXTUAL-CONVENTION
    STATUS        current
    DESCRIPTION
        ""
    SYNTAX        INTEGER
    {
        nop(0),
        downloadBegin(332),
        downloadLocal(333),
        downloadUnpackLocal(334),
        downloadFail(548),
        downloadSuccess(549)
    }

CfprApApplicationDownloaderFsmTaskItem ::= TEXTUAL-CONVENTION
    STATUS        current
    DESCRIPTION
        ""
    SYNTAX        INTEGER
    {
        nop(0),
        download(332)
    }

CfprApBiosBootDevErrorCode ::= TEXTUAL-CONVENTION
    STATUS        current
    DESCRIPTION
        ""
    SYNTAX        INTEGER
    {
        success(0),
        failure(1)
    }

CfprApBiosBootDevGrpType ::= TEXTUAL-CONVENTION
    STATUS        current
    DESCRIPTION
        ""
    SYNTAX        INTEGER
    {
        systemBootOrder(0),
        fddOrder(1),
        hddOrder(2),
        cdOrder(3),
        networkDeviceOrder(6),
        internalEfiShell(16),
        unknownDeviceOrder(99),
        localStorageAnyDeviceOrder(100),
        sanDeviceOrder(101),
        sanAnyDeviceOrder(102),
        internalUsbDeviceOrder(103),
        externalUsbDeviceOrder(104),
        sdcardDeviceOrder(105),
        lanAnyDeviceOrder(106),
        uefiTargetDeviceOrder(107),
        iscsiDeviceOrder(108),
        iscsiAnyDeviceOrder(109),
        cimcVmediaCddDeviceOrder(110),
        cimcVmediaHddDeviceOrder(111),
        cimcVmediaFddDeviceOrder(112),
        kvmVmediaCddDeviceOrder(113),
        kvmVmediaHddDeviceOrder(114),
        kvmVmediaFddDeviceOrder(115),
        bevOrder(128)
    }

CfprApBiosBootDevOrder ::= TEXTUAL-CONVENTION
    STATUS        current
    DESCRIPTION
        ""
    SYNTAX        INTEGER
    {
        n1(1),
        n2(2),
        n3(3),
        n4(4),
        n5(5),
        n6(6),
        n7(7)
    }

CfprApBiosDefaultAction ::= TEXTUAL-CONVENTION
    STATUS        current
    DESCRIPTION
        ""
    SYNTAX        INTEGER
    {
        no(0),
        yes(1)
    }

CfprApBiosSupportedAction ::= TEXTUAL-CONVENTION
    STATUS        current
    DESCRIPTION
        ""
    SYNTAX        INTEGER
    {
        no(0),
        yes(1)
    }

CfprApBiosVfACPI10SupportVpACPI10Support ::= TEXTUAL-CONVENTION
    STATUS        current
    DESCRIPTION
        ""
    SYNTAX        INTEGER
    {
        platformRecommended(0),
        disabled(159),
        enabled(160)
    }

CfprApBiosVfAllUSBDevicesVpAllUSBDevices ::= TEXTUAL-CONVENTION
    STATUS        current
    DESCRIPTION
        ""
    SYNTAX        INTEGER
    {
        platformRecommended(0),
        disabled(300),
        enabled(301)
    }

CfprApBiosVfAltitudeVpAltitude ::= TEXTUAL-CONVENTION
    STATUS        current
    DESCRIPTION
        ""
    SYNTAX        INTEGER
    {
        platformRecommended(0),
        auto(361),
        n300M(362),
        n900M(363),
        n1500M(364),
        n3000M(365)
    }

CfprApBiosVfAssertNMIOnPERRVpAssertNMIOnPERR ::= TEXTUAL-CONVENTION
    STATUS        current
    DESCRIPTION
        ""
    SYNTAX        INTEGER
    {
        platformRecommended(0),
        disabled(98),
        enabled(99)
    }

CfprApBiosVfAssertNMIOnSERRVpAssertNMIOnSERR ::= TEXTUAL-CONVENTION
    STATUS        current
    DESCRIPTION
        ""
    SYNTAX        INTEGER
    {
        platformRecommended(0),
        disabled(96),
        enabled(97)
    }

CfprApBiosVfBootOptionRetryVpBootOptionRetry ::= TEXTUAL-CONVENTION
    STATUS        current
    DESCRIPTION
        ""
    SYNTAX        INTEGER
    {
        platformRecommended(0),
        disabled(129),
        enabled(130)
    }

CfprApBiosVfCPUPerformanceVpCPUPerformance ::= TEXTUAL-CONVENTION
    STATUS        current
    DESCRIPTION
        ""
    SYNTAX        INTEGER
    {
        platformRecommended(0),
        enterprise(282),
        highThroughput(283),
        hpc(284)
    }

CfprApBiosVfConsoleRedirectionVpBaudRate ::= TEXTUAL-CONVENTION
    STATUS        current
    DESCRIPTION
        ""
    SYNTAX        INTEGER
    {
        platformRecommended(0),
        n9600(110),
        n19200(111),
        n38400(112),
        n57600(113),
        n115200(114)
    }

CfprApBiosVfConsoleRedirectionVpConsoleRedirection ::= TEXTUAL-CONVENTION
    STATUS        current
    DESCRIPTION
        ""
    SYNTAX        INTEGER
    {
        platformRecommended(0),
        disabled(103),
        enabled(104),
        serialPortA(105),
        serialPortB(106),
        com0(107)
    }

CfprApBiosVfConsoleRedirectionVpFlowControl ::= TEXTUAL-CONVENTION
    STATUS        current
    DESCRIPTION
        ""
    SYNTAX        INTEGER
    {
        platformRecommended(0),
        none(108),
        rtsCts(109)
    }

CfprApBiosVfConsoleRedirectionVpLegacyOSRedirection ::= TEXTUAL-CONVENTION
    STATUS        current
    DESCRIPTION
        ""
    SYNTAX        INTEGER
    {
        platformRecommended(0),
        disabled(119),
        enabled(120)
    }

CfprApBiosVfConsoleRedirectionVpPuttyKeyPad ::= TEXTUAL-CONVENTION
    STATUS        current
    DESCRIPTION
        ""
    SYNTAX        INTEGER
    {
        platformRecommended(0),
        vt100(121),
        linux(122),
        xtermr6(123),
        sco(124),
        escn(125),
        vt400(126)
    }

CfprApBiosVfConsoleRedirectionVpTerminalType ::= TEXTUAL-CONVENTION
    STATUS        current
    DESCRIPTION
        ""
    SYNTAX        INTEGER
    {
        platformRecommended(0),
        pcAnsi(115),
        vt100(116),
        vt100Plus(117),
        vtUtf8(118)
    }

CfprApBiosVfCoreMultiProcessingVpCoreMultiProcessing ::= TEXTUAL-CONVENTION
    STATUS        current
    DESCRIPTION
        ""
    SYNTAX        INTEGER
    {
        platformRecommended(0),
        all(29),
        n1(30),
        n2(31),
        n3(32),
        n4(33),
        n5(34),
        n6(35),
        n7(36),
        n8(37),
        n9(38),
        n10(39),
        n11(40),
        n12(41),
        n13(42),
        n14(43),
        n15(44),
        n16(45),
        n17(46),
        n18(47)
    }

CfprApBiosVfDRAMClockThrottlingVpDRAMClockThrottling ::= TEXTUAL-CONVENTION
    STATUS        current
    DESCRIPTION
        ""
    SYNTAX        INTEGER
    {
        platformRecommended(0),
        auto(346),
        balanced(347),
        performance(348),
        energyEfficient(349)
    }

CfprApBiosVfDirectCacheAccessVpDirectCacheAccess ::= TEXTUAL-CONVENTION
    STATUS        current
    DESCRIPTION
        ""
    SYNTAX        INTEGER
    {
        platformRecommended(0),
        disabled(62),
        enabled(63)
    }

CfprApBiosVfDramRefreshRateVpDramRefreshRate ::= TEXTUAL-CONVENTION
    STATUS        current
    DESCRIPTION
        ""
    SYNTAX        INTEGER
    {
        platformRecommended(0),
        n1x(17),
        n2x(18),
        n3x(19),
        n4x(20),
        auto(21)
    }

CfprApBiosVfEnhancedIntelSpeedStepTechVpEnhancedIntelSpeedStepTech ::= TEXTUAL-CONVENTION
    STATUS        current
    DESCRIPTION
        ""
    SYNTAX        INTEGER
    {
        platformRecommended(0),
        disabled(22),
        enabled(23)
    }

CfprApBiosVfExecuteDisableBitVpExecuteDisableBit ::= TEXTUAL-CONVENTION
    STATUS        current
    DESCRIPTION
        ""
    SYNTAX        INTEGER
    {
        platformRecommended(0),
        disabled(48),
        enabled(49)
    }

CfprApBiosVfFRB2TimerVpFRB2Timer ::= TEXTUAL-CONVENTION
    STATUS        current
    DESCRIPTION
        ""
    SYNTAX        INTEGER
    {
        platformRecommended(0),
        disabled(331),
        enabled(332)
    }

CfprApBiosVfFrequencyFloorOverrideVpFrequencyFloorOverride ::= TEXTUAL-CONVENTION
    STATUS        current
    DESCRIPTION
        ""
    SYNTAX        INTEGER
    {
        platformRecommended(0),
        disabled(341),
        enabled(342)
    }

CfprApBiosVfFrontPanelLockoutVpFrontPanelLockout ::= TEXTUAL-CONVENTION
    STATUS        current
    DESCRIPTION
        ""
    SYNTAX        INTEGER
    {
        platformRecommended(0),
        disabled(94),
        enabled(95)
    }

CfprApBiosVfIntelEntrySASRAIDModuleVpSASRAID ::= TEXTUAL-CONVENTION
    STATUS        current
    DESCRIPTION
        ""
    SYNTAX        INTEGER
    {
        platformRecommended(0),
        disabled(74),
        enabled(75)
    }

CfprApBiosVfIntelEntrySASRAIDModuleVpSASRAIDModule ::= TEXTUAL-CONVENTION
    STATUS        current
    DESCRIPTION
        ""
    SYNTAX        INTEGER
    {
        platformRecommended(0),
        itIrRaid(76),
        intelEsrtii(77)
    }

CfprApBiosVfIntelHyperThreadingTechVpIntelHyperThreadingTech ::= TEXTUAL-CONVENTION
    STATUS        current
    DESCRIPTION
        ""
    SYNTAX        INTEGER
    {
        platformRecommended(0),
        disabled(24),
        enabled(25)
    }

CfprApBiosVfIntelTurboBoostTechVpIntelTurboBoostTech ::= TEXTUAL-CONVENTION
    STATUS        current
    DESCRIPTION
        ""
    SYNTAX        INTEGER
    {
        platformRecommended(0),
        disabled(1),
        enabled(2)
    }

CfprApBiosVfIntelVTForDirectedIOVpIntelVTDATSSupport ::= TEXTUAL-CONVENTION
    STATUS        current
    DESCRIPTION
        ""
    SYNTAX        INTEGER
    {
        platformRecommended(0),
        disabled(58),
        enabled(59)
    }

CfprApBiosVfIntelVTForDirectedIOVpIntelVTDCoherencySupport ::= TEXTUAL-CONVENTION
    STATUS        current
    DESCRIPTION
        ""
    SYNTAX        INTEGER
    {
        platformRecommended(0),
        disabled(56),
        enabled(57)
    }

CfprApBiosVfIntelVTForDirectedIOVpIntelVTDInterruptRemapping ::= TEXTUAL-CONVENTION
    STATUS        current
    DESCRIPTION
        ""
    SYNTAX        INTEGER
    {
        platformRecommended(0),
        disabled(54),
        enabled(55)
    }

CfprApBiosVfIntelVTForDirectedIOVpIntelVTDPassThroughDMASupport ::= TEXTUAL-CONVENTION
    STATUS        current
    DESCRIPTION
        ""
    SYNTAX        INTEGER
    {
        platformRecommended(0),
        disabled(60),
        enabled(61)
    }

CfprApBiosVfIntelVTForDirectedIOVpIntelVTForDirectedIO ::= TEXTUAL-CONVENTION
    STATUS        current
    DESCRIPTION
        ""
    SYNTAX        INTEGER
    {
        platformRecommended(0),
        disabled(52),
        enabled(53)
    }

CfprApBiosVfIntelVirtualizationTechnologyVpIntelVirtTechnology ::= TEXTUAL-CONVENTION
    STATUS        current
    DESCRIPTION
        ""
    SYNTAX        INTEGER
    {
        platformRecommended(0),
        disabled(50),
        enabled(51)
    }

CfprApBiosVfInterleaveConfigurationVpChannelInterleaving ::= TEXTUAL-CONVENTION
    STATUS        current
    DESCRIPTION
        ""
    SYNTAX        INTEGER
    {
        platformRecommended(0),
        auto(7),
        n1Way(8),
        n2Way(9),
        n3Way(10),
        n4Way(11)
    }

CfprApBiosVfInterleaveConfigurationVpMemoryInterleaving ::= TEXTUAL-CONVENTION
    STATUS        current
    DESCRIPTION
        ""
    SYNTAX        INTEGER
    {
        platformRecommended(0),
        numa1WayNodeInterleave(3),
        n2WayNodeInterleave(4),
        n4WayNodeInterleave(5),
        n8WayInterleavingInterSocket(6)
    }

CfprApBiosVfInterleaveConfigurationVpRankInterleaving ::= TEXTUAL-CONVENTION
    STATUS        current
    DESCRIPTION
        ""
    SYNTAX        INTEGER
    {
        platformRecommended(0),
        auto(12),
        n1Way(13),
        n2Way(14),
        n4Way(15),
        n8Way(16)
    }

CfprApBiosVfLocalX2ApicVpLocalX2Apic ::= TEXTUAL-CONVENTION
    STATUS        current
    DESCRIPTION
        ""
    SYNTAX        INTEGER
    {
        platformRecommended(0),
        xapic(26),
        x2apic(27),
        auto(28)
    }

CfprApBiosVfLvDIMMSupportVpLvDDRMode ::= TEXTUAL-CONVENTION
    STATUS        current
    DESCRIPTION
        ""
    SYNTAX        INTEGER
    {
        platformRecommended(0),
        powerSavingMode(161),
        performanceMode(162),
        auto(163)
    }

CfprApBiosVfMaxVariableMTRRSettingVpProcessorMtrr ::= TEXTUAL-CONVENTION
    STATUS        current
    DESCRIPTION
        ""
    SYNTAX        INTEGER
    {
        platformRecommended(0),
        autoMax(285),
        n8(286)
    }

CfprApBiosVfMaximumMemoryBelow4GBVpMaximumMemoryBelow4GB ::= TEXTUAL-CONVENTION
    STATUS        current
    DESCRIPTION
        ""
    SYNTAX        INTEGER
    {
        platformRecommended(0),
        disabled(88),
        enabled(89)
    }

CfprApBiosVfMemoryMappedIOAbove4GBVpMemoryMappedIOAbove4GB ::= TEXTUAL-CONVENTION
    STATUS        current
    DESCRIPTION
        ""
    SYNTAX        INTEGER
    {
        platformRecommended(0),
        disabled(90),
        enabled(91)
    }

CfprApBiosVfMirroringModeVpMirroringMode ::= TEXTUAL-CONVENTION
    STATUS        current
    DESCRIPTION
        ""
    SYNTAX        INTEGER
    {
        platformRecommended(0),
        interSocket(70),
        intraSocket(71)
    }

CfprApBiosVfNUMAOptimizedVpNUMAOptimized ::= TEXTUAL-CONVENTION
    STATUS        current
    DESCRIPTION
        ""
    SYNTAX        INTEGER
    {
        platformRecommended(0),
        disabled(72),
        enabled(73)
    }

CfprApBiosVfOSBootWatchdogTimerVpOSBootWatchdogTimer ::= TEXTUAL-CONVENTION
    STATUS        current
    DESCRIPTION
        ""
    SYNTAX        INTEGER
    {
        platformRecommended(0),
        disabled(151),
        enabled(152)
    }

CfprApBiosVfOSBootWatchdogTimerPolicyVpOSBootWatchdogTimerPolicy ::= TEXTUAL-CONVENTION
    STATUS        current
    DESCRIPTION
        ""
    SYNTAX        INTEGER
    {
        platformRecommended(0),
        reset(153),
        powerOff(154)
    }

CfprApBiosVfOSBootWatchdogTimerTimeoutVpOSBootWatchdogTimerTimeout ::= TEXTUAL-CONVENTION
    STATUS        current
    DESCRIPTION
        ""
    SYNTAX        INTEGER
    {
        platformRecommended(0),
        n5Minutes(155),
        n10Minutes(156),
        n15Minutes(157),
        n20Minutes(158)
    }

CfprApBiosVfOnboardSATAControllerVpOnboardSATAController ::= TEXTUAL-CONVENTION
    STATUS        current
    DESCRIPTION
        ""
    SYNTAX        INTEGER
    {
        platformRecommended(0),
        disabled(78),
        enabled(79)
    }

CfprApBiosVfOnboardSATAControllerVpSATAMode ::= TEXTUAL-CONVENTION
    STATUS        current
    DESCRIPTION
        ""
    SYNTAX        INTEGER
    {
        platformRecommended(0),
        enhanced(80),
        ahci(81),
        swRaid(82),
        compatibility(83)
    }

CfprApBiosVfOnboardStorageVpOnboardSCUStorageSupport ::= TEXTUAL-CONVENTION
    STATUS        current
    DESCRIPTION
        ""
    SYNTAX        INTEGER
    {
        platformRecommended(0),
        disabled(84),
        enabled(85)
    }

CfprApBiosVfOptionROMEnableVpState ::= TEXTUAL-CONVENTION
    STATUS        current
    DESCRIPTION
        ""
    SYNTAX        INTEGER
    {
        platformRecommended(0),
        disabled(166),
        enabled(167),
        uefiOnly(168),
        legacyOnly(169)
    }

CfprApBiosVfOptionROMLoadVpLoad ::= TEXTUAL-CONVENTION
    STATUS        current
    DESCRIPTION
        ""
    SYNTAX        INTEGER
    {
        platformRecommended(0),
        enabled(164),
        disabled(165)
    }

CfprApBiosVfPCISlotLinkSpeedVpPCIeSlot10LinkSpeed ::= TEXTUAL-CONVENTION
    STATUS        current
    DESCRIPTION
        ""
    SYNTAX        INTEGER
    {
        platformRecommended(0),
        gen1(277),
        gen2(278),
        gen3(279),
        auto(280),
        disabled(281)
    }

CfprApBiosVfPCISlotLinkSpeedVpPCIeSlot1LinkSpeed ::= TEXTUAL-CONVENTION
    STATUS        current
    DESCRIPTION
        ""
    SYNTAX        INTEGER
    {
        platformRecommended(0),
        gen1(232),
        gen2(233),
        gen3(234),
        auto(235),
        disabled(236)
    }

CfprApBiosVfPCISlotLinkSpeedVpPCIeSlot2LinkSpeed ::= TEXTUAL-CONVENTION
    STATUS        current
    DESCRIPTION
        ""
    SYNTAX        INTEGER
    {
        platformRecommended(0),
        gen1(237),
        gen2(238),
        gen3(239),
        auto(240),
        disabled(241)
    }

CfprApBiosVfPCISlotLinkSpeedVpPCIeSlot3LinkSpeed ::= TEXTUAL-CONVENTION
    STATUS        current
    DESCRIPTION
        ""
    SYNTAX        INTEGER
    {
        platformRecommended(0),
        gen1(242),
        gen2(243),
        gen3(244),
        auto(245),
        disabled(246)
    }

CfprApBiosVfPCISlotLinkSpeedVpPCIeSlot4LinkSpeed ::= TEXTUAL-CONVENTION
    STATUS        current
    DESCRIPTION
        ""
    SYNTAX        INTEGER
    {
        platformRecommended(0),
        gen1(247),
        gen2(248),
        gen3(249),
        auto(250),
        disabled(251)
    }

CfprApBiosVfPCISlotLinkSpeedVpPCIeSlot5LinkSpeed ::= TEXTUAL-CONVENTION
    STATUS        current
    DESCRIPTION
        ""
    SYNTAX        INTEGER
    {
        platformRecommended(0),
        gen1(252),
        gen2(253),
        gen3(254),
        auto(255),
        disabled(256)
    }

CfprApBiosVfPCISlotLinkSpeedVpPCIeSlot6LinkSpeed ::= TEXTUAL-CONVENTION
    STATUS        current
    DESCRIPTION
        ""
    SYNTAX        INTEGER
    {
        platformRecommended(0),
        gen1(257),
        gen2(258),
        gen3(259),
        auto(260),
        disabled(261)
    }

CfprApBiosVfPCISlotLinkSpeedVpPCIeSlot7LinkSpeed ::= TEXTUAL-CONVENTION
    STATUS        current
    DESCRIPTION
        ""
    SYNTAX        INTEGER
    {
        platformRecommended(0),
        gen1(262),
        gen2(263),
        gen3(264),
        auto(265),
        disabled(266)
    }

CfprApBiosVfPCISlotLinkSpeedVpPCIeSlot8LinkSpeed ::= TEXTUAL-CONVENTION
    STATUS        current
    DESCRIPTION
        ""
    SYNTAX        INTEGER
    {
        platformRecommended(0),
        gen1(267),
        gen2(268),
        gen3(269),
        auto(270),
        disabled(271)
    }

CfprApBiosVfPCISlotLinkSpeedVpPCIeSlot9LinkSpeed ::= TEXTUAL-CONVENTION
    STATUS        current
    DESCRIPTION
        ""
    SYNTAX        INTEGER
    {
        platformRecommended(0),
        gen1(272),
        gen2(273),
        gen3(274),
        auto(275),
        disabled(276)
    }

CfprApBiosVfPCISlotOptionROMEnableVpPCIeSlotHBAOptionROM ::= TEXTUAL-CONVENTION
    STATUS        current
    DESCRIPTION
        ""
    SYNTAX        INTEGER
    {
        platformRecommended(0),
        disabled(220),
        enabled(221),
        uefiOnly(222),
        legacyOnly(223)
    }

CfprApBiosVfPCISlotOptionROMEnableVpPCIeSlotMLOMOptionROM ::= TEXTUAL-CONVENTION
    STATUS        current
    DESCRIPTION
        ""
    SYNTAX        INTEGER
    {
        platformRecommended(0),
        disabled(216),
        enabled(217),
        uefiOnly(218),
        legacyOnly(219)
    }

CfprApBiosVfPCISlotOptionROMEnableVpPCIeSlotN1OptionROM ::= TEXTUAL-CONVENTION
    STATUS        current
    DESCRIPTION
        ""
    SYNTAX        INTEGER
    {
        platformRecommended(0),
        disabled(224),
        enabled(225),
        uefiOnly(226),
        legacyOnly(227)
    }

CfprApBiosVfPCISlotOptionROMEnableVpPCIeSlotN2OptionROM ::= TEXTUAL-CONVENTION
    STATUS        current
    DESCRIPTION
        ""
    SYNTAX        INTEGER
    {
        platformRecommended(0),
        disabled(228),
        enabled(229),
        uefiOnly(230),
        legacyOnly(231)
    }

CfprApBiosVfPCISlotOptionROMEnableVpPCIeSlotSASOptionROM ::= TEXTUAL-CONVENTION
    STATUS        current
    DESCRIPTION
        ""
    SYNTAX        INTEGER
    {
        platformRecommended(0),
        disabled(170),
        enabled(171),
        uefiOnly(172),
        legacyOnly(173)
    }

CfprApBiosVfPCISlotOptionROMEnableVpSlot10State ::= TEXTUAL-CONVENTION
    STATUS        current
    DESCRIPTION
        ""
    SYNTAX        INTEGER
    {
        platformRecommended(0),
        disabled(210),
        enabled(211),
        uefiOnly(212),
        legacyOnly(213)
    }

CfprApBiosVfPCISlotOptionROMEnableVpSlot1State ::= TEXTUAL-CONVENTION
    STATUS        current
    DESCRIPTION
        ""
    SYNTAX        INTEGER
    {
        platformRecommended(0),
        disabled(174),
        enabled(175),
        uefiOnly(176),
        legacyOnly(177)
    }

CfprApBiosVfPCISlotOptionROMEnableVpSlot2State ::= TEXTUAL-CONVENTION
    STATUS        current
    DESCRIPTION
        ""
    SYNTAX        INTEGER
    {
        platformRecommended(0),
        disabled(178),
        enabled(179),
        uefiOnly(180),
        legacyOnly(181)
    }

CfprApBiosVfPCISlotOptionROMEnableVpSlot3State ::= TEXTUAL-CONVENTION
    STATUS        current
    DESCRIPTION
        ""
    SYNTAX        INTEGER
    {
        platformRecommended(0),
        disabled(182),
        enabled(183),
        uefiOnly(184),
        legacyOnly(185)
    }

CfprApBiosVfPCISlotOptionROMEnableVpSlot4State ::= TEXTUAL-CONVENTION
    STATUS        current
    DESCRIPTION
        ""
    SYNTAX        INTEGER
    {
        platformRecommended(0),
        disabled(186),
        enabled(187),
        uefiOnly(188),
        legacyOnly(189)
    }

CfprApBiosVfPCISlotOptionROMEnableVpSlot5State ::= TEXTUAL-CONVENTION
    STATUS        current
    DESCRIPTION
        ""
    SYNTAX        INTEGER
    {
        platformRecommended(0),
        disabled(190),
        enabled(191),
        uefiOnly(192),
        legacyOnly(193)
    }

CfprApBiosVfPCISlotOptionROMEnableVpSlot6State ::= TEXTUAL-CONVENTION
    STATUS        current
    DESCRIPTION
        ""
    SYNTAX        INTEGER
    {
        platformRecommended(0),
        disabled(194),
        enabled(195),
        uefiOnly(196),
        legacyOnly(197)
    }

CfprApBiosVfPCISlotOptionROMEnableVpSlot7State ::= TEXTUAL-CONVENTION
    STATUS        current
    DESCRIPTION
        ""
    SYNTAX        INTEGER
    {
        platformRecommended(0),
        disabled(198),
        enabled(199),
        uefiOnly(200),
        legacyOnly(201)
    }

CfprApBiosVfPCISlotOptionROMEnableVpSlot8State ::= TEXTUAL-CONVENTION
    STATUS        current
    DESCRIPTION
        ""
    SYNTAX        INTEGER
    {
        platformRecommended(0),
        disabled(202),
        enabled(203),
        uefiOnly(204),
        legacyOnly(205)
    }

CfprApBiosVfPCISlotOptionROMEnableVpSlot9State ::= TEXTUAL-CONVENTION
    STATUS        current
    DESCRIPTION
        ""
    SYNTAX        INTEGER
    {
        platformRecommended(0),
        disabled(206),
        enabled(207),
        uefiOnly(208),
        legacyOnly(209)
    }

CfprApBiosVfPCISlotOptionROMEnableVpSlotMezzState ::= TEXTUAL-CONVENTION
    STATUS        current
    DESCRIPTION
        ""
    SYNTAX        INTEGER
    {
        platformRecommended(0),
        disabled(214),
        enabled(215)
    }

CfprApBiosVfPOSTErrorPauseVpPOSTErrorPause ::= TEXTUAL-CONVENTION
    STATUS        current
    DESCRIPTION
        ""
    SYNTAX        INTEGER
    {
        platformRecommended(0),
        disabled(138),
        enabled(139)
    }

CfprApBiosVfPSTATECoordinationVpPSTATECoordination ::= TEXTUAL-CONVENTION
    STATUS        current
    DESCRIPTION
        ""
    SYNTAX        INTEGER
    {
        platformRecommended(0),
        hwAll(343),
        swAll(344),
        swAny(345)
    }

CfprApBiosVfPackageCStateLimitVpPackageCStateLimit ::= TEXTUAL-CONVENTION
    STATUS        current
    DESCRIPTION
        ""
    SYNTAX        INTEGER
    {
        platformRecommended(0),
        noLimit(295),
        c0(296),
        c1(297),
        c3(298),
        c6(299)
    }

CfprApBiosVfProcessorC1EVpProcessorC1E ::= TEXTUAL-CONVENTION
    STATUS        current
    DESCRIPTION
        ""
    SYNTAX        INTEGER
    {
        platformRecommended(0),
        disabled(149),
        enabled(150)
    }

CfprApBiosVfProcessorC3ReportVpProcessorC3Report ::= TEXTUAL-CONVENTION
    STATUS        current
    DESCRIPTION
        ""
    SYNTAX        INTEGER
    {
        platformRecommended(0),
        disabled(140),
        acpiC2(141),
        acpiC3(142)
    }

CfprApBiosVfProcessorC6ReportVpProcessorC6Report ::= TEXTUAL-CONVENTION
    STATUS        current
    DESCRIPTION
        ""
    SYNTAX        INTEGER
    {
        platformRecommended(0),
        disabled(143),
        enabled(144)
    }

CfprApBiosVfProcessorC7ReportVpProcessorC7Report ::= TEXTUAL-CONVENTION
    STATUS        current
    DESCRIPTION
        ""
    SYNTAX        INTEGER
    {
        platformRecommended(0),
        disabled(147),
        enabled(148)
    }

CfprApBiosVfProcessorCStateVpProcessorCState ::= TEXTUAL-CONVENTION
    STATUS        current
    DESCRIPTION
        ""
    SYNTAX        INTEGER
    {
        platformRecommended(0),
        disabled(145),
        enabled(146)
    }

CfprApBiosVfProcessorEnergyConfigurationVpEnergyPerformance ::= TEXTUAL-CONVENTION
    STATUS        current
    DESCRIPTION
        ""
    SYNTAX        INTEGER
    {
        platformRecommended(0),
        performance(337),
        balancedPerformance(338),
        balancedEnergy(339),
        energyEfficient(340)
    }

CfprApBiosVfProcessorEnergyConfigurationVpPowerTechnology ::= TEXTUAL-CONVENTION
    STATUS        current
    DESCRIPTION
        ""
    SYNTAX        INTEGER
    {
        platformRecommended(0),
        disabled(333),
        energyEfficient(334),
        performance(335),
        custom(336)
    }

CfprApBiosVfProcessorPrefetchConfigVpAdjacentCacheLinePrefetcher ::= TEXTUAL-CONVENTION
    STATUS        current
    DESCRIPTION
        ""
    SYNTAX        INTEGER
    {
        platformRecommended(0),
        disabled(318),
        enabled(319)
    }

CfprApBiosVfProcessorPrefetchConfigVpDCUIPPrefetcher ::= TEXTUAL-CONVENTION
    STATUS        current
    DESCRIPTION
        ""
    SYNTAX        INTEGER
    {
        platformRecommended(0),
        disabled(322),
        enabled(323)
    }

CfprApBiosVfProcessorPrefetchConfigVpDCUStreamerPrefetch ::= TEXTUAL-CONVENTION
    STATUS        current
    DESCRIPTION
        ""
    SYNTAX        INTEGER
    {
        platformRecommended(0),
        disabled(320),
        enabled(321)
    }

CfprApBiosVfProcessorPrefetchConfigVpHardwarePrefetcher ::= TEXTUAL-CONVENTION
    STATUS        current
    DESCRIPTION
        ""
    SYNTAX        INTEGER
    {
        platformRecommended(0),
        disabled(316),
        enabled(317)
    }

CfprApBiosVfQPILinkFrequencySelectVpQPILinkFrequencySelect ::= TEXTUAL-CONVENTION
    STATUS        current
    DESCRIPTION
        ""
    SYNTAX        INTEGER
    {
        platformRecommended(0),
        n6400(350),
        n7200(351),
        n8000(352),
        auto(353)
    }

CfprApBiosVfQuietBootVpQuietBoot ::= TEXTUAL-CONVENTION
    STATUS        current
    DESCRIPTION
        ""
    SYNTAX        INTEGER
    {
        platformRecommended(0),
        disabled(136),
        enabled(137)
    }

CfprApBiosVfResumeOnACPowerLossVpResumeOnACPowerLoss ::= TEXTUAL-CONVENTION
    STATUS        current
    DESCRIPTION
        ""
    SYNTAX        INTEGER
    {
        platformRecommended(0),
        stayOff(100),
        lastState(101),
        reset(102)
    }

CfprApBiosVfScrubPoliciesVpDemandScrub ::= TEXTUAL-CONVENTION
    STATUS        current
    DESCRIPTION
        ""
    SYNTAX        INTEGER
    {
        platformRecommended(0),
        disabled(326),
        enabled(327)
    }

CfprApBiosVfScrubPoliciesVpPatrolScrub ::= TEXTUAL-CONVENTION
    STATUS        current
    DESCRIPTION
        ""
    SYNTAX        INTEGER
    {
        platformRecommended(0),
        disabled(324),
        enabled(325)
    }

CfprApBiosVfSelectMemoryRASConfigurationVpSelectMemoryRASConf ::= TEXTUAL-CONVENTION
    STATUS        current
    DESCRIPTION
        ""
    SYNTAX        INTEGER
    {
        platformRecommended(0),
        maximumPerformance(64),
        mirroring(65),
        lockstep(66),
        sparing(67)
    }

CfprApBiosVfSerialPortAEnableVpSerialPortAEnable ::= TEXTUAL-CONVENTION
    STATUS        current
    DESCRIPTION
        ""
    SYNTAX        INTEGER
    {
        platformRecommended(0),
        disabled(86),
        enabled(87)
    }

CfprApBiosVfSparingModeVpSparingMode ::= TEXTUAL-CONVENTION
    STATUS        current
    DESCRIPTION
        ""
    SYNTAX        INTEGER
    {
        platformRecommended(0),
        dimmSparing(68),
        rankSparing(69)
    }

CfprApBiosVfSriovConfigVpSriov ::= TEXTUAL-CONVENTION
    STATUS        current
    DESCRIPTION
        ""
    SYNTAX        INTEGER
    {
        platformRecommended(0),
        disabled(92),
        enabled(93)
    }

CfprApBiosVfTPMSupportVpTPMSupport ::= TEXTUAL-CONVENTION
    STATUS        current
    DESCRIPTION
        ""
    SYNTAX        INTEGER
    {
        platformRecommended(0),
        disabled(354),
        enabled(355)
    }

CfprApBiosVfUCSMBootModeControlVpUEFIBootMode ::= TEXTUAL-CONVENTION
    STATUS        current
    DESCRIPTION
        ""
    SYNTAX        INTEGER
    {
        platformRecommended(0),
        disabled(293),
        enabled(294)
    }

CfprApBiosVfUCSMBootOrderRuleControlVpUCSMBootOrderRule ::= TEXTUAL-CONVENTION
    STATUS        current
    DESCRIPTION
        ""
    SYNTAX        INTEGER
    {
        platformRecommended(0),
        strict(291),
        loose(292)
    }

CfprApBiosVfUEFIOSUseLegacyVideoVpUEFIOSUseLegacyVideo ::= TEXTUAL-CONVENTION
    STATUS        current
    DESCRIPTION
        ""
    SYNTAX        INTEGER
    {
        platformRecommended(0),
        disabled(127),
        enabled(128)
    }

CfprApBiosVfUSBBootConfigVpLegacyUSBSupport ::= TEXTUAL-CONVENTION
    STATUS        current
    DESCRIPTION
        ""
    SYNTAX        INTEGER
    {
        platformRecommended(0),
        disabled(133),
        enabled(134),
        auto(135)
    }

CfprApBiosVfUSBBootConfigVpMakeDeviceNonBootable ::= TEXTUAL-CONVENTION
    STATUS        current
    DESCRIPTION
        ""
    SYNTAX        INTEGER
    {
        platformRecommended(0),
        disabled(131),
        enabled(132)
    }

CfprApBiosVfUSBConfigurationVpLegacyUSBSupport ::= TEXTUAL-CONVENTION
    STATUS        current
    DESCRIPTION
        ""
    SYNTAX        INTEGER
    {
        platformRecommended(0),
        disabled(358),
        enabled(359),
        auto(360)
    }

CfprApBiosVfUSBConfigurationVpXHCIMode ::= TEXTUAL-CONVENTION
    STATUS        current
    DESCRIPTION
        ""
    SYNTAX        INTEGER
    {
        platformRecommended(0),
        disabled(356),
        enabled(357)
    }

CfprApBiosVfUSBFrontPanelAccessLockVpUSBFrontPanelLock ::= TEXTUAL-CONVENTION
    STATUS        current
    DESCRIPTION
        ""
    SYNTAX        INTEGER
    {
        platformRecommended(0),
        disabled(289),
        enabled(290)
    }

CfprApBiosVfUSBPortConfigurationVpPort6064Emulation ::= TEXTUAL-CONVENTION
    STATUS        current
    DESCRIPTION
        ""
    SYNTAX        INTEGER
    {
        platformRecommended(0),
        disabled(302),
        enabled(303)
    }

CfprApBiosVfUSBPortConfigurationVpUSBPortFront ::= TEXTUAL-CONVENTION
    STATUS        current
    DESCRIPTION
        ""
    SYNTAX        INTEGER
    {
        platformRecommended(0),
        disabled(306),
        enabled(307)
    }

CfprApBiosVfUSBPortConfigurationVpUSBPortInternal ::= TEXTUAL-CONVENTION
    STATUS        current
    DESCRIPTION
        ""
    SYNTAX        INTEGER
    {
        platformRecommended(0),
        disabled(308),
        enabled(309)
    }

CfprApBiosVfUSBPortConfigurationVpUSBPortKVM ::= TEXTUAL-CONVENTION
    STATUS        current
    DESCRIPTION
        ""
    SYNTAX        INTEGER
    {
        platformRecommended(0),
        disabled(310),
        enabled(311)
    }

CfprApBiosVfUSBPortConfigurationVpUSBPortRear ::= TEXTUAL-CONVENTION
    STATUS        current
    DESCRIPTION
        ""
    SYNTAX        INTEGER
    {
        platformRecommended(0),
        disabled(304),
        enabled(305)
    }

CfprApBiosVfUSBPortConfigurationVpUSBPortSDCard ::= TEXTUAL-CONVENTION
    STATUS        current
    DESCRIPTION
        ""
    SYNTAX        INTEGER
    {
        platformRecommended(0),
        disabled(314),
        enabled(315)
    }

CfprApBiosVfUSBPortConfigurationVpUSBPortVMedia ::= TEXTUAL-CONVENTION
    STATUS        current
    DESCRIPTION
        ""
    SYNTAX        INTEGER
    {
        platformRecommended(0),
        disabled(312),
        enabled(313)
    }

CfprApBiosVfUSBSysIdlePowerOptimizingSettingVpUSBIdlePowerOptimize ::= TEXTUAL-CONVENTION
    STATUS        current
    DESCRIPTION
        ""
    SYNTAX        INTEGER
    {
        platformRecommended(0),
        highPerformance(287),
        lowerIdlePower(288)
    }

CfprApBiosVfVGAPriorityVpVGAPriority ::= TEXTUAL-CONVENTION
    STATUS        current
    DESCRIPTION
        ""
    SYNTAX        INTEGER
    {
        platformRecommended(0),
        onboard(328),
        offboard(329),
        onboardVgaDisabled(330)
    }

CfprApBmcSELCntEqptClassId ::= TEXTUAL-CONVENTION
    STATUS        current
    DESCRIPTION
        ""
    SYNTAX        INTEGER
    {
        unspecified(0),
        computeBoard(125),
        memoryUnit(250),
        processorUnit(352)
    }

CfprApBmcSELCntEqptInstIdPropId ::= TEXTUAL-CONVENTION
    STATUS        current
    DESCRIPTION
        ""
    SYNTAX        INTEGER
    {
        unspecified(0),
        memoryUnitId(673),
        processorUnitId(1006)
    }

CfprApBmcSELCntStatsClassId ::= TEXTUAL-CONVENTION
    STATUS        current
    DESCRIPTION
        ""
    SYNTAX        INTEGER
    {
        unspecified(0),
        computePCIeFatalProtocolStats(544),
        computePCIeFatalReceiveStats(545),
        computePCIeFatalCompletionStats(546),
        computePCIeFatalStats(547),
        memoryErrorStats(941),
        processorErrorStats(1511)
    }

CfprApCallhomeAdminState ::= TEXTUAL-CONVENTION
    STATUS        current
    DESCRIPTION
        ""
    SYNTAX        INTEGER
    {
        off(0),
        on(1)
    }

CfprApCallhomeAlertGroup ::= TEXTUAL-CONVENTION
    STATUS        current
    DESCRIPTION
        ""
    SYNTAX        INTEGER
    {
        diagnostic(0),
        environmental(1),
        unknown(100)
    }

CfprApCallhomeAlertGroups ::= TEXTUAL-CONVENTION
    STATUS        current
    DESCRIPTION
        ""
    SYNTAX        BITS
    {
        system(0),
        environmental(1),
        linecard(2),
        supervisor(3),
        inventory(4),
        test(5),
        ciscoTac(6),
        syslogPort(7),
        license(8),
        lifeCycle(9),
        diagnostic(10),
        smartLicense(11)
    }

CfprApCallhomeAlertLevel ::= TEXTUAL-CONVENTION
    STATUS        current
    DESCRIPTION
        ""
    SYNTAX        INTEGER
    {
        debug(0),
        normal(1),
        notify(2),
        warning(3),
        minor(4),
        major(5),
        critical(6),
        fatal(7),
        unknown(100)
    }

CfprApCallhomeAlertMessageSubtype ::= TEXTUAL-CONVENTION
    STATUS        current
    DESCRIPTION
        ""
    SYNTAX        INTEGER
    {
        nosubtype(0),
        test(1),
        full(2),
        delta(3),
        minor(4),
        major(5),
        goldnormal(6),
        goldminor(7),
        goldmajor(8),
        unknown(100)
    }

CfprApCallhomeAlertMessageType ::= TEXTUAL-CONVENTION
    STATUS        current
    DESCRIPTION
        ""
    SYNTAX        INTEGER
    {
        inventory(0),
        syslog(1),
        test(2),
        diag(3),
        env(4),
        conf(5),
        telemetry(6),
        unknown(100)
    }

CfprApCallhomeAlertThrottlingAdminState ::= TEXTUAL-CONVENTION
    STATUS        current
    DESCRIPTION
        ""
    SYNTAX        INTEGER
    {
        off(0),
        on(1)
    }

CfprApCallhomeAnonymousReportingAdminState ::= TEXTUAL-CONVENTION
    STATUS        current
    DESCRIPTION
        ""
    SYNTAX        INTEGER
    {
        off(0),
        on(1)
    }

CfprApCallhomeCallhomeProtocol ::= TEXTUAL-CONVENTION
    STATUS        current
    DESCRIPTION
        ""
    SYNTAX        INTEGER
    {
        email(0),
        https(1),
        http(2)
    }

CfprApCallhomeEpConfigState ::= TEXTUAL-CONVENTION
    STATUS        current
    DESCRIPTION
        ""
    SYNTAX        INTEGER
    {
        ok(0),
        notApplied(1)
    }

CfprApCallhomeEpFsmCurrentFsm ::= TEXTUAL-CONVENTION
    STATUS        current
    DESCRIPTION
        ""
    SYNTAX        INTEGER
    {
        nop(0),
        configCallhome(124)
    }

CfprApCallhomeEpFsmStageName ::= TEXTUAL-CONVENTION
    STATUS        current
    DESCRIPTION
        ""
    SYNTAX        INTEGER
    {
        nop(0),
        configCallhomeBegin(124),
        configCallhomeSetLocal(125),
        configCallhomeSetPeer(126),
        configCallhomeFail(550),
        configCallhomeSuccess(551)
    }

CfprApCallhomeEpFsmTaskItem ::= TEXTUAL-CONVENTION
    STATUS        current
    DESCRIPTION
        ""
    SYNTAX        INTEGER
    {
        nop(0),
        configCallhome(124)
    }

CfprApCallhomeFormat ::= TEXTUAL-CONVENTION
    STATUS        current
    DESCRIPTION
        ""
    SYNTAX        INTEGER
    {
        xml(1),
        fullTxt(2),
        shortTxt(4)
    }

CfprApCallhomeHttpProxyEnable ::= TEXTUAL-CONVENTION
    STATUS        current
    DESCRIPTION
        ""
    SYNTAX        INTEGER
    {
        off(0),
        on(1)
    }

CfprApCallhomeLevel ::= TEXTUAL-CONVENTION
    STATUS        current
    DESCRIPTION
        ""
    SYNTAX        INTEGER
    {
        debug(0),
        normal(1),
        notification(2),
        warning(3),
        minor(4),
        major(5),
        critical(6),
        fatal(7),
        disaster(8)
    }

CfprApCallhomePolicyAdminState ::= TEXTUAL-CONVENTION
    STATUS        current
    DESCRIPTION
        ""
    SYNTAX        INTEGER
    {
        enabled(1),
        disabled(2)
    }

CfprApCallhomeUrgency ::= TEXTUAL-CONVENTION
    STATUS        current
    DESCRIPTION
        ""
    SYNTAX        INTEGER
    {
        emergency(0),
        alert(1),
        critical(2),
        error(3),
        warning(4),
        notice(5),
        info(6),
        debug(7)
    }

CfprApCallhomeReportingType ::= TEXTUAL-CONVENTION
    STATUS        current
    DESCRIPTION
        ""
    SYNTAX        INTEGER
    {
        smartLicenseData(0),
        smartCallHomeData(1)
    }

CfprApCapabilityAdminState ::= TEXTUAL-CONVENTION
    STATUS        current
    DESCRIPTION
        ""
    SYNTAX        INTEGER
    {
        restart(0),
        idle(1)
    }

CfprApCapabilityCatalogueFsmCurrentFsm ::= TEXTUAL-CONVENTION
    STATUS        current
    DESCRIPTION
        ""
    SYNTAX        INTEGER
    {
        nop(0),
        activateCatalog(421),
        deployCatalogue(435)
    }

CfprApCapabilityCatalogueFsmStageName ::= TEXTUAL-CONVENTION
    STATUS        current
    DESCRIPTION
        ""
    SYNTAX        INTEGER
    {
        nop(0),
        activateCatalogBegin(421),
        activateCatalogCopyCatFromRep(422),
        activateCatalogUnpackLocal(423),
        activateCatalogCopyExternalRepToRemote(424),
        activateCatalogCopyRemote(425),
        activateCatalogApplyCatalog(426),
        activateCatalogRescanImages(427),
        activateCatalogEvaluateStatus(428),
        deployCatalogueBegin(435),
        deployCatalogueSyncPortAGLocal(436),
        deployCatalogueSyncPortAGRemote(437),
        deployCatalogueFinalize(438),
        activateCatalogFail(552),
        activateCatalogSuccess(553),
        deployCatalogueFail(554),
        deployCatalogueSuccess(555)
    }

CfprApCapabilityCatalogueFsmTaskItem ::= TEXTUAL-CONVENTION
    STATUS        current
    DESCRIPTION
        ""
    SYNTAX        INTEGER
    {
        nop(0),
        activateCatalog(421),
        deployCatalogue(435)
    }

CfprApCapabilityFeatureStatus ::= TEXTUAL-CONVENTION
    STATUS        current
    DESCRIPTION
        ""
    SYNTAX        INTEGER
    {
        supported(0),
        unsupported(1)
    }

CfprApCapabilityMgmtExtensionFsmCurrentFsm ::= TEXTUAL-CONVENTION
    STATUS        current
    DESCRIPTION
        ""
    SYNTAX        INTEGER
    {
        nop(0),
        activateMgmtExt(429)
    }

CfprApCapabilityMgmtExtensionFsmStageName ::= TEXTUAL-CONVENTION
    STATUS        current
    DESCRIPTION
        ""
    SYNTAX        INTEGER
    {
        nop(0),
        activateMgmtExtBegin(429),
        activateMgmtExtUnpackLocal(430),
        activateMgmtExtCopyRemote(431),
        activateMgmtExtApplyCatalog(432),
        activateMgmtExtRescanImages(433),
        activateMgmtExtEvaluateStatus(434),
        activateMgmtExtFail(556),
        activateMgmtExtSuccess(557)
    }

CfprApCapabilityMgmtExtensionFsmTaskItem ::= TEXTUAL-CONVENTION
    STATUS        current
    DESCRIPTION
        ""
    SYNTAX        INTEGER
    {
        nop(0),
        activateMgmtExt(429)
    }

CfprApCapabilityOperStatus ::= TEXTUAL-CONVENTION
    STATUS        current
    DESCRIPTION
        ""
    SYNTAX        INTEGER
    {
        init(0),
        downloading(1),
        downloaded(2),
        applied(3),
        failed(4)
    }

CfprApCapabilityPlatform ::= TEXTUAL-CONVENTION
    STATUS        current
    DESCRIPTION
        ""
    SYNTAX        INTEGER
    {
        ucs6100(0),
        ucs6200(1),
        ucs6324(2)
    }

CfprApCapabilityUpdaterFsmCurrentFsm ::= TEXTUAL-CONVENTION
    STATUS        current
    DESCRIPTION
        ""
    SYNTAX        INTEGER
    {
        nop(0),
        updater(413)
    }

CfprApCapabilityUpdaterFsmStageName ::= TEXTUAL-CONVENTION
    STATUS        current
    DESCRIPTION
        ""
    SYNTAX        INTEGER
    {
        nop(0),
        updaterBegin(413),
        updaterLocal(414),
        updaterUnpackLocal(415),
        updaterDeleteLocal(416),
        updaterCopyRemote(417),
        updaterApply(418),
        updaterRescanImages(419),
        updaterEvaluateStatus(420),
        updaterFail(558),
        updaterSuccess(559)
    }

CfprApCapabilityUpdaterFsmTaskItem ::= TEXTUAL-CONVENTION
    STATUS        current
    DESCRIPTION
        ""
    SYNTAX        INTEGER
    {
        nop(0),
        updater(413)
    }

CfprApChangeStatus ::= TEXTUAL-CONVENTION
    STATUS        current
    DESCRIPTION
        ""
    SYNTAX        INTEGER
    {
        modified(0),
        created(1),
        deleted(2),
        intentDeletion(3)
    }

CfprApCimcvmediaDeviceType ::= TEXTUAL-CONVENTION
    STATUS        current
    DESCRIPTION
        ""
    SYNTAX        INTEGER
    {
        unknown(0),
        cdd(1),
        hdd(2)
    }

CfprApCimcvmediaErrorType ::= TEXTUAL-CONVENTION
    STATUS        current
    DESCRIPTION
        ""
    SYNTAX        INTEGER
    {
        unknown(0),
        none(1),
        genericFailure(2),
        connectionTimeout(3),
        connectionRejected(4),
        authenticationFailed(5),
        badPath(6),
        badParam(7),
        invalidVdiskUsage(8),
        invalidVdiskType(9),
        alreadyMapped(10),
        imageStoreFull(11),
        fileNotFound(12),
        openRoFailed(13),
        openRwFailed(14),
        diskEjected(15),
        diskIoFailure(16),
        writeToReadonlyFile(17),
        mountInUse(18),
        invalidArgument(19),
        imgageDeleted(20),
        postmapError(21)
    }

CfprApCimcvmediaMountConfigRetryOnMountFail ::= TEXTUAL-CONVENTION
    STATUS        current
    DESCRIPTION
        ""
    SYNTAX        INTEGER
    {
        no(0),
        yes(1)
    }

CfprApCimcvmediaMountStatus ::= TEXTUAL-CONVENTION
    STATUS        current
    DESCRIPTION
        ""
    SYNTAX        INTEGER
    {
        unknown(0),
        mounting(1),
        mounted(2),
        unmounting(3),
        notMounted(4),
        mountFailed(5),
        unmountFailed(6)
    }

CfprApCimcvmediaTransport ::= TEXTUAL-CONVENTION
    STATUS        current
    DESCRIPTION
        ""
    SYNTAX        INTEGER
    {
        unknown(0),
        nfs(1),
        cifs(2),
        http(3),
        https(4)
    }

CfprApCommAdminState ::= TEXTUAL-CONVENTION
    STATUS        current
    DESCRIPTION
        ""
    SYNTAX        INTEGER
    {
        enabled(1),
        disabled(2)
    }

CfprApCommChannel ::= TEXTUAL-CONVENTION
    STATUS        current
    DESCRIPTION
        ""
    SYNTAX        INTEGER
    {
        fullssl(0),
        noencssl(1),
        plain(2)
    }

CfprApCommCipherSuiteMode ::= TEXTUAL-CONVENTION
    STATUS        current
    DESCRIPTION
        ""
    SYNTAX        INTEGER
    {
        highStrength(1),
        mediumStrength(2),
        lowStrength(3),
        custom(4)
    }

CfprApCommClientAdminState ::= TEXTUAL-CONVENTION
    STATUS        current
    DESCRIPTION
        ""
    SYNTAX        INTEGER
    {
        enabled(1),
        disabled(2)
    }

CfprApCommDnsProviderAdminState ::= TEXTUAL-CONVENTION
    STATUS        current
    DESCRIPTION
        ""
    SYNTAX        INTEGER
    {
        enabled(1),
        disabled(2)
    }

CfprApCommFilePathProtocol ::= TEXTUAL-CONVENTION
    STATUS        current
    DESCRIPTION
        ""
    SYNTAX        INTEGER
    {
        none(0),
        workspace(1),
        volatile(2),
        ftp(3),
        tftp(4),
        scp(5),
        sftp(6),
        usbdrive(7),
        usbA(8),
        usbB(9)
    }

CfprApCommNtpProviderAdminState ::= TEXTUAL-CONVENTION
    STATUS        current
    DESCRIPTION
        ""
    SYNTAX        INTEGER
    {
        enabled(1),
        disabled(2)
    }

CfprApCommProtocol ::= TEXTUAL-CONVENTION
    STATUS        current
    DESCRIPTION
        ""
    SYNTAX        INTEGER
    {
        none(0),
        tcp(1),
        udp(2),
        all(3)
    }

CfprApCommShellProto ::= TEXTUAL-CONVENTION
    STATUS        current
    DESCRIPTION
        ""
    SYNTAX        INTEGER
    {
        none(0),
        tcp(1),
        udp(2),
        all(3)
    }

CfprApCommSnmpConfigState ::= TEXTUAL-CONVENTION
    STATUS        current
    DESCRIPTION
        ""
    SYNTAX        INTEGER
    {
        ok(0),
        notApplied(1)
    }

CfprApCommSnmpProto ::= TEXTUAL-CONVENTION
    STATUS        current
    DESCRIPTION
        ""
    SYNTAX        INTEGER
    {
        none(0),
        tcp(1),
        udp(2),
        all(3)
    }

CfprApCommSnmpAuth ::= TEXTUAL-CONVENTION
    STATUS        current
    DESCRIPTION
        ""
    SYNTAX        INTEGER
    {
        sha(2)
    }

CfprApCommSnmpNotificationType ::= TEXTUAL-CONVENTION
    STATUS        current
    DESCRIPTION
        ""
    SYNTAX        INTEGER
    {
        traps(1),
        informs(2)
    }

CfprApCommSnmpV3Privilege ::= TEXTUAL-CONVENTION
    STATUS        current
    DESCRIPTION
        ""
    SYNTAX        INTEGER
    {
        auth(1),
        noauth(2),
        priv(3)
    }

CfprApCommSnmpVersion ::= TEXTUAL-CONVENTION
    STATUS        current
    DESCRIPTION
        ""
    SYNTAX        INTEGER
    {
        v1(1),
        v2c(2),
        v3(3)
    }

CfprApCommSshAdminState ::= TEXTUAL-CONVENTION
    STATUS        current
    DESCRIPTION
        ""
    SYNTAX        INTEGER
    {
        enabled(1),
        disabled(2)
    }

CfprApCommSvcEpFsmCurrentFsm ::= TEXTUAL-CONVENTION
    STATUS        current
    DESCRIPTION
        ""
    SYNTAX        INTEGER
    {
        nop(0),
        updateSvcEp(335),
        restartWebSvc(341)
    }

CfprApCommSvcEpFsmStageName ::= TEXTUAL-CONVENTION
    STATUS        current
    DESCRIPTION
        ""
    SYNTAX        INTEGER
    {
        nop(0),
        updateSvcEpBegin(335),
        updateSvcEpSetEpLocal(336),
        updateSvcEpSetEpPeer(337),
        updateSvcEpPropogateEpSettings(338),
        updateSvcEpPropogateEpTimeZoneSettingsToFexIomLocal(339),
        updateSvcEpPropogateEpTimeZoneSettingsToFexIomPeer(340),
        restartWebSvcBegin(341),
        restartWebSvcLocal(342),
        restartWebSvcPeer(343),
        restartWebSvcFail(560),
        restartWebSvcSuccess(561),
        updateSvcEpFail(562),
        updateSvcEpSuccess(563)
    }

CfprApCommSvcEpFsmTaskFlags ::= TEXTUAL-CONVENTION
    STATUS        current
    DESCRIPTION
        ""
    SYNTAX        BITS
    {
        samDmeCommSvcEpUpdateSvcEpEpChange(24),
        samDmeCommSvcEpUpdateSvcEpPropogateSettings(25)
    }

CfprApCommSvcEpFsmTaskItem ::= TEXTUAL-CONVENTION
    STATUS        current
    DESCRIPTION
        ""
    SYNTAX        INTEGER
    {
        nop(0),
        updateSvcEp(335),
        restartWebSvc(341)
    }

CfprApCommSyslogProto ::= TEXTUAL-CONVENTION
    STATUS        current
    DESCRIPTION
        ""
    SYNTAX        INTEGER
    {
        none(0),
        tcp(1),
        udp(2),
        all(3)
    }

CfprApCommSyslogAdminState ::= TEXTUAL-CONVENTION
    STATUS        current
    DESCRIPTION
        ""
    SYNTAX        INTEGER
    {
        enabled(1),
        disabled(2)
    }

CfprApCommSyslogClientEnum ::= TEXTUAL-CONVENTION
    STATUS        current
    DESCRIPTION
        ""
    SYNTAX        INTEGER
    {
        primary(1),
        secondary(2),
        tertiary(3)
    }

CfprApCommSyslogFileSize ::= TEXTUAL-CONVENTION
    STATUS        current
    DESCRIPTION
        ""
    SYNTAX        Gauge32 (4096..4194304)

CfprApCommSyslogForwardingFacility ::= TEXTUAL-CONVENTION
    STATUS        current
    DESCRIPTION
        ""
    SYNTAX        INTEGER
    {
        local0(0),
        local1(1),
        local2(2),
        local3(3),
        local4(4),
        local5(5),
        local6(6),
        local7(7)
    }

CfprApCommSyslogRestrictedSeverity ::= TEXTUAL-CONVENTION
    STATUS        current
    DESCRIPTION
        ""
    SYNTAX        INTEGER
    {
        emergencies(0),
        alerts(1),
        critical(2)
    }

CfprApCommSyslogSeverity ::= TEXTUAL-CONVENTION
    STATUS        current
    DESCRIPTION
        ""
    SYNTAX        INTEGER
    {
        emergencies(0),
        alerts(1),
        critical(2),
        errors(3),
        warnings(4),
        notifications(5),
        information(6),
        debugging(7)
    }

CfprApCommSyslogSourceAudits ::= TEXTUAL-CONVENTION
    STATUS        current
    DESCRIPTION
        ""
    SYNTAX        INTEGER
    {
        enabled(1),
        disabled(2)
    }

CfprApCommSyslogSourceEvents ::= TEXTUAL-CONVENTION
    STATUS        current
    DESCRIPTION
        ""
    SYNTAX        INTEGER
    {
        enabled(1),
        disabled(2)
    }

CfprApCommSyslogSourceFaults ::= TEXTUAL-CONVENTION
    STATUS        current
    DESCRIPTION
        ""
    SYNTAX        INTEGER
    {
        enabled(1),
        disabled(2)
    }

CfprApCommTimeZoneConfigState ::= TEXTUAL-CONVENTION
    STATUS        current
    DESCRIPTION
        ""
    SYNTAX        INTEGER
    {
        success(0),
        failure(1)
    }

CfprApCommWebProto ::= TEXTUAL-CONVENTION
    STATUS        current
    DESCRIPTION
        ""
    SYNTAX        INTEGER
    {
        none(0),
        tcp(1),
        udp(2),
        all(3)
    }

CfprApComputeABoardPower ::= TEXTUAL-CONVENTION
    STATUS        current
    DESCRIPTION
        ""
    SYNTAX        INTEGER
    {
        unknown(0),
        on(1),
        test(2),
        off(3),
        online(4),
        offline(5),
        offduty(6),
        degraded(7),
        powerSave(8),
        error(9),
        ok(10),
        failed(11),
        notSupported(100)
    }

CfprApComputeAdminLinkAggregation ::= TEXTUAL-CONVENTION
    STATUS        current
    DESCRIPTION
        ""
    SYNTAX        INTEGER
    {
        none(0),
        portChannel(1),
        global(2)
    }

CfprApComputeAdminMemoryState ::= TEXTUAL-CONVENTION
    STATUS        current
    DESCRIPTION
        ""
    SYNTAX        INTEGER
    {
        policy(1),
        resetMemoryErrors(2),
        resetInProgress(3)
    }

CfprApComputeAdminPowerState ::= TEXTUAL-CONVENTION
    STATUS        current
    DESCRIPTION
        ""
    SYNTAX        INTEGER
    {
        cycleImmediate(2),
        cycleWait(3),
        hardResetImmediate(4),
        hardResetWait(5),
        cmosResetImmediate(12),
        bmcResetImmediate(13),
        bmcResetWait(14),
        diagnosticInterrupt(15),
        kvmReset(16),
        policy(30),
        adminUp(31),
        adminDown(32),
        ipmiReset(33)
    }

CfprApComputeAdminState ::= TEXTUAL-CONVENTION
    STATUS        current
    DESCRIPTION
        ""
    SYNTAX        INTEGER
    {
        inService(1),
        outOfService(2)
    }

CfprApComputeAdminTrigger ::= TEXTUAL-CONVENTION
    STATUS        current
    DESCRIPTION
        ""
    SYNTAX        INTEGER
    {
        undiscovered(0),
        rediscover(1),
        resetToFactory(2),
        discovered(3),
        remove(4),
        migrate(5),
        decommission(6),
        upgradeFirmware(7)
    }

CfprApComputeAlarmSeverity ::= TEXTUAL-CONVENTION
    STATUS        current
    DESCRIPTION
        ""
    SYNTAX        INTEGER
    {
        minor(1),
        severe(2)
    }

CfprApComputeAssociation ::= TEXTUAL-CONVENTION
    STATUS        current
    DESCRIPTION
        ""
    SYNTAX        INTEGER
    {
        none(0),
        establishing(1),
        associated(2),
        removing(3),
        failed(4),
        throttled(5)
    }

CfprApComputeAvailability ::= TEXTUAL-CONVENTION
    STATUS        current
    DESCRIPTION
        ""
    SYNTAX        INTEGER
    {
        unavailable(0),
        available(1)
    }

CfprApComputeBlackListing ::= TEXTUAL-CONVENTION
    STATUS        current
    DESCRIPTION
        ""
    SYNTAX        INTEGER
    {
        disabled(0),
        enabled(1)
    }

CfprApComputeBladeSlotId ::= TEXTUAL-CONVENTION
    STATUS        current
    DESCRIPTION
        ""
    SYNTAX        Gauge32 (1..8)

CfprApComputeBladeFsmCurrentFsm ::= TEXTUAL-CONVENTION
    STATUS        current
    DESCRIPTION
        ""
    SYNTAX        INTEGER
    {
        nop(0),
        diag(186),
        swConnUpd(208),
        serviceInfraDeploy(213),
        serviceInfraWithdraw(216)
    }

CfprApComputeBladeFsmStageName ::= TEXTUAL-CONVENTION
    STATUS        current
    DESCRIPTION
        ""
    SYNTAX        INTEGER
    {
        nop(0),
        diagBegin(186),
        diagConfigFeLocal(187),
        diagConfigFePeer(188),
        diagSwConfigLocal(189),
        diagSwConfigPeer(190),
        diagDisableServerConnSwB(191),
        diagEnableServerConnSwA(192),
        diagDisableServerConnSwA(193),
        diagEnableServerConnSwB(194),
        diagCleanupServerConnSwA(195),
        diagCleanupServerConnSwB(196),
        diagSwUnconfigLocal(197),
        diagSwUnconfigPeer(198),
        diagRemoveConfig(199),
        diagRestoreConfigFeLocal(200),
        diagRestoreConfigFePeer(201),
        diagEvaluateStatus(202),
        diagSuccess(203),
        diagFail(204),
        swConnUpdBegin(208),
        swConnUpdA(209),
        swConnUpdB(210),
        serviceInfraDeployBegin(213),
        serviceInfraDeploySwConfigLocal(214),
        serviceInfraDeploySwConfigPeer(215),
        serviceInfraWithdrawBegin(216),
        serviceInfraWithdrawSwUnConfigLocal(217),
        serviceInfraWithdrawSwUnConfigPeer(218),
        serviceInfraDeployFail(564),
        serviceInfraDeploySuccess(565),
        serviceInfraWithdrawFail(566),
        serviceInfraWithdrawSuccess(567),
        swConnUpdFail(568),
        swConnUpdSuccess(569)
    }

CfprApComputeBladeFsmTaskFlags ::= TEXTUAL-CONVENTION
    STATUS        current
    DESCRIPTION
        ""
    SYNTAX        BITS
    {
        samDmeComputeBladeDiagDetailDiag(17),
        samDmeComputeBladeDiagEfiDiag(18),
        samDmeComputeBladeDiagCancelDiag(19)
    }

CfprApComputeBladeFsmTaskItem ::= TEXTUAL-CONVENTION
    STATUS        current
    DESCRIPTION
        ""
    SYNTAX        INTEGER
    {
        nop(0),
        diag(186)
    }

CfprApComputeChassisConnPolicyChassisId ::= TEXTUAL-CONVENTION
    STATUS        current
    DESCRIPTION
        ""
    SYNTAX        Gauge32 (1..255)

CfprApComputeChassisDiscAction ::= TEXTUAL-CONVENTION
    STATUS        current
    DESCRIPTION
        ""
    SYNTAX        INTEGER
    {
        immediate(0),
        userAcknowledged(1),
        n1Link(2),
        n2Link(3),
        n4Link(4),
        n8Link(5),
        platformMax(6)
    }

CfprApComputeChassisQualMaxId ::= TEXTUAL-CONVENTION
    STATUS        current
    DESCRIPTION
        ""
    SYNTAX        Gauge32 (1..255)

CfprApComputeChassisQualMinId ::= TEXTUAL-CONVENTION
    STATUS        current
    DESCRIPTION
        ""
    SYNTAX        Gauge32 (1..255)

CfprApComputeCheckPoint ::= TEXTUAL-CONVENTION
    STATUS        current
    DESCRIPTION
        ""
    SYNTAX        INTEGER
    {
        unknown(0),
        removing(1),
        shallowCheckpoint(2),
        deepCheckpoint(3),
        discovered(4)
    }

CfprApComputeConnectivityRebalancing ::= TEXTUAL-CONVENTION
    STATUS        current
    DESCRIPTION
        ""
    SYNTAX        INTEGER
    {
        immediate(0),
        userAcknowledged(1)
    }

CfprApComputeDiscovery ::= TEXTUAL-CONVENTION
    STATUS        current
    DESCRIPTION
        ""
    SYNTAX        INTEGER
    {
        undiscovered(0),
        inProgress(1),
        malformedFruInfo(2),
        fruNotReady(3),
        insufficientlyEquipped(4),
        invalidAdaptorIocard(5),
        failed(8),
        complete(16),
        retry(32),
        throttled(64),
        illegalFru(128),
        fruIdentityIndeterminate(129),
        fruStateIndeterminate(130),
        diagnosticsInProgress(131),
        efidiagnosticsInProgress(132),
        diagnosticsFailed(133),
        diagnosticsComplete(134),
        waitingForUserAck(135),
        userAcknowledged(136),
        waitingForMgmtAck(137),
        illegalPartNumber(138)
    }

CfprApComputeIOHubEnvStatsThresholded ::= TEXTUAL-CONVENTION
    STATUS        current
    DESCRIPTION
        ""
    SYNTAX        BITS
    {
        temperature(0),
        temperatureAvg(1),
        temperatureMax(2),
        temperatureMin(3)
    }

CfprApComputeIOHubEnvStatsHistThresholded ::= TEXTUAL-CONVENTION
    STATUS        current
    DESCRIPTION
        ""
    SYNTAX        BITS
    {
        temperature(0),
        temperatureAvg(1),
        temperatureMax(2),
        temperatureMin(3)
    }

CfprApComputeIssues ::= TEXTUAL-CONVENTION
    STATUS        current
    DESCRIPTION
        ""
    SYNTAX        BITS
    {
        computeThermal(0),
        computeInoperable(1),
        computeVoltage(2),
        computePerf(3),
        computePower(4),
        removed(5),
        config(6),
        computePostFailure(7),
        cpuThermal(8),
        cpuInoperable(9),
        cpuVoltage(10),
        cpuPerf(11),
        cpuPower(12),
        memoryThermal(13),
        memoryInoperable(14),
        memoryVoltage(15),
        memoryPerf(16),
        memoryPower(17),
        adaptorThermal(18),
        adaptorInoperable(19),
        adaptorVoltage(20),
        adaptorPerf(21),
        adaptorPower(22),
        nicThermal(23),
        nicInoperable(24),
        nicVoltage(25),
        nicPerf(26),
        nicPower(27),
        hbaThermal(28),
        hbaInoperable(29),
        hbaVoltage(30),
        hbaPerf(31),
        hbaPower(32),
        mismatch(33),
        powerInoperable(34),
        networkMisconfig(35),
        adaptorMismatch(36)
    }

CfprApComputeKvmMgmtPolicyVmediaEncryption ::= TEXTUAL-CONVENTION
    STATUS        current
    DESCRIPTION
        ""
    SYNTAX        INTEGER
    {
        disable(0),
        enable(1)
    }

CfprApComputeLinkAggregation ::= TEXTUAL-CONVENTION
    STATUS        current
    DESCRIPTION
        ""
    SYNTAX        INTEGER
    {
        none(0),
        portChannel(1)
    }

CfprApComputeLinkAggregationCap ::= TEXTUAL-CONVENTION
    STATUS        current
    DESCRIPTION
        ""
    SYNTAX        BITS
    {
        portChannel(0)
    }

CfprApComputeMbPowerStatsThresholded ::= TEXTUAL-CONVENTION
    STATUS        current
    DESCRIPTION
        ""
    SYNTAX        BITS
    {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CfprApComputeMbPowerStatsHistThresholded ::= TEXTUAL-CONVENTION
    STATUS        current
    DESCRIPTION
        ""
    SYNTAX        BITS
    {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CfprApComputeMbTempStatsThresholded ::= TEXTUAL-CONVENTION
    STATUS        current
    DESCRIPTION
        ""
    SYNTAX        BITS
    {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CfprApComputeMbTempStatsHistThresholded ::= TEXTUAL-CONVENTION
    STATUS        current
    DESCRIPTION
        ""
    SYNTAX        BITS
    {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CfprApComputeMemoryUnitConstraintType ::= TEXTUAL-CONVENTION
    STATUS        current
    DESCRIPTION
        ""
    SYNTAX        INTEGER
    {
        unknown(0),
        kit(1)
    }

CfprApComputeMode ::= TEXTUAL-CONVENTION
    STATUS        current
    DESCRIPTION
        ""
    SYNTAX        INTEGER
    {
        none(0),
        single(1),
        scaled(2)
    }

CfprApComputeOwner ::= TEXTUAL-CONVENTION
    STATUS        current
    DESCRIPTION
        ""
    SYNTAX        INTEGER
    {
        policy(1),
        management(2)
    }

CfprApComputePCIeFatalCompletionStatsThresholded ::= TEXTUAL-CONVENTION
    STATUS        current
    DESCRIPTION
        ""
    SYNTAX        BITS
    {
        abortErrors(0),
        timeoutErrors(1),
        unexpectedErrors(2)
    }

CfprApComputePCIeFatalProtocolStatsThresholded ::= TEXTUAL-CONVENTION
    STATUS        current
    DESCRIPTION
        ""
    SYNTAX        BITS
    {
        dllpErrors(0),
        flowControlErrors(1)
    }

CfprApComputePCIeFatalReceiveStatsThresholded ::= TEXTUAL-CONVENTION
    STATUS        current
    DESCRIPTION
        ""
    SYNTAX        BITS
    {
        bufferOverflowErrors(0),
        errFatalErrors(1),
        errNonFatalErrors(2),
        unsupportedRequestErrors(3)
    }

CfprApComputePCIeFatalStatsThresholded ::= TEXTUAL-CONVENTION
    STATUS        current
    DESCRIPTION
        ""
    SYNTAX        BITS
    {
        acsViolationErrors(0),
        malformedTLPErrors(1),
        poisonedTLPErrors(2),
        surpriseLinkDownErrors(3)
    }

CfprApComputePciCapOrder ::= TEXTUAL-CONVENTION
    STATUS        current
    DESCRIPTION
        ""
    SYNTAX        INTEGER
    {
        ascending(0),
        descending(1),
        ascendingDual(2),
        ascendingSeq(3),
        ascendingExtended(4)
    }

CfprApComputePhysicalLowVoltageMemory ::= TEXTUAL-CONVENTION
    STATUS        current
    DESCRIPTION
        ""
    SYNTAX        INTEGER
    {
        notApplicable(0),
        lowVoltage(1),
        regularVoltage(2)
    }

CfprApComputePhysicalFsmCurrentFsm ::= TEXTUAL-CONVENTION
    STATUS        current
    DESCRIPTION
        ""
    SYNTAX        INTEGER
    {
        nop(0),
        swConnUpd(208),
        serviceInfraDeploy(213),
        serviceInfraWithdraw(216)
    }

CfprApComputePhysicalFsmStageName ::= TEXTUAL-CONVENTION
    STATUS        current
    DESCRIPTION
        ""
    SYNTAX        INTEGER
    {
        nop(0),
        swConnUpdBegin(208),
        swConnUpdA(209),
        swConnUpdB(210),
        serviceInfraDeployBegin(213),
        serviceInfraDeploySwConfigLocal(214),
        serviceInfraDeploySwConfigPeer(215),
        serviceInfraWithdrawBegin(216),
        serviceInfraWithdrawSwUnConfigLocal(217),
        serviceInfraWithdrawSwUnConfigPeer(218),
        serviceInfraDeployFail(564),
        serviceInfraDeploySuccess(565),
        serviceInfraWithdrawFail(566),
        serviceInfraWithdrawSuccess(567),
        swConnUpdFail(568),
        swConnUpdSuccess(569)
    }

CfprApComputePhysicalFsmTaskItem ::= TEXTUAL-CONVENTION
    STATUS        current
    DESCRIPTION
        ""
    SYNTAX        INTEGER
    {
        nop(0),
        swConnUpd(208),
        serviceInfraDeploy(213),
        serviceInfraWithdraw(216)
    }

CfprApComputePooledRackUnitId ::= TEXTUAL-CONVENTION
    STATUS        current
    DESCRIPTION
        ""
    SYNTAX        Gauge32 (1..255)

CfprApComputePooledSlotSlotId ::= TEXTUAL-CONVENTION
    STATUS        current
    DESCRIPTION
        ""
    SYNTAX        Gauge32 (1..8)

CfprApComputePsuClusterState ::= TEXTUAL-CONVENTION
    STATUS        current
    DESCRIPTION
        ""
    SYNTAX        INTEGER
    {
        unknown(0),
        slot1Master(1),
        slot2Master(2),
        notClustered(3)
    }

CfprApComputePsuControlRedundancy ::= TEXTUAL-CONVENTION
    STATUS        current
    DESCRIPTION
        ""
    SYNTAX        INTEGER
    {
        unknown(0),
        nonRedundant(1),
        nPlus1(2),
        grid(3)
    }

CfprApComputePsuRedundancy ::= TEXTUAL-CONVENTION
    STATUS        current
    DESCRIPTION
        ""
    SYNTAX        INTEGER
    {
        nonRedundant(1),
        nPlus1(2),
        grid(3)
    }

CfprApComputePsuRedundancyOperQualifier ::= TEXTUAL-CONVENTION
    STATUS        current
    DESCRIPTION
        ""
    SYNTAX        BITS
    {
        redundancyLost(0),
        redundancyDegraded(1),
        nonRedundantSufficientResources(2),
        nonRedundantInsufficientResources(3)
    }

CfprApComputePsuRedundancyOperState ::= TEXTUAL-CONVENTION
    STATUS        current
    DESCRIPTION
        ""
    SYNTAX        INTEGER
    {
        unknown(0),
        ok(1),
        failed(2),
        degraded(3)
    }

CfprApComputeRackQualMaxId ::= TEXTUAL-CONVENTION
    STATUS        current
    DESCRIPTION
        ""
    SYNTAX        Gauge32 (1..255)

CfprApComputeRackQualMinId ::= TEXTUAL-CONVENTION
    STATUS        current
    DESCRIPTION
        ""
    SYNTAX        Gauge32 (1..255)

CfprApComputeRackUnitId ::= TEXTUAL-CONVENTION
    STATUS        current
    DESCRIPTION
        ""
    SYNTAX        Gauge32 (1..255)

CfprApComputeRackUnitFsmCurrentFsm ::= TEXTUAL-CONVENTION
    STATUS        current
    DESCRIPTION
        ""
    SYNTAX        INTEGER
    {
        nop(0),
        swConnUpd(208),
        serviceInfraDeploy(213),
        serviceInfraWithdraw(216)
    }

CfprApComputeRackUnitFsmStageName ::= TEXTUAL-CONVENTION
    STATUS        current
    DESCRIPTION
        ""
    SYNTAX        INTEGER
    {
        nop(0),
        swConnUpdBegin(208),
        swConnUpdA(209),
        swConnUpdB(210),
        serviceInfraDeployBegin(213),
        serviceInfraDeploySwConfigLocal(214),
        serviceInfraDeploySwConfigPeer(215),
        serviceInfraWithdrawBegin(216),
        serviceInfraWithdrawSwUnConfigLocal(217),
        serviceInfraWithdrawSwUnConfigPeer(218),
        serviceInfraDeployFail(564),
        serviceInfraDeploySuccess(565),
        serviceInfraWithdrawFail(566),
        serviceInfraWithdrawSuccess(567),
        swConnUpdFail(568),
        swConnUpdSuccess(569)
    }

CfprApComputeRackUnitMbTempStatsThresholded ::= TEXTUAL-CONVENTION
    STATUS        current
    DESCRIPTION
        ""
    SYNTAX        BITS
    {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CfprApComputeRackUnitMbTempStatsHistThresholded ::= TEXTUAL-CONVENTION
    STATUS        current
    DESCRIPTION
        ""
    SYNTAX        BITS
    {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CfprApComputeScrubAction ::= TEXTUAL-CONVENTION
    STATUS        current
    DESCRIPTION
        ""
    SYNTAX        INTEGER
    {
        no(0),
        yes(1)
    }

CfprApComputeServerDiscPolicyFsmCurrentFsm ::= TEXTUAL-CONVENTION
    STATUS        current
    DESCRIPTION
        ""
    SYNTAX        INTEGER
    {
        nop(0),
        resolveScrubPolicy(1)
    }

CfprApComputeServerDiscPolicyFsmStageName ::= TEXTUAL-CONVENTION
    STATUS        current
    DESCRIPTION
        ""
    SYNTAX        INTEGER
    {
        nop(0),
        resolveScrubPolicyBegin(1),
        resolveScrubPolicyResolve(2),
        resolveScrubPolicyFail(570),
        resolveScrubPolicySuccess(571)
    }

CfprApComputeServerDiscPolicyFsmTaskItem ::= TEXTUAL-CONVENTION
    STATUS        current
    DESCRIPTION
        ""
    SYNTAX        INTEGER
    {
        nop(0),
        resolveScrubPolicy(1)
    }

CfprApComputeServerMgmtDiscAction ::= TEXTUAL-CONVENTION
    STATUS        current
    DESCRIPTION
        ""
    SYNTAX        INTEGER
    {
        autoAcknowledged(0),
        userAcknowledged(1)
    }

CfprApComputeSlotQualMaxId ::= TEXTUAL-CONVENTION
    STATUS        current
    DESCRIPTION
        ""
    SYNTAX        Gauge32 (1..8)

CfprApComputeSlotQualMinId ::= TEXTUAL-CONVENTION
    STATUS        current
    DESCRIPTION
        ""
    SYNTAX        Gauge32 (1..8)

CfprApComputeUpgradeStatus ::= TEXTUAL-CONVENTION
    STATUS        current
    DESCRIPTION
        ""
    SYNTAX        INTEGER
    {
        notUpgraded(0),
        upgraded(1),
        notApplicable(2)
    }

CfprApConditionAckAction ::= TEXTUAL-CONVENTION
    STATUS        current
    DESCRIPTION
        ""
    SYNTAX        INTEGER
    {
        deleteOnClear(1),
        initialSeverity(2)
    }

CfprApConditionActionIndicator ::= TEXTUAL-CONVENTION
    STATUS        current
    DESCRIPTION
        ""
    SYNTAX        INTEGER
    {
        creation(0),
        modification(1),
        deletion(2),
        stateTransition(3),
        special(4),
        failure(5)
    }

CfprApConditionCallHomeCause ::= TEXTUAL-CONVENTION
    STATUS        current
    DESCRIPTION
        ""
    SYNTAX        INTEGER
    {
        unspecified(0),
        identityUnestablishable(1),
        powerProblem(2),
        equipmentInoperable(3),
        equipmentInaccessible(4),
        vifIdsMismatch(5),
        adaptorMismatch(6),
        voltageProblem(7),
        psuInsufficient(8),
        psuMixedMode(9),
        connectivityProblem(10),
        equipmentDisabled(11),
        thermalProblem(12),
        configurationFailure(13),
        associationFailed(14),
        equipmentOffline(15),
        equipmentProblem(16),
        fruProblem(17),
        healthLedAmberBlinking(18),
        healthLedAmber(19),
        licenseGraceperiodExpired(20),
        equipmentDegraded(21),
        mgmtifDown(22),
        arpTargetsConfigError(23),
        ndiscTargetsConfigError(24),
        equipmentRemoved(25),
        limitReached(26),
        nearMaxLimit(27),
        inventoryFailed(28),
        memoryError(29),
        linkDown(30),
        electionFailure(31),
        managementServicesFailure(32),
        managementServicesUnresponsive(33),
        versionIncompatible(34),
        portFailed(35)
    }

CfprApConditionCause ::= TEXTUAL-CONVENTION
    STATUS        current
    DESCRIPTION
        ""
    SYNTAX        INTEGER
    {
        unknown(0),
        namedPolicyUnresolved(1),
        transition(2),
        vlanPermitUnresolved(3),
        groupPermitUnresolved(4),
        insufficientResources(5),
        insufficientlyEquipped(6),
        identityUnestablishable(7),
        powerProblem(8),
        thermalProblem(9),
        equipmentInoperable(10),
        discoveryFailed(11),
        associationFailed(12),
        disassociationFailed(13),
        equipmentMissing(14),
        equipmentInaccessible(15),
        vifIdsMismatch(16),
        adaptorMismatch(17),
        voltageProblem(18),
        emptyPool(19),
        equipmentProblem(20),
        boardCtrlUpgraded(21),
        vmediaMountInaccessible(22),
        decommissioned(23),
        beginFailed(24),
        fsmFailed(25),
        resolveFailed(26),
        checkInventoryStatusFailed(27),
        reportFullInventoryFailed(28),
        imageDeleted(29),
        imageUnusable(30),
        imageCannotBoot(31),
        activationFailed(32),
        cimcFirmwareMismatch(33),
        pldFirmwareMismatch(34),
        defaultHostpackMissing(35),
        localFailed(37),
        unpackLocalFailed(38),
        deleteLocalFailed(39),
        copyRemoteFailed(40),
        remoteFailed(41),
        copyExtToLocalFailed(42),
        copyExtToPeerFailed(43),
        startFailed(44),
        executeFailed(45),
        copyToLocalFailed(46),
        copyToPeerFailed(47),
        updateLocalFailed(48),
        verifyLocalFailed(49),
        resetLocalFailed(50),
        updateRemoteFailed(51),
        verifyRemoteFailed(52),
        resetRemoteFailed(53),
        copyImgFromRepFailed(54),
        copyiomimgToSubFailed(55),
        waitForReadyFailed(56),
        restoreFailed(57),
        waitForDeployFailed(58),
        validateApplicationPackFailed(59),
        deleteCurrentApplicationFailed(60),
        pollDeleteCurrentApplicationStatusFailed(61),
        setStartupServiceManagerVersionFailed(62),
        pollStartupServiceManagerStatusFailed(63),
        activateNpuImageFailed(64),
        pollNpuActivationStatusFailed(65),
        activateSystemImageFailed(66),
        activateFirmwareImageFailed(67),
        rebootSystemForImageUpgradeFailed(68),
        waitForSystemReadyFailed(69),
        pollSystemActivationStatusFailed(70),
        activateManagerImageFailed(71),
        pollManagerActivationStatusFailed(72),
        activateApplicationImageFailed(73),
        pollApplicationActivationStatusFailed(74),
        completeFirmwareUpgradeFailed(75),
        validateFirmwarePackFailed(76),
        debundlePortFailed(77),
        pollDebundlePortFailed(78),
        activateFirmwarePackFailed(79),
        pollActivateOfFirmwarePackFailed(80),
        updateImageVersionFailed(81),
        waitForFirmwareVersionUpdateFailed(82),
        updatePackageVersionFailed(83),
        resolveDistributableNamesFailed(84),
        resolveDistributableFailed(85),
        resolveImagesFailed(86),
        activateCatalogFailed(87),
        pingFailed(88),
        groupCapInsufficient(89),
        oldChassisComponentFirmware(90),
        oldFirmware(91),
        psuInsufficient(92),
        psuRedundancyFail(93),
        powerCapFail(94),
        powerConsumptionHitLimit(95),
        noAckFromBios(96),
        noCapFail(97),
        psuMixedMode(98),
        slotNotResponding(99),
        bladeNotWorking(100),
        diskFormatFailed(101),
        bladeSwap(102),
        switchConfigFailed(103),
        appinstanceNotResponding(104),
        appinstanceInstallFailed(105),
        appinstanceStartFailed(106),
        appinstanceUpdateFailed(107),
        appinstanceStopFailed(108),
        appinstanceError(109),
        logicalDeviceIncompleteConfiguration(110),
        logicalDeviceError(111),
        licenseAgreementNotAccepted(112),
        appinstanceUnsupported(113),
        appMetaCorrupted(114),
        updateFailed(115),
        stopDecoratorAppsFailed(116),
        wairForStopDecoratorsFailed(117),
        stopMainAppFailed(118),
        waitForBladeRebootFailed(119),
        waitForStopMainAppFailed(120),
        startAppsFailed(121),
        waitForPortReadyFailed(122),
        createLogicalDeviceFailed(123),
        updateConnectivityFailed(124),
        updateVlanGroupsFailed(125),
        updateEthFlowMonFailed(126),
        portInventorySwAfailed(127),
        portInventorySwBfailed(128),
        configSwAfailed(129),
        configSwBfailed(130),
        verifyPhysConfigFailed(131),
        successFailed(132),
        failFailed(133),
        verifyBreakoutConfigFailed(134),
        updateZonesFailed(135),
        noVlanOptimization(136),
        vifDown(137),
        configurationFailed(138),
        pinningMismatch(139),
        pinningMisconfig(140),
        inaccessibleVlanReferenced(141),
        referencedVlanUnresolvable(142),
        referencedRemoteVlanUnresolvable(143),
        invalidVlanInTheAllowedVlanList(144),
        vlanConflictPermit(145),
        profileConfigIncorrect(146),
        multipleConnectionPolicies(147),
        setLocalFailed(148),
        setPeerFailed(149),
        callhomeConfigError(150),
        disableFailed(151),
        enableFailed(152),
        disableAfailed(153),
        enableAfailed(154),
        disableBfailed(155),
        enableBfailed(156),
        unidentifiableFru(157),
        connectivityProblem(158),
        linkDown(159),
        linkMisconnected(160),
        linkMissing(161),
        validateLocalFailed(162),
        validateRemoteFailed(163),
        deleteRemoteFailed(164),
        equipmentDegraded(165),
        equipmentDisabled(166),
        applyTemplateFailed(167),
        applyIdentifiersFailed(168),
        checkAssignedIdentifiersForDupFailed(169),
        resolvePoliciesFailed(170),
        resolveNetworkPoliciesFailed(171),
        resolveNetworkTemplatesFailed(172),
        resolveIdentifiersFailed(173),
        applyDefaultIdentifiersFailed(174),
        checkAssignedDefaultIdentifiersForDupFailed(175),
        resolveDefaultIdentifiersFailed(176),
        resolveScheduleFailed(177),
        validatePolicyOwnershipFailed(178),
        applyPoliciesFailed(179),
        provisionStorageFailed(180),
        waitForStorageProvisionFailed(181),
        resolveBootConfigFailed(182),
        evaluateAssociationFailed(183),
        analyzeImpactFailed(184),
        waitForMaintPermissionFailed(185),
        waitForMaintWindowFailed(186),
        commitStorageFailed(187),
        waitForCommitStorageFailed(188),
        applyConfigFailed(189),
        waitForAssocCompletionFailed(190),
        configFeLocalFailed(191),
        configFePeerFailed(192),
        swConfigLocalFailed(193),
        swConfigPeerFailed(194),
        disableServerConnSwBfailed(195),
        enableServerConnSwAfailed(196),
        disableServerConnSwAfailed(197),
        enableServerConnSwBfailed(198),
        cleanupServerConnSwAfailed(199),
        cleanupServerConnSwBfailed(200),
        swUnconfigLocalFailed(201),
        swUnconfigPeerFailed(202),
        removeConfigFailed(203),
        restoreConfigFeLocalFailed(204),
        restoreConfigFePeerFailed(205),
        evaluateStatusFailed(206),
        cimcvlanCfgLocalFailed(207),
        cimcvlanCfgPeerFailed(208),
        aFailed(209),
        bFailed(210),
        swUnConfigLocalFailed(211),
        swUnConfigPeerFailed(212),
        checkLicenseFailed(213),
        identifyFailed(214),
        configureSwMgmtEndPointFailed(215),
        configureVifNsFailed(216),
        decomissionFailed(217),
        disableEndPointFailed(218),
        unIdentifyLocalFailed(219),
        unIdentifyPeerFailed(220),
        waitFailed(221),
        shutdownFailed(222),
        enablePortFailed(223),
        serverFailed(224),
        configurationFailure(225),
        maintenanceFailed(226),
        equipmentRemoved(227),
        serverInaccessible(228),
        assignmentFailed(229),
        unassociated(230),
        svnicNotPresent(231),
        nonExistentScheduler(232),
        unsupportedCimcFirmware(233),
        discoveryInProgress(234),
        configurationInProgress(235),
        unconfigurationInProgress(236),
        poweredOff(237),
        inMaintenance(238),
        underTest(239),
        serverUnassociated(240),
        serverAssociating(241),
        serverAssociated(242),
        serverDeassociating(243),
        serverUnassigned(244),
        serverAssigned(245),
        configurationNotApplied(246),
        configurationApplying(247),
        configurationApplied(248),
        newVnicVconSchemeApplied(249),
        satelliteConnectionAbsent(250),
        satelliteConnectionInit(251),
        satelliteMisConnected(252),
        unexpectedNumberOfLinks(253),
        equipmentOffline(254),
        fexUnsupported(255),
        performanceProblem(256),
        firmwareUpgradeProblem(257),
        unsupportedConnectivityConfiguration(258),
        equipmentUnacknowledged(259),
        autoFirmwareUpgrade(260),
        equipmentDisconnected(261),
        fruProblem(262),
        powerDown(263),
        act2Fail(264),
        healthLedAmberBlinking(265),
        tpmOnSlaveBoard(266),
        healthLedAmber(267),
        executeAfailed(268),
        executeBfailed(269),
        sendCommandFailed(270),
        waitStageFailed(271),
        updateAppInstanceFailed(272),
        checkBladeReadinessFailed(273),
        waitForAppsInstallationFailed(274),
        waitForLinkConfigurationFailed(275),
        releaseAppLicenseFailed(276),
        configureLinksFailed(277),
        waitForConfigCompletionFailed(278),
        updateBundleStatusFailed(279),
        sendBundleStatusFailed(280),
        sendInterfacesFailed(281),
        unconfigureLinksFailed(282),
        configureSwitchFailed(283),
        waitForSwitchConfigFailed(284),
        unconfigureLogicalDeviceFailed(285),
        sendStatusFailed(286),
        sendConfigFailed(287),
        startDiskFormatFailed(288),
        resetBladePowerFailed(289),
        waitForDiskFormatCompleteFailed(290),
        updateTimeZoneFailed(291),
        getAttributesFailed(292),
        sendUpdateFailed(293),
        stopAppFailed(294),
        waitForStopAppFailed(295),
        upgradeAppFailed(296),
        waitForUpgradeAppFailed(297),
        startAppFailed(298),
        configureFailed(299),
        clientLostConnectivity(300),
        licenseGraceperiodEntered(301),
        licenseGraceperiod10days(302),
        licenseGraceperiod30days(303),
        licenseGraceperiod60days(304),
        licenseGraceperiod90days(305),
        licenseGraceperiod119days(306),
        licenseGraceperiodExpired(307),
        licenseInsufficient(308),
        capacityExceeded(309),
        configurationError(310),
        operationFailed(311),
        equipmentUnhealthy(312),
        peerFailed(313),
        setEpLocalFailed(314),
        setEpPeerFailed(315),
        propogateEpSettingsFailed(316),
        propogateEpTimeZoneSettingsToFexIomLocalFailed(317),
        propogateEpTimeZoneSettingsToFexIomPeerFailed(318),
        providerGroupAlreadyExists(319),
        providerGroupSizeEmpty(320),
        invalidServerGroup(321),
        invalidKeyringCertificate(322),
        invalidKeyringModulus(323),
        invalidTrustpointCertChain(324),
        roleConfigError(325),
        localeConfigError(326),
        localeOrgConfigError(327),
        userRoleConfigError(328),
        userLocaleConfigError(329),
        keyringConfigError(330),
        snmpConfigError(331),
        timezoneFileNotExists(332),
        userConfigError(333),
        snmpUserConfigError(334),
        commSvcConfigError(335),
        setKeyRingLocalFailed(336),
        setKeyRingPeerFailed(337),
        postSetKeyRingLocalFailed(338),
        postSetKeyRingPeerFailed(339),
        setRealmLocalFailed(340),
        setRealmPeerFailed(341),
        setUserLocalFailed(342),
        setUserPeerFailed(343),
        serverError(344),
        tftpServerError(345),
        copySubFailed(346),
        copyPrimaryFailed(347),
        deleteSubFailed(348),
        deletePrimaryFailed(349),
        removeFailed(350),
        mgmtifDown(351),
        arpTargetsConfigError(352),
        ndiscTargetsConfigError(353),
        duplicatedAssigned(354),
        switchFailed(355),
        limitReached(356),
        nearMaxLimit(357),
        inventoryFailed(358),
        memoryError(359),
        extraPrimaryVlans(360),
        extraSecondaryVlans(361),
        extraSecondaryVlansPerPrimary(362),
        configInterfaceFailed(363),
        verifyLinkConfigFailed(364),
        setEpAfailed(365),
        setEpBfailed(366),
        bootupFailure(367),
        createLocalFailed(368),
        createRemoteFailed(369),
        suppressStatusChange(370),
        loadCatalogFailed(371),
        applyFailed(372),
        rescanImagesFailed(373),
        copyCatFromRepFailed(374),
        copyExternalRepToRemoteFailed(375),
        applyCatalogFailed(376),
        syncPortaglocalFailed(377),
        syncPortagremoteFailed(378),
        finalizeFailed(379),
        updateEthMonFailed(380),
        updateFcMonFailed(381),
        serverMoved(382),
        serverIdentificationProblem(383),
        primaryVlanMissingForIsolated(384),
        primaryVlanMissingForCommunity(385),
        emptyPinGroup(386),
        membershipDown(387),
        invalidTarget(388),
        configError(389),
        vlanMismatch(390),
        vlanErrorAssocPrimary(391),
        interfaceMisconfigured(392),
        missingPrimaryVlan(393),
        udldLinkDown(394),
        vlanMcastPolicyMisconfigured(395),
        namedVlanUnresolved(396),
        updateSspEthMonFailed(397),
        deletePcapFileFailed(398),
        syncFailed(399),
        validateConfigurationFailed(400),
        applyPhysicalFailed(401),
        waitOnPhysFailed(402),
        reportFailed(403),
        backupLocalFailed(404),
        uploadFailed(405),
        downloadLocalFailed(406),
        cleanUpFailed(407),
        configBreakoutFailed(408),
        waitForSwitchFailed(409),
        configFailed(410),
        reportResultsFailed(411),
        primaryFailed(412),
        secondaryFailed(413),
        electionFailure(414),
        managementServicesFailure(415),
        managementServicesUnresponsive(416),
        haNotReady(417),
        versionIncompatible(418),
        deviceSharedStorageError(419),
        haSshKeysMismatched(420),
        fprmProcessFailure(421),
        logCapacity(422),
        fileTransferFailed(423),
        newLink(424),
        anotherConnectionAlreadyEnabled(425),
        connectionUnused(426),
        unsupportedConnectivity(427),
        incompatibleServerFirmware(428),
        namedInbandVlanUnresolved(429),
        inbandUnsupportedServer(430),
        configBackupOutdated(431),
        leadershipChange(432),
        deviceSharedStorageIOError(433),
        registerClientFailed(434),
        verifyRegistrationFailed(435),
        mountLocalFailed(436),
        mountPeerFailed(437),
        unmountLocalFailed(438),
        unmountPeerFailed(439),
        portFailed(440),
        unsupportedTransceiver(441),
        interfaceFailed(442),
        operationalStateDown(443),
        cmcVifDown(444),
        verifyGuidFailed(445),
        unregisterFailed(446),
        cleanOldDataFailed(447),
        requestFailed(448),
        verifyFailed(449),
        resolveAllFailed(450),
        suspendModeEntered(451),
        releaseFailed(452),
        resolveManyFailed(453),
        releaseManyFailed(454),
        releaseAllFailed(455),
        thresholdCrossed(456),
        waitForChassisMoReadyFailed(457),
        unsupported(458),
        checkFirmwareUpgradeStatusFailed(459),
        defaultInfraVersionMissing(460),
        defaultInfraBundleValidationFailed(461),
        defaultInfraBundleInstallAppFailure(464),
        any(-1)
    }

CfprApConditionCode ::= TEXTUAL-CONVENTION
    STATUS        current
    DESCRIPTION
        ""
    SYNTAX        INTEGER
    {
        generic(0),
        f0019(19),
        f0021(21),
        f0056(56),
        f0057(57),
        f0058(58),
        f0059(59),
        f0060(60),
        f0061(61),
        f0062(62),
        f0063(63),
        f0064(64),
        f0065(65),
        f0066(66),
        f0067(67),
        f0068(68),
        f0069(69),
        f0070(70),
        f0071(71),
        f0072(72),
        f0073(73),
        f0074(74),
        f0075(75),
        f0076(76),
        f0077(77),
        f0078(78),
        f0079(79),
        f0080(80),
        f0081(81),
        f0082(82),
        f0083(83),
        f0084(84),
        f0085(85),
        f0086(86),
        f0087(87),
        f0088(88),
        f0089(89),
        f0090(90),
        f0095(95),
        f0096(96),
        f0097(97),
        f0098(98),
        f0099(99),
        f0100(100),
        f0101(101),
        f0149(149),
        f0150(150),
        f0151(151),
        f0152(152),
        f0153(153),
        f0154(154),
        f0155(155),
        f0156(156),
        f0157(157),
        f0158(158),
        f0159(159),
        f0160(160),
        f0161(161),
        f0162(162),
        f0163(163),
        f0185(185),
        f0186(186),
        f0187(187),
        f0188(188),
        f0189(189),
        f0190(190),
        f0191(191),
        f0192(192),
        f0193(193),
        f0194(194),
        f0195(195),
        f0196(196),
        f0197(197),
        f0198(198),
        f0199(199),
        f0200(200),
        f0299(299),
        f0300(300),
        f0314(314),
        f0315(315),
        f0316(316),
        f0317(317),
        f0318(318),
        f0319(319),
        f0320(320),
        f0321(321),
        f0322(322),
        f0323(323),
        f0324(324),
        f0325(325),
        f0326(326),
        f0332(332),
        f0335(335),
        f0349(349),
        f0350(350),
        f0351(351),
        f0352(352),
        f0353(353),
        f0354(354),
        f0355(355),
        f0356(356),
        f0357(357),
        f0358(358),
        f0359(359),
        f0369(369),
        f0370(370),
        f0371(371),
        f0372(372),
        f0373(373),
        f0374(374),
        f0375(375),
        f0376(376),
        f0377(377),
        f0378(378),
        f0379(379),
        f0380(380),
        f0381(381),
        f0657(657),
        f0658(658),
        f0659(659),
        f0660(660),
        f0661(661),
        f0662(662),
        f0663(663),
        f0664(664),
        f0665(665),
        f0666(666),
        f0667(667),
        f0668(668),
        f0669(669),
        f0675(675),
        f0687(687),
        f0688(688),
        f0689(689),
        f0690(690),
        f0691(691),
        f0692(692),
        f0693(693),
        f0694(694),
        f0695(695),
        f0696(696),
        f0697(697),
        f0698(698),
        f0699(699),
        f0700(700),
        f0701(701),
        f0702(702),
        f0703(703),
        f0704(704),
        f0705(705),
        f0706(706),
        f0707(707),
        f0708(708),
        f0709(709),
        f0710(710),
        f0711(711),
        f0712(712),
        f0713(713),
        f0714(714),
        f0715(715),
        f0716(716),
        f0717(717),
        f0718(718),
        f0719(719),
        f0720(720),
        f0721(721),
        f0722(722),
        f0723(723),
        f0724(724),
        f0725(725),
        f0726(726),
        f0727(727),
        f0728(728),
        f0729(729),
        f0730(730),
        f0731(731),
        f0732(732),
        f0733(733),
        f0734(734),
        f0735(735),
        f0736(736),
        f0737(737),
        f0738(738),
        f0739(739),
        f0740(740),
        f0741(741),
        f0742(742),
        f0743(743),
        f0744(744),
        f0745(745),
        f0746(746),
        f0747(747),
        f0748(748),
        f0749(749),
        f0750(750),
        f0751(751),
        f0752(752),
        f0753(753),
        f0754(754),
        f0755(755),
        f0756(756),
        f0757(757),
        f0758(758),
        f0759(759),
        f0760(760),
        f0792(792),
        f0793(793),
        f0794(794),
        f0795(795),
        f0796(796),
        f0797(797),
        f0798(798),
        f0799(799),
        f0800(800),
        f0809(809),
        f0810(810),
        f0811(811),
        f0812(812),
        f0813(813),
        f0814(814),
        f0815(815),
        f0816(816),
        f0817(817),
        f0818(818),
        f0819(819),
        f0820(820),
        f0821(821),
        f0822(822),
        f0823(823),
        f0824(824),
        f0825(825),
        f0826(826),
        f0827(827),
        f0828(828),
        f0829(829),
        f0830(830),
        f0831(831),
        f0832(832),
        f0833(833),
        f0834(834),
        f0835(835),
        f0836(836),
        f0837(837),
        f0838(838),
        f0839(839),
        f0844(844),
        f0850(850),
        f0851(851),
        f0852(852),
        f0853(853),
        f0854(854),
        f0855(855),
        f0856(856),
        f0857(857),
        f0858(858),
        f0859(859),
        f0860(860),
        f0861(861),
        f0862(862),
        f0863(863),
        f0864(864),
        f0865(865),
        f0866(866),
        f0871(871),
        f0872(872),
        f0899(899),
        f0900(900),
        f0901(901),
        f0902(902),
        f0903(903),
        f0904(904),
        f0905(905),
        f0906(906),
        f0907(907),
        f0964(964),
        f0965(965),
        f0966(966),
        f0967(967),
        f0977(977),
        f0978(978),
        f0979(979),
        f0980(980),
        f0981(981),
        f0982(982),
        f0983(983),
        f0984(984),
        f0985(985),
        f0986(986),
        f0987(987),
        f0996(996),
        f0997(997),
        f1014(1014),
        f1020(1020),
        f1038(1038),
        f1039(1039),
        f1040(1040),
        f1041(1041),
        f1042(1042),
        f1043(1043),
        f1044(1044),
        f1045(1045),
        f1046(1046),
        f1047(1047),
        f1048(1048),
        f1049(1049),
        f1050(1050),
        f1051(1051),
        f1052(1052),
        f1053(1053),
        f1054(1054),
        f1055(1055),
        f1056(1056),
        f1057(1057),
        f1058(1058),
        f1059(1059),
        f1060(1060),
        f1061(1061),
        f1062(1062),
        f1115(1115),
        f1116(1116),
        f1117(1117),
        f1118(1118),
        f1119(1119),
        f1120(1120),
        f1121(1121),
        f1122(1122),
        f1123(1123),
        f1124(1124),
        f1125(1125),
        f1126(1126),
        f1127(1127),
        f1128(1128),
        f1129(1129),
        f1130(1130),
        f1131(1131),
        f1132(1132),
        f1133(1133),
        f1134(1134),
        f1135(1135),
        f1136(1136),
        f1137(1137),
        f1138(1138),
        f1139(1139),
        f1140(1140),
        f1141(1141),
        f1150(1150),
        f1151(1151),
        f1152(1152),
        f1153(1153),
        f1154(1154),
        f1155(1155),
        f1156(1156),
        f1157(1157),
        f1158(1158),
        f1159(1159),
        f1174(1174),
        f1308(1308),
        f1309(1309),
        f1310(1310),
        f1311(1311),
        f1312(1312),
        f1313(1313),
        f16476(16476),
        f16477(16477),
        f16517(16517),
        f16518(16518),
        f16519(16519),
        f16520(16520),
        f16521(16521),
        f16522(16522),
        f16523(16523),
        f16524(16524),
        f16525(16525),
        f16526(16526),
        f16528(16528),
        f16529(16529),
        f16530(16530),
        f16585(16585),
        f16586(16586),
        f16587(16587),
        f16588(16588),
        f16589(16589),
        f16667(16667),
        f16668(16668),
        f16669(16669),
        f16670(16670),
        f16671(16671),
        f16676(16676),
        f16681(16681),
        f16682(16682),
        f16718(16718),
        f16727(16727),
        f16730(16730),
        f16731(16731),
        f16748(16748),
        f16749(16749),
        f16750(16750),
        f16751(16751),
        f16752(16752),
        f16770(16770),
        f16780(16780),
        f16803(16803),
        f16804(16804),
        f16805(16805),
        f16806(16806),
        f16807(16807),
        f16815(16815),
        f16816(16816),
        f16817(16817),
        f16818(16818),
        f16819(16819),
        f16822(16822),
        f16823(16823),
        f17063(17063),
        f17064(17064),
        f17065(17065),
        f17066(17066),
        f17149(17149),
        f17151(17151),
        f17152(17152),
        f17153(17153),
        f17154(17154),
        f17155(17155),
        f17156(17156),
        f17157(17157),
        f17158(17158),
        f17159(17159),
        f17160(17160),
        f17161(17161),
        f17162(17162),
        f17163(17163),
        f17164(17164),
        f17165(17165),
        f17166(17166),
        f17167(17167),
        f17169(17169),
        f17170(17170),
        f17185(17185),
        f17186(17186),
        f17187(17187),
        f17224(17224),
        f17226(17226),
        f17227(17227),
        f17231(17231),
        f17232(17232),
        f17233(17233),
        f17251(17251),
        f17252(17252),
        f17253(17253),
        f17254(17254),
        f17265(17265),
        f17266(17266),
        f17267(17267),
        f17268(17268),
        f17269(17269),
        f17270(17270),
        f17271(17271),
        f17272(17272),
        f17336(17336),
        f17337(17337),
        f17340(17340),
        f17347(17347),
        f17358(17358),
        f17359(17359),
        f17360(17360),
        f17373(17373),
        f17374(17374),
        f17378(17378),
        f17403(17403),
        f17408(17408),
        f17409(17409),
        f17410(17410),
        f17411(17411),
        f17420(17420),
        f17421(17421),
        f17469(17469),
        f17470(17470),
        f17476(17476),
        f17477(17477),
        f17478(17478),
        f17484(17484),
        f17490(17490),
        f17491(17491),
        f17492(17492),
        f17493(17493),
        f17494(17494),
        f17495(17495),
        f17496(17496),
        f17497(17497),
        f17498(17498),
        f17531(17531),
        f17532(17532),
        f17533(17533),
        f17554(17554),
        f17555(17555),
        f17556(17556),
        f17559(17559),
        f17560(17560),
        f17561(17561),
        f17562(17562),
        f17563(17563),
        f17564(17564),
        f17565(17565),
        f17566(17566),
        f17567(17567),
        f17568(17568),
        f17569(17569),
        f17570(17570),
        f17571(17571),
        f17572(17572),
        f17573(17573),
        f17690(17690),
        f34261(34261),
        f34263(34263),
        f34264(34264),
        f34265(34265),
        f34269(34269),
        f34271(34271),
        f34272(34272),
        f34273(34273),
        f34277(34277),
        f34279(34279),
        f34280(34280),
        f34281(34281),
        f34287(34287),
        f34289(34289),
        f34290(34290),
        f34291(34291),
        f34295(34295),
        f34297(34297),
        f34298(34298),
        f34299(34299),
        f34303(34303),
        f34305(34305),
        f34306(34306),
        f34307(34307),
        f34311(34311),
        f34313(34313),
        f34314(34314),
        f34315(34315),
        f34321(34321),
        f34323(34323),
        f34324(34324),
        f34325(34325),
        f34329(34329),
        f34331(34331),
        f34332(34332),
        f34333(34333),
        f34337(34337),
        f34339(34339),
        f34340(34340),
        f34341(34341),
        f34345(34345),
        f34347(34347),
        f34348(34348),
        f34349(34349),
        f34353(34353),
        f34355(34355),
        f34356(34356),
        f34357(34357),
        f34363(34363),
        f34365(34365),
        f34366(34366),
        f34367(34367),
        f34372(34372),
        f34383(34383),
        f34395(34395),
        f34406(34406),
        f34417(34417),
        f34428(34428),
        f34440(34440),
        f34451(34451),
        f34462(34462),
        f34474(34474),
        f34485(34485),
        f34496(34496),
        f34507(34507),
        f34841(34841),
        f34843(34843),
        f34844(34844),
        f34845(34845),
        f35108(35108),
        f35110(35110),
        f35111(35111),
        f35112(35112),
        f35116(35116),
        f35118(35118),
        f35119(35119),
        f35120(35120),
        f35124(35124),
        f35126(35126),
        f35127(35127),
        f35128(35128),
        f35132(35132),
        f35134(35134),
        f35135(35135),
        f35136(35136),
        f35140(35140),
        f35142(35142),
        f35143(35143),
        f35144(35144),
        f35148(35148),
        f35150(35150),
        f35151(35151),
        f35152(35152),
        f35156(35156),
        f35158(35158),
        f35159(35159),
        f35160(35160),
        f35164(35164),
        f35166(35166),
        f35167(35167),
        f35168(35168),
        f35174(35174),
        f35176(35176),
        f35177(35177),
        f35178(35178),
        f35182(35182),
        f35184(35184),
        f35185(35185),
        f35186(35186),
        f35190(35190),
        f35192(35192),
        f35193(35193),
        f35194(35194),
        f35200(35200),
        f35202(35202),
        f35203(35203),
        f35204(35204),
        f35208(35208),
        f35210(35210),
        f35211(35211),
        f35212(35212),
        f35216(35216),
        f35218(35218),
        f35219(35219),
        f35220(35220),
        f35844(35844),
        f35845(35845),
        f35846(35846),
        f35847(35847),
        f35854(35854),
        f35855(35855),
        f35856(35856),
        f35857(35857),
        f35864(35864),
        f35865(35865),
        f35866(35866),
        f35867(35867),
        f35874(35874),
        f35875(35875),
        f35876(35876),
        f35877(35877),
        f35884(35884),
        f35885(35885),
        f35886(35886),
        f35887(35887),
        f35894(35894),
        f35895(35895),
        f35896(35896),
        f35897(35897),
        f35907(35907),
        f35908(35908),
        f35909(35909),
        f35910(35910),
        f35917(35917),
        f35918(35918),
        f35919(35919),
        f35920(35920),
        f35927(35927),
        f35928(35928),
        f35929(35929),
        f35930(35930),
        f35937(35937),
        f35938(35938),
        f35939(35939),
        f35940(35940),
        f35947(35947),
        f35948(35948),
        f35949(35949),
        f35950(35950),
        f35957(35957),
        f35958(35958),
        f35959(35959),
        f35960(35960),
        f35970(35970),
        f35971(35971),
        f35972(35972),
        f35973(35973),
        f35980(35980),
        f35981(35981),
        f35982(35982),
        f35983(35983),
        f35990(35990),
        f35991(35991),
        f35992(35992),
        f35993(35993),
        f36000(36000),
        f36001(36001),
        f36002(36002),
        f36003(36003),
        f36010(36010),
        f36011(36011),
        f36012(36012),
        f36013(36013),
        f36020(36020),
        f36021(36021),
        f36022(36022),
        f36023(36023),
        f36030(36030),
        f36031(36031),
        f36032(36032),
        f36033(36033),
        f36043(36043),
        f36044(36044),
        f36045(36045),
        f36046(36046),
        f36053(36053),
        f36054(36054),
        f36055(36055),
        f36056(36056),
        f36063(36063),
        f36064(36064),
        f36065(36065),
        f36066(36066),
        f36073(36073),
        f36074(36074),
        f36075(36075),
        f36076(36076),
        f36083(36083),
        f36084(36084),
        f36085(36085),
        f36086(36086),
        f36096(36096),
        f36097(36097),
        f36098(36098),
        f36099(36099),
        f36106(36106),
        f36107(36107),
        f36108(36108),
        f36109(36109),
        f36116(36116),
        f36117(36117),
        f36118(36118),
        f36119(36119),
        f36129(36129),
        f36130(36130),
        f36131(36131),
        f36132(36132),
        f36139(36139),
        f36140(36140),
        f36141(36141),
        f36142(36142),
        f36149(36149),
        f36150(36150),
        f36151(36151),
        f36152(36152),
        f36161(36161),
        f36162(36162),
        f36163(36163),
        f36164(36164),
        f36171(36171),
        f36172(36172),
        f36173(36173),
        f36174(36174),
        f36181(36181),
        f36182(36182),
        f36183(36183),
        f36184(36184),
        f36191(36191),
        f36192(36192),
        f36193(36193),
        f36194(36194),
        f36203(36203),
        f36204(36204),
        f36205(36205),
        f36206(36206),
        f36213(36213),
        f36214(36214),
        f36215(36215),
        f36216(36216),
        f36223(36223),
        f36224(36224),
        f36225(36225),
        f36226(36226),
        f36233(36233),
        f36234(36234),
        f36235(36235),
        f36236(36236),
        f36243(36243),
        f36244(36244),
        f36245(36245),
        f36246(36246),
        f36253(36253),
        f36254(36254),
        f36255(36255),
        f36256(36256),
        f36263(36263),
        f36264(36264),
        f36265(36265),
        f36266(36266),
        f36273(36273),
        f36274(36274),
        f36275(36275),
        f36276(36276),
        f36285(36285),
        f36286(36286),
        f36287(36287),
        f36288(36288),
        f36295(36295),
        f36296(36296),
        f36297(36297),
        f36298(36298),
        f36305(36305),
        f36306(36306),
        f36307(36307),
        f36308(36308),
        f36315(36315),
        f36316(36316),
        f36317(36317),
        f36318(36318),
        f36325(36325),
        f36326(36326),
        f36327(36327),
        f36328(36328),
        f36337(36337),
        f36338(36338),
        f36339(36339),
        f36340(36340),
        f36347(36347),
        f36348(36348),
        f36349(36349),
        f36350(36350),
        f36360(36360),
        f36361(36361),
        f36362(36362),
        f36363(36363),
        f36370(36370),
        f36371(36371),
        f36372(36372),
        f36373(36373),
        f36380(36380),
        f36381(36381),
        f36382(36382),
        f36383(36383),
        f36390(36390),
        f36391(36391),
        f36392(36392),
        f36393(36393),
        f36403(36403),
        f36404(36404),
        f36405(36405),
        f36406(36406),
        f36413(36413),
        f36414(36414),
        f36415(36415),
        f36416(36416),
        f36423(36423),
        f36424(36424),
        f36425(36425),
        f36426(36426),
        f36433(36433),
        f36434(36434),
        f36435(36435),
        f36436(36436),
        f36446(36446),
        f36447(36447),
        f36448(36448),
        f36449(36449),
        f36456(36456),
        f36457(36457),
        f36458(36458),
        f36459(36459),
        f36466(36466),
        f36467(36467),
        f36468(36468),
        f36469(36469),
        f36479(36479),
        f36480(36480),
        f36481(36481),
        f36482(36482),
        f36489(36489),
        f36490(36490),
        f36491(36491),
        f36492(36492),
        f36499(36499),
        f36500(36500),
        f36501(36501),
        f36502(36502),
        f36509(36509),
        f36510(36510),
        f36511(36511),
        f36512(36512),
        f36519(36519),
        f36520(36520),
        f36521(36521),
        f36522(36522),
        f36532(36532),
        f36533(36533),
        f36534(36534),
        f36535(36535),
        f36542(36542),
        f36543(36543),
        f36544(36544),
        f36545(36545),
        f36552(36552),
        f36553(36553),
        f36554(36554),
        f36555(36555),
        f36562(36562),
        f36563(36563),
        f36564(36564),
        f36565(36565),
        f36575(36575),
        f36576(36576),
        f36577(36577),
        f36578(36578),
        f36585(36585),
        f36586(36586),
        f36587(36587),
        f36588(36588),
        f36595(36595),
        f36596(36596),
        f36597(36597),
        f36598(36598),
        f36605(36605),
        f36606(36606),
        f36607(36607),
        f36608(36608),
        f36619(36619),
        f36620(36620),
        f36621(36621),
        f36622(36622),
        f36629(36629),
        f36630(36630),
        f36631(36631),
        f36632(36632),
        f36639(36639),
        f36640(36640),
        f36641(36641),
        f36642(36642),
        f36649(36649),
        f36650(36650),
        f36651(36651),
        f36652(36652),
        f36663(36663),
        f36664(36664),
        f36665(36665),
        f36666(36666),
        f36673(36673),
        f36674(36674),
        f36675(36675),
        f36676(36676),
        f36683(36683),
        f36684(36684),
        f36685(36685),
        f36686(36686),
        f36693(36693),
        f36694(36694),
        f36695(36695),
        f36696(36696),
        f36706(36706),
        f36707(36707),
        f36708(36708),
        f36709(36709),
        f36716(36716),
        f36717(36717),
        f36718(36718),
        f36719(36719),
        f36726(36726),
        f36727(36727),
        f36728(36728),
        f36729(36729),
        f36736(36736),
        f36737(36737),
        f36738(36738),
        f36739(36739),
        f36746(36746),
        f36747(36747),
        f36748(36748),
        f36749(36749),
        f36759(36759),
        f36760(36760),
        f36761(36761),
        f36762(36762),
        f36769(36769),
        f36770(36770),
        f36771(36771),
        f36772(36772),
        f36779(36779),
        f36780(36780),
        f36781(36781),
        f36782(36782),
        f36789(36789),
        f36790(36790),
        f36791(36791),
        f36792(36792),
        f36802(36802),
        f36803(36803),
        f36804(36804),
        f36805(36805),
        f36812(36812),
        f36813(36813),
        f36814(36814),
        f36815(36815),
        f36822(36822),
        f36823(36823),
        f36824(36824),
        f36825(36825),
        f36832(36832),
        f36833(36833),
        f36834(36834),
        f36835(36835),
        f36845(36845),
        f36846(36846),
        f36847(36847),
        f36848(36848),
        f36855(36855),
        f36856(36856),
        f36857(36857),
        f36858(36858),
        f36865(36865),
        f36866(36866),
        f36867(36867),
        f36868(36868),
        f36875(36875),
        f36876(36876),
        f36877(36877),
        f36878(36878),
        f36887(36887),
        f36888(36888),
        f36889(36889),
        f36890(36890),
        f36897(36897),
        f36898(36898),
        f36899(36899),
        f36900(36900),
        f36907(36907),
        f36908(36908),
        f36909(36909),
        f36910(36910),
        f36917(36917),
        f36918(36918),
        f36919(36919),
        f36920(36920),
        f36927(36927),
        f36928(36928),
        f36929(36929),
        f36930(36930),
        f36937(36937),
        f36938(36938),
        f36939(36939),
        f36940(36940),
        f36947(36947),
        f36948(36948),
        f36949(36949),
        f36950(36950),
        f36957(36957),
        f36958(36958),
        f36959(36959),
        f36960(36960),
        f36969(36969),
        f36970(36970),
        f36971(36971),
        f36972(36972),
        f36979(36979),
        f36980(36980),
        f36981(36981),
        f36982(36982),
        f36989(36989),
        f36990(36990),
        f36991(36991),
        f36992(36992),
        f36999(36999),
        f37000(37000),
        f37001(37001),
        f37002(37002),
        f37011(37011),
        f37012(37012),
        f37013(37013),
        f37014(37014),
        f37021(37021),
        f37022(37022),
        f37023(37023),
        f37024(37024),
        f37031(37031),
        f37032(37032),
        f37033(37033),
        f37034(37034),
        f37041(37041),
        f37042(37042),
        f37043(37043),
        f37044(37044),
        f37051(37051),
        f37052(37052),
        f37053(37053),
        f37054(37054),
        f37061(37061),
        f37062(37062),
        f37063(37063),
        f37064(37064),
        f37071(37071),
        f37072(37072),
        f37073(37073),
        f37074(37074),
        f37081(37081),
        f37082(37082),
        f37083(37083),
        f37084(37084),
        f37200(37200),
        f37202(37202),
        f37203(37203),
        f37204(37204),
        f37208(37208),
        f37210(37210),
        f37211(37211),
        f37212(37212),
        f37216(37216),
        f37218(37218),
        f37219(37219),
        f37220(37220),
        f37226(37226),
        f37228(37228),
        f37229(37229),
        f37230(37230),
        f37236(37236),
        f37238(37238),
        f37239(37239),
        f37240(37240),
        f37246(37246),
        f37248(37248),
        f37249(37249),
        f37250(37250),
        f37255(37255),
        f37266(37266),
        f37277(37277),
        f37288(37288),
        f37879(37879),
        f37881(37881),
        f37882(37882),
        f37883(37883),
        f37887(37887),
        f37889(37889),
        f37890(37890),
        f37891(37891),
        f37895(37895),
        f37897(37897),
        f37898(37898),
        f37899(37899),
        f37903(37903),
        f37905(37905),
        f37906(37906),
        f37907(37907),
        f37911(37911),
        f37913(37913),
        f37914(37914),
        f37915(37915),
        f37919(37919),
        f37921(37921),
        f37922(37922),
        f37923(37923),
        f37929(37929),
        f37931(37931),
        f37932(37932),
        f37933(37933),
        f37937(37937),
        f37939(37939),
        f37940(37940),
        f37941(37941),
        f37945(37945),
        f37947(37947),
        f37948(37948),
        f37949(37949),
        f37953(37953),
        f37955(37955),
        f37956(37956),
        f37957(37957),
        f37963(37963),
        f37965(37965),
        f37966(37966),
        f37967(37967),
        f37971(37971),
        f37973(37973),
        f37974(37974),
        f37975(37975),
        f37979(37979),
        f37981(37981),
        f37982(37982),
        f37983(37983),
        f37987(37987),
        f37989(37989),
        f37990(37990),
        f37991(37991),
        f37995(37995),
        f37997(37997),
        f37998(37998),
        f37999(37999),
        f38003(38003),
        f38005(38005),
        f38006(38006),
        f38007(38007),
        f38014(38014),
        f38016(38016),
        f38017(38017),
        f38018(38018),
        f38022(38022),
        f38024(38024),
        f38025(38025),
        f38026(38026),
        f38030(38030),
        f38032(38032),
        f38033(38033),
        f38034(38034),
        f38040(38040),
        f38042(38042),
        f38043(38043),
        f38044(38044),
        f38048(38048),
        f38050(38050),
        f38051(38051),
        f38052(38052),
        f38056(38056),
        f38058(38058),
        f38059(38059),
        f38060(38060),
        f38067(38067),
        f38069(38069),
        f38070(38070),
        f38071(38071),
        f38075(38075),
        f38077(38077),
        f38078(38078),
        f38079(38079),
        f38083(38083),
        f38085(38085),
        f38086(38086),
        f38087(38087),
        f38094(38094),
        f38096(38096),
        f38097(38097),
        f38098(38098),
        f38104(38104),
        f38106(38106),
        f38107(38107),
        f38108(38108),
        f38114(38114),
        f38116(38116),
        f38117(38117),
        f38118(38118),
        f38122(38122),
        f38124(38124),
        f38125(38125),
        f38126(38126),
        f38130(38130),
        f38132(38132),
        f38133(38133),
        f38134(38134),
        f38138(38138),
        f38140(38140),
        f38141(38141),
        f38142(38142),
        f38146(38146),
        f38148(38148),
        f38149(38149),
        f38150(38150),
        f38157(38157),
        f38159(38159),
        f38160(38160),
        f38161(38161),
        f38165(38165),
        f38167(38167),
        f38168(38168),
        f38169(38169),
        f38173(38173),
        f38175(38175),
        f38176(38176),
        f38177(38177),
        f38181(38181),
        f38183(38183),
        f38184(38184),
        f38185(38185),
        f38191(38191),
        f38193(38193),
        f38194(38194),
        f38195(38195),
        f38199(38199),
        f38201(38201),
        f38202(38202),
        f38203(38203),
        f38207(38207),
        f38209(38209),
        f38210(38210),
        f38211(38211),
        f38218(38218),
        f38220(38220),
        f38221(38221),
        f38222(38222),
        f38226(38226),
        f38228(38228),
        f38229(38229),
        f38230(38230),
        f38234(38234),
        f38236(38236),
        f38237(38237),
        f38238(38238),
        f38242(38242),
        f38244(38244),
        f38245(38245),
        f38246(38246),
        f38250(38250),
        f38252(38252),
        f38253(38253),
        f38254(38254),
        f38258(38258),
        f38260(38260),
        f38261(38261),
        f38262(38262),
        f38268(38268),
        f38270(38270),
        f38271(38271),
        f38272(38272),
        f38276(38276),
        f38278(38278),
        f38279(38279),
        f38280(38280),
        f38287(38287),
        f38289(38289),
        f38290(38290),
        f38291(38291),
        f38506(38506),
        f38507(38507),
        f38508(38508),
        f38509(38509),
        f38516(38516),
        f38517(38517),
        f38518(38518),
        f38519(38519),
        f38526(38526),
        f38527(38527),
        f38528(38528),
        f38529(38529),
        f38536(38536),
        f38537(38537),
        f38538(38538),
        f38539(38539),
        f38546(38546),
        f38547(38547),
        f38548(38548),
        f38549(38549),
        f38556(38556),
        f38557(38557),
        f38558(38558),
        f38559(38559),
        f38568(38568),
        f38569(38569),
        f38570(38570),
        f38571(38571),
        f38578(38578),
        f38579(38579),
        f38580(38580),
        f38581(38581),
        f38588(38588),
        f38589(38589),
        f38590(38590),
        f38591(38591),
        f38598(38598),
        f38599(38599),
        f38600(38600),
        f38601(38601),
        f38608(38608),
        f38609(38609),
        f38610(38610),
        f38611(38611),
        f38618(38618),
        f38619(38619),
        f38620(38620),
        f38621(38621),
        f38630(38630),
        f38631(38631),
        f38632(38632),
        f38633(38633),
        f38640(38640),
        f38641(38641),
        f38642(38642),
        f38643(38643),
        f38650(38650),
        f38651(38651),
        f38652(38652),
        f38653(38653),
        f38660(38660),
        f38661(38661),
        f38662(38662),
        f38663(38663),
        f38670(38670),
        f38671(38671),
        f38672(38672),
        f38673(38673),
        f38680(38680),
        f38681(38681),
        f38682(38682),
        f38683(38683),
        f38690(38690),
        f38691(38691),
        f38692(38692),
        f38693(38693),
        f38700(38700),
        f38701(38701),
        f38702(38702),
        f38703(38703),
        f38710(38710),
        f38711(38711),
        f38712(38712),
        f38713(38713),
        f38722(38722),
        f38723(38723),
        f38724(38724),
        f38725(38725),
        f38732(38732),
        f38733(38733),
        f38734(38734),
        f38735(38735),
        f38742(38742),
        f38743(38743),
        f38744(38744),
        f38745(38745),
        f38752(38752),
        f38753(38753),
        f38754(38754),
        f38755(38755),
        f38762(38762),
        f38763(38763),
        f38764(38764),
        f38765(38765),
        f38774(38774),
        f38775(38775),
        f38776(38776),
        f38777(38777),
        f38784(38784),
        f38785(38785),
        f38786(38786),
        f38787(38787),
        f38794(38794),
        f38795(38795),
        f38796(38796),
        f38797(38797),
        f38804(38804),
        f38805(38805),
        f38806(38806),
        f38807(38807),
        f38814(38814),
        f38815(38815),
        f38816(38816),
        f38817(38817),
        f38824(38824),
        f38825(38825),
        f38826(38826),
        f38827(38827),
        f38834(38834),
        f38835(38835),
        f38836(38836),
        f38837(38837),
        f38844(38844),
        f38845(38845),
        f38846(38846),
        f38847(38847),
        f38856(38856),
        f38857(38857),
        f38858(38858),
        f38859(38859),
        f38866(38866),
        f38867(38867),
        f38868(38868),
        f38869(38869),
        f38876(38876),
        f38877(38877),
        f38878(38878),
        f38879(38879),
        f38888(38888),
        f38889(38889),
        f38890(38890),
        f38891(38891),
        f38898(38898),
        f38899(38899),
        f38900(38900),
        f38901(38901),
        f38908(38908),
        f38909(38909),
        f38910(38910),
        f38911(38911),
        f38918(38918),
        f38919(38919),
        f38920(38920),
        f38921(38921),
        f38928(38928),
        f38929(38929),
        f38930(38930),
        f38931(38931),
        f38938(38938),
        f38939(38939),
        f38940(38940),
        f38941(38941),
        f38948(38948),
        f38949(38949),
        f38950(38950),
        f38951(38951),
        f38958(38958),
        f38959(38959),
        f38960(38960),
        f38961(38961),
        f39841(39841),
        f39843(39843),
        f39844(39844),
        f39845(39845),
        f39852(39852),
        f39854(39854),
        f39855(39855),
        f39856(39856),
        f39860(39860),
        f39862(39862),
        f39863(39863),
        f39864(39864),
        f39869(39869),
        f39880(39880),
        f39891(39891),
        f39902(39902),
        f39913(39913),
        f40569(40569),
        f40570(40570),
        f40571(40571),
        f40572(40572),
        f40579(40579),
        f40580(40580),
        f40581(40581),
        f40582(40582),
        f40589(40589),
        f40590(40590),
        f40591(40591),
        f40592(40592),
        f40599(40599),
        f40600(40600),
        f40601(40601),
        f40602(40602),
        f40611(40611),
        f40612(40612),
        f40613(40613),
        f40614(40614),
        f40621(40621),
        f40622(40622),
        f40623(40623),
        f40624(40624),
        f40631(40631),
        f40632(40632),
        f40633(40633),
        f40634(40634),
        f40641(40641),
        f40642(40642),
        f40643(40643),
        f40644(40644),
        f40651(40651),
        f40652(40652),
        f40653(40653),
        f40654(40654),
        f40661(40661),
        f40662(40662),
        f40663(40663),
        f40664(40664),
        f40671(40671),
        f40672(40672),
        f40673(40673),
        f40674(40674),
        f40681(40681),
        f40682(40682),
        f40683(40683),
        f40684(40684),
        f40691(40691),
        f40692(40692),
        f40693(40693),
        f40694(40694),
        f40701(40701),
        f40702(40702),
        f40703(40703),
        f40704(40704),
        f42989(42989),
        f42991(42991),
        f42992(42992),
        f42993(42993),
        f77916(77916),
        f77917(77917),
        f77957(77957),
        f77958(77958),
        f77959(77959),
        f77960(77960),
        f77961(77961),
        f77962(77962),
        f77963(77963),
        f77964(77964),
        f77965(77965),
        f77966(77966),
        f77968(77968),
        f77969(77969),
        f77970(77970),
        f78025(78025),
        f78026(78026),
        f78027(78027),
        f78028(78028),
        f78029(78029),
        f78107(78107),
        f78108(78108),
        f78109(78109),
        f78110(78110),
        f78111(78111),
        f78116(78116),
        f78121(78121),
        f78122(78122),
        f78158(78158),
        f78167(78167),
        f78170(78170),
        f78171(78171),
        f78188(78188),
        f78189(78189),
        f78190(78190),
        f78191(78191),
        f78192(78192),
        f78210(78210),
        f78220(78220),
        f78243(78243),
        f78244(78244),
        f78245(78245),
        f78246(78246),
        f78247(78247),
        f78255(78255),
        f78256(78256),
        f78257(78257),
        f78258(78258),
        f78259(78259),
        f78262(78262),
        f78263(78263),
        f78503(78503),
        f78504(78504),
        f78505(78505),
        f78506(78506),
        f78589(78589),
        f78591(78591),
        f78592(78592),
        f78593(78593),
        f78594(78594),
        f78595(78595),
        f78596(78596),
        f78597(78597),
        f78598(78598),
        f78599(78599),
        f78600(78600),
        f78601(78601),
        f78602(78602),
        f78603(78603),
        f78604(78604),
        f78605(78605),
        f78606(78606),
        f78607(78607),
        f78609(78609),
        f78610(78610),
        f78625(78625),
        f78626(78626),
        f78627(78627),
        f78664(78664),
        f78666(78666),
        f78667(78667),
        f78671(78671),
        f78672(78672),
        f78673(78673),
        f78691(78691),
        f78692(78692),
        f78693(78693),
        f78694(78694),
        f78705(78705),
        f78706(78706),
        f78707(78707),
        f78708(78708),
        f78709(78709),
        f78710(78710),
        f78711(78711),
        f78712(78712),
        f78776(78776),
        f78777(78777),
        f78780(78780),
        f78787(78787),
        f78798(78798),
        f78799(78799),
        f78800(78800),
        f78813(78813),
        f78814(78814),
        f78818(78818),
        f78843(78843),
        f78848(78848),
        f78849(78849),
        f78850(78850),
        f78851(78851),
        f78860(78860),
        f78861(78861),
        f78909(78909),
        f78910(78910),
        f78916(78916),
        f78917(78917),
        f78918(78918),
        f78924(78924),
        f78930(78930),
        f78931(78931),
        f78932(78932),
        f78933(78933),
        f78934(78934),
        f78935(78935),
        f78936(78936),
        f78937(78937),
        f78938(78938),
        f78971(78971),
        f78972(78972),
        f78973(78973),
        f78994(78994),
        f78995(78995),
        f78996(78996),
        f78999(78999),
        f79000(79000),
        f79001(79001),
        f79002(79002),
        f79003(79003),
        f79004(79004),
        f79005(79005),
        f79006(79006),
        f79007(79007),
        f79008(79008),
        f79009(79009),
        f79010(79010),
        f79011(79011),
        f79012(79012),
        f79013(79013),
        f79130(79130),
        f999516(999516),
        f999517(999517),
        f999557(999557),
        f999558(999558),
        f999559(999559),
        f999560(999560),
        f999561(999561),
        f999562(999562),
        f999563(999563),
        f999564(999564),
        f999565(999565),
        f999566(999566),
        f999568(999568),
        f999569(999569),
        f999570(999570),
        f999625(999625),
        f999626(999626),
        f999627(999627),
        f999628(999628),
        f999629(999629),
        f999707(999707),
        f999708(999708),
        f999709(999709),
        f999710(999710),
        f999711(999711),
        f999716(999716),
        f999721(999721),
        f999722(999722),
        f999758(999758),
        f999767(999767),
        f999770(999770),
        f999771(999771),
        f999788(999788),
        f999789(999789),
        f999790(999790),
        f999791(999791),
        f999792(999792),
        f999810(999810),
        f999820(999820),
        f999843(999843),
        f999844(999844),
        f999845(999845),
        f999846(999846),
        f999847(999847),
        f999855(999855),
        f999856(999856),
        f999857(999857),
        f999858(999858),
        f999859(999859),
        f999862(999862),
        f999863(999863),
        f1000103(1000103),
        f1000104(1000104),
        f1000105(1000105),
        f1000106(1000106),
        f1000189(1000189),
        f1000191(1000191),
        f1000192(1000192),
        f1000193(1000193),
        f1000194(1000194),
        f1000195(1000195),
        f1000196(1000196),
        f1000197(1000197),
        f1000198(1000198),
        f1000199(1000199),
        f1000200(1000200),
        f1000201(1000201),
        f1000202(1000202),
        f1000203(1000203),
        f1000204(1000204),
        f1000205(1000205),
        f1000206(1000206),
        f1000207(1000207),
        f1000209(1000209),
        f1000210(1000210),
        f1000225(1000225),
        f1000226(1000226),
        f1000227(1000227),
        f1000264(1000264),
        f1000266(1000266),
        f1000267(1000267),
        f1000271(1000271),
        f1000272(1000272),
        f1000273(1000273),
        f1000291(1000291),
        f1000292(1000292),
        f1000293(1000293),
        f1000294(1000294),
        f1000305(1000305),
        f1000306(1000306),
        f1000307(1000307),
        f1000308(1000308),
        f1000309(1000309),
        f1000310(1000310),
        f1000311(1000311),
        f1000312(1000312),
        f1000376(1000376),
        f1000377(1000377),
        f1000380(1000380),
        f1000387(1000387),
        f1000398(1000398),
        f1000399(1000399),
        f1000400(1000400),
        f1000413(1000413),
        f1000414(1000414),
        f1000418(1000418),
        f1000443(1000443),
        f1000448(1000448),
        f1000449(1000449),
        f1000450(1000450),
        f1000451(1000451),
        f1000460(1000460),
        f1000461(1000461),
        f1000509(1000509),
        f1000510(1000510),
        f1000516(1000516),
        f1000517(1000517),
        f1000518(1000518),
        f1000524(1000524),
        f1000530(1000530),
        f1000531(1000531),
        f1000532(1000532),
        f1000533(1000533),
        f1000534(1000534),
        f1000535(1000535),
        f1000536(1000536),
        f1000537(1000537),
        f1000538(1000538),
        f1000571(1000571),
        f1000572(1000572),
        f1000573(1000573),
        f1000594(1000594),
        f1000595(1000595),
        f1000596(1000596),
        f1000599(1000599),
        f1000600(1000600),
        f1000601(1000601),
        f1000602(1000602),
        f1000603(1000603),
        f1000604(1000604),
        f1000605(1000605),
        f1000606(1000606),
        f1000607(1000607),
        f1000608(1000608),
        f1000609(1000609),
        f1000610(1000610),
        f1000611(1000611),
        f1000612(1000612),
        f1000613(1000613),
        f1000730(1000730),
        e4194305(4194305),
        e4194306(4194306),
        e4194307(4194307),
        e4194308(4194308),
        e4194309(4194309),
        e4194310(4194310),
        e4194311(4194311),
        e4194312(4194312),
        e4194313(4194313),
        e4194314(4194314),
        e4194315(4194315),
        e4194316(4194316),
        e4194317(4194317),
        e4194318(4194318),
        e4194319(4194319),
        e4194320(4194320),
        e4194321(4194321),
        e4194322(4194322),
        e4194323(4194323),
        e4194324(4194324),
        e4194325(4194325),
        e4194326(4194326),
        e4194327(4194327),
        e4194328(4194328),
        e4194329(4194329),
        e4194330(4194330),
        e4194331(4194331),
        e4194332(4194332),
        e4194333(4194333),
        e4194334(4194334),
        e4194335(4194335),
        e4194336(4194336),
        e4194337(4194337),
        e4194338(4194338),
        e4194339(4194339),
        e4194340(4194340),
        e4194341(4194341),
        e4194342(4194342),
        e4194343(4194343),
        e4194344(4194344),
        e4194345(4194345),
        e4194346(4194346),
        e4194347(4194347),
        e4194348(4194348),
        e4194349(4194349),
        e4194350(4194350),
        e4194351(4194351),
        e4194352(4194352),
        e4194353(4194353),
        e4194354(4194354),
        e4194355(4194355),
        e4194356(4194356),
        e4194357(4194357),
        e4194358(4194358),
        e4194359(4194359),
        e4194360(4194360),
        e4194361(4194361),
        e4194362(4194362),
        e4194363(4194363),
        e4194364(4194364),
        e4194365(4194365),
        e4194366(4194366),
        e4194367(4194367),
        e4194368(4194368),
        e4194369(4194369),
        e4194370(4194370),
        e4194371(4194371),
        e4194372(4194372),
        e4194373(4194373),
        e4194374(4194374),
        e4194375(4194375),
        e4194376(4194376),
        e4194377(4194377),
        e4194378(4194378),
        e4194379(4194379),
        e4194380(4194380),
        e4194381(4194381),
        e4194382(4194382),
        e4194383(4194383),
        e4194384(4194384),
        e4194385(4194385),
        e4194386(4194386),
        e4194387(4194387),
        e4194388(4194388),
        e4194389(4194389),
        e4194390(4194390),
        e4194391(4194391),
        e4194392(4194392),
        e4194393(4194393),
        e4194394(4194394),
        e4194395(4194395),
        e4194396(4194396),
        e4194397(4194397),
        e4194398(4194398),
        e4194399(4194399),
        e4194400(4194400),
        e4194401(4194401),
        e4194402(4194402),
        e4194403(4194403),
        e4194404(4194404),
        e4194405(4194405),
        e4194406(4194406),
        e4194407(4194407),
        e4194408(4194408),
        e4194409(4194409),
        e4194410(4194410),
        e4194411(4194411),
        e4194412(4194412),
        e4194413(4194413),
        e4194414(4194414),
        e4194415(4194415),
        e4194416(4194416),
        e4194417(4194417),
        e4194418(4194418),
        e4194419(4194419),
        e4194420(4194420),
        e4194421(4194421),
        e4194422(4194422),
        e4194423(4194423),
        e4194424(4194424),
        e4194425(4194425),
        e4194426(4194426),
        e4194427(4194427),
        e4194428(4194428),
        e4194429(4194429),
        e4194430(4194430),
        e4194431(4194431),
        e4194432(4194432),
        e4194433(4194433),
        e4194434(4194434),
        e4194435(4194435),
        e4194436(4194436),
        e4194437(4194437),
        e4194438(4194438),
        e4194439(4194439),
        e4194440(4194440),
        e4194441(4194441),
        e4194442(4194442),
        e4194443(4194443),
        e4194444(4194444),
        e4194445(4194445),
        e4194446(4194446),
        e4194447(4194447),
        e4194448(4194448),
        e4194449(4194449),
        e4194450(4194450),
        e4194451(4194451),
        e4194452(4194452),
        e4194453(4194453),
        e4194454(4194454),
        e4194455(4194455),
        e4194456(4194456),
        e4194457(4194457),
        e4194458(4194458),
        e4194459(4194459),
        e4194460(4194460),
        e4194461(4194461),
        e4194462(4194462),
        e4194463(4194463),
        e4194464(4194464),
        e4194465(4194465),
        e4194466(4194466),
        e4194467(4194467),
        e4194468(4194468),
        e4194469(4194469),
        e4194470(4194470),
        e4194471(4194471),
        e4194472(4194472),
        e4194473(4194473),
        e4194474(4194474),
        e4194475(4194475),
        e4194476(4194476),
        e4194477(4194477),
        e4194478(4194478),
        e4194479(4194479),
        e4194480(4194480),
        e4194481(4194481),
        e4194482(4194482),
        e4194483(4194483),
        e4194484(4194484),
        e4194485(4194485),
        e4194486(4194486),
        e4194487(4194487),
        e4194488(4194488),
        e4194489(4194489),
        e4194490(4194490),
        e4194491(4194491),
        e4194492(4194492),
        e4194493(4194493),
        e4194494(4194494),
        e4194495(4194495),
        e4194496(4194496),
        e4194497(4194497),
        e4194498(4194498),
        e4194499(4194499),
        e4194500(4194500),
        e4194501(4194501),
        e4194502(4194502),
        e4194503(4194503),
        e4194504(4194504),
        e4194505(4194505),
        e4194506(4194506),
        e4194507(4194507),
        e4194508(4194508),
        e4194509(4194509),
        e4194510(4194510),
        e4194511(4194511),
        e4194512(4194512),
        e4194513(4194513),
        e4194514(4194514),
        e4194515(4194515),
        e4194516(4194516),
        e4194517(4194517),
        e4194518(4194518),
        e4194519(4194519),
        e4194520(4194520),
        e4194521(4194521),
        e4194522(4194522),
        e4194523(4194523),
        e4194524(4194524),
        e4194525(4194525),
        e4194526(4194526),
        e4194527(4194527),
        e4194528(4194528),
        e4194529(4194529),
        e4194530(4194530),
        e4194531(4194531),
        e4194532(4194532),
        e4194533(4194533),
        e4194534(4194534),
        e4194535(4194535),
        e4194536(4194536),
        e4194537(4194537),
        e4194538(4194538),
        e4194539(4194539),
        e4194540(4194540),
        e4194541(4194541),
        e4194542(4194542),
        e4194543(4194543),
        e4194544(4194544),
        e4194545(4194545),
        e4194546(4194546),
        e4194547(4194547),
        e4194548(4194548),
        e4194549(4194549),
        e4194550(4194550),
        e4194551(4194551),
        e4194552(4194552),
        e4194553(4194553),
        e4194554(4194554),
        e4194555(4194555),
        e4194556(4194556),
        e4194557(4194557),
        e4194558(4194558),
        e4194559(4194559),
        e4194560(4194560),
        e4194561(4194561),
        e4194562(4194562),
        e4194563(4194563),
        e4194564(4194564),
        e4194565(4194565),
        e4194566(4194566),
        e4194567(4194567),
        e4194568(4194568),
        e4194569(4194569),
        e4194570(4194570),
        e4194571(4194571),
        e4194572(4194572),
        e4194573(4194573),
        e4194574(4194574),
        e4194575(4194575),
        e4194576(4194576),
        e4194577(4194577),
        e4194578(4194578),
        e4194579(4194579),
        e4194580(4194580),
        e4194581(4194581),
        e4194582(4194582),
        e4194583(4194583),
        e4194584(4194584),
        e4194585(4194585),
        e4194586(4194586),
        e4194587(4194587),
        e4194588(4194588),
        e4194589(4194589),
        e4194590(4194590),
        e4194591(4194591),
        e4194592(4194592),
        e4194593(4194593),
        e4194594(4194594),
        e4194595(4194595),
        e4194596(4194596),
        e4194597(4194597),
        e4194598(4194598),
        e4194599(4194599),
        e4194600(4194600),
        e4194601(4194601),
        e4194602(4194602),
        e4194603(4194603),
        e4194604(4194604),
        e4194605(4194605),
        e4194606(4194606),
        e4194607(4194607),
        e4194608(4194608),
        e4194609(4194609),
        e4194610(4194610),
        e4194611(4194611),
        e4194612(4194612),
        e4194613(4194613),
        e4194614(4194614),
        e4194615(4194615),
        e4194616(4194616),
        e4194617(4194617),
        e4194618(4194618),
        e4194619(4194619),
        e4194620(4194620),
        e4194621(4194621),
        e4194622(4194622),
        e4194623(4194623),
        e4194624(4194624),
        e4194625(4194625),
        e4194626(4194626),
        e4194627(4194627),
        e4194628(4194628),
        e4194629(4194629),
        e4194630(4194630),
        e4194631(4194631),
        e4194632(4194632),
        e4194633(4194633),
        e4194634(4194634),
        e4194635(4194635),
        e4194636(4194636),
        e4194637(4194637),
        e4194638(4194638),
        e4194639(4194639),
        e4194640(4194640),
        e4194641(4194641),
        e4194642(4194642),
        e4194643(4194643),
        e4194644(4194644),
        e4194645(4194645),
        e4194646(4194646),
        e4194647(4194647),
        e4194648(4194648),
        e4194649(4194649),
        e4194650(4194650),
        e4194651(4194651),
        e4194652(4194652),
        e4194653(4194653),
        e4194654(4194654),
        e4194655(4194655),
        e4194656(4194656),
        e4194657(4194657),
        e4194658(4194658),
        e4194659(4194659),
        e4194660(4194660),
        e4194661(4194661),
        e4194662(4194662),
        e4194663(4194663),
        e4194664(4194664),
        e4194665(4194665),
        e4194666(4194666),
        e4194667(4194667),
        e4194668(4194668),
        e4194669(4194669),
        e4194670(4194670),
        e4194671(4194671),
        e4194672(4194672),
        e4194673(4194673),
        e4194674(4194674),
        e4194675(4194675),
        e4194676(4194676),
        e4194677(4194677),
        e4194678(4194678),
        e4194679(4194679),
        e4194680(4194680),
        e4194681(4194681),
        e4194682(4194682),
        e4194683(4194683),
        e4194684(4194684),
        e4194685(4194685),
        e4194686(4194686),
        e4194687(4194687),
        e4194688(4194688),
        e4194689(4194689),
        e4194690(4194690),
        e4194691(4194691),
        e4194692(4194692),
        e4194693(4194693),
        e4194694(4194694),
        e4194695(4194695),
        e4194696(4194696),
        e4194697(4194697),
        e4194698(4194698),
        e4194699(4194699),
        e4194700(4194700),
        e4194701(4194701),
        e4194702(4194702),
        e4194703(4194703),
        e4194704(4194704),
        e4194705(4194705),
        e4194706(4194706),
        e4194707(4194707),
        e4194708(4194708),
        e4194709(4194709),
        e4194710(4194710),
        e4194711(4194711),
        e4194712(4194712),
        e4194713(4194713),
        e4194714(4194714),
        e4194715(4194715),
        e4194716(4194716),
        e4194717(4194717),
        e4194718(4194718),
        e4194719(4194719),
        e4194720(4194720),
        e4194721(4194721),
        e4194722(4194722),
        e4194723(4194723),
        e4194724(4194724),
        e4194725(4194725),
        e4194726(4194726),
        e4194727(4194727),
        e4194728(4194728),
        e4194729(4194729),
        e4194730(4194730),
        e4194731(4194731),
        e4194732(4194732),
        e4194733(4194733),
        e4194734(4194734),
        e4194735(4194735),
        e4194736(4194736),
        e4194737(4194737),
        e4194738(4194738),
        e4194739(4194739),
        e4194740(4194740),
        e4194741(4194741),
        e4194742(4194742),
        e4194743(4194743),
        e4194744(4194744),
        e4194745(4194745),
        e4194746(4194746),
        e4194747(4194747),
        e4194748(4194748),
        e4194749(4194749),
        e4194750(4194750),
        e4194751(4194751),
        e4194752(4194752),
        e4194753(4194753),
        e4194754(4194754),
        e4194755(4194755),
        e4194756(4194756),
        e4194757(4194757),
        e4194758(4194758),
        e4194759(4194759),
        e4194760(4194760),
        e4194761(4194761),
        e4194762(4194762),
        e4194763(4194763),
        e4194764(4194764),
        e4194765(4194765),
        e4194766(4194766),
        e4194767(4194767),
        e4194768(4194768),
        e4194769(4194769),
        e4194770(4194770),
        e4194771(4194771),
        e4194772(4194772),
        e4194773(4194773),
        e4194774(4194774),
        e4194775(4194775),
        e4194776(4194776),
        e4194777(4194777),
        e4194778(4194778),
        e4194779(4194779),
        e4194780(4194780),
        e4194781(4194781),
        e4194782(4194782),
        e4194783(4194783),
        e4194784(4194784),
        e4194785(4194785),
        e4194786(4194786),
        e4194787(4194787),
        e4194788(4194788),
        e4194789(4194789),
        e4194790(4194790),
        e4194791(4194791),
        e4194792(4194792),
        e4194793(4194793),
        e4194794(4194794),
        e4194795(4194795),
        e4194796(4194796),
        e4194797(4194797),
        e4194798(4194798),
        e4194799(4194799),
        e4194800(4194800),
        e4194801(4194801),
        e4194802(4194802),
        e4194803(4194803),
        e4194804(4194804),
        e4194805(4194805),
        e4194806(4194806),
        e4194807(4194807),
        e4194808(4194808),
        e4194809(4194809),
        e4194810(4194810),
        e4194811(4194811),
        e4194812(4194812),
        e4194813(4194813),
        e4194814(4194814),
        e4194815(4194815),
        e4194816(4194816),
        e4194817(4194817),
        e4194818(4194818),
        e4194819(4194819),
        e4194820(4194820),
        e4194821(4194821),
        e4194822(4194822),
        e4194823(4194823),
        e4194824(4194824),
        e4194825(4194825),
        e4194826(4194826),
        e4194827(4194827),
        e4194828(4194828),
        e4194829(4194829),
        e4194830(4194830),
        e4194831(4194831),
        e4194832(4194832),
        e4194833(4194833),
        e4194834(4194834),
        e4194835(4194835),
        e4194836(4194836),
        e4194837(4194837),
        e4194838(4194838),
        e4194839(4194839),
        e4194840(4194840),
        e4194841(4194841),
        e4194842(4194842),
        e4194843(4194843),
        e4194844(4194844),
        e4194845(4194845),
        e4194846(4194846),
        e4194847(4194847),
        e4194848(4194848),
        e4194849(4194849),
        e4194850(4194850),
        e4194851(4194851),
        e4194852(4194852),
        e4194853(4194853),
        e4194854(4194854),
        e4194855(4194855),
        e4194856(4194856),
        e4194857(4194857),
        e4194858(4194858),
        e4194859(4194859),
        e4194860(4194860),
        e4194861(4194861),
        e4194862(4194862),
        e4194863(4194863),
        e4194864(4194864),
        e4194865(4194865),
        e4194866(4194866),
        e4194867(4194867),
        e4194868(4194868),
        e4194869(4194869),
        e4194870(4194870),
        e4194871(4194871),
        e4194872(4194872),
        e4194873(4194873),
        e4194874(4194874),
        e4194875(4194875),
        e4194876(4194876),
        e4194877(4194877),
        e4194878(4194878),
        e4194879(4194879),
        e4194880(4194880),
        e4194881(4194881),
        e4194882(4194882),
        e4194883(4194883),
        e4194884(4194884),
        e4194885(4194885),
        e4194886(4194886),
        e4194887(4194887),
        e4194888(4194888),
        e4194889(4194889),
        e4194890(4194890),
        e4194891(4194891),
        e4194892(4194892),
        e4194893(4194893),
        e4194894(4194894),
        e4194895(4194895),
        e4194896(4194896),
        e4194897(4194897),
        e4194898(4194898),
        e4194899(4194899),
        e4194900(4194900),
        e4194901(4194901),
        e4194902(4194902),
        e4194903(4194903),
        e4194904(4194904),
        e4194905(4194905),
        e4194906(4194906),
        e4194907(4194907),
        e4194908(4194908),
        e4194909(4194909),
        e4194910(4194910),
        e4194911(4194911),
        e4194912(4194912),
        e4194913(4194913),
        e4194914(4194914),
        e4194915(4194915),
        e4194916(4194916),
        e4194917(4194917),
        e4194918(4194918),
        e4194919(4194919),
        e4194920(4194920),
        e4194921(4194921),
        e4194922(4194922),
        e4194923(4194923),
        e4194924(4194924),
        e4194925(4194925),
        e4194926(4194926),
        e4194927(4194927),
        e4194928(4194928),
        e4194929(4194929),
        e4194930(4194930),
        e4194931(4194931),
        e4194932(4194932),
        e4194933(4194933),
        e4194934(4194934),
        e4194935(4194935),
        e4194936(4194936),
        e4194937(4194937),
        e4194938(4194938),
        e4194939(4194939),
        e4194940(4194940),
        e4194941(4194941),
        e4194942(4194942),
        e4194943(4194943),
        e4194944(4194944),
        e4194945(4194945),
        e4194946(4194946),
        e4194947(4194947),
        e4194948(4194948),
        e4194949(4194949),
        e4194950(4194950),
        e4194951(4194951),
        e4194952(4194952),
        e4194953(4194953),
        e4194954(4194954),
        e4194955(4194955),
        e4194956(4194956),
        e4194957(4194957),
        e4194958(4194958),
        e4194959(4194959),
        e4194960(4194960),
        e4194961(4194961),
        e4194962(4194962),
        e4194963(4194963),
        e4194964(4194964),
        e4194965(4194965),
        e4194966(4194966),
        e4194967(4194967),
        e4194968(4194968),
        e4194969(4194969),
        e4194970(4194970),
        e4194971(4194971),
        e4194972(4194972),
        e4194973(4194973),
        e4194974(4194974),
        e4194975(4194975),
        e4194976(4194976),
        e4194977(4194977),
        e4194978(4194978),
        e4194979(4194979),
        e4194980(4194980),
        e4194981(4194981),
        e4194982(4194982),
        e4194983(4194983),
        e4194984(4194984),
        e4194985(4194985),
        e4194986(4194986),
        e4194987(4194987),
        e4194988(4194988),
        e4194989(4194989),
        e4194990(4194990),
        e4194991(4194991),
        e4194992(4194992),
        e4194993(4194993),
        e4194994(4194994),
        e4194995(4194995),
        e4194996(4194996),
        e4194997(4194997),
        e4194998(4194998),
        e4194999(4194999),
        e4195000(4195000),
        e4195001(4195001),
        e4195002(4195002),
        e4195003(4195003),
        e4195004(4195004),
        e4195005(4195005),
        e4195006(4195006),
        e4195007(4195007),
        e4195008(4195008),
        e4195009(4195009),
        e4195010(4195010),
        e4195011(4195011),
        e4195012(4195012),
        e4195013(4195013),
        e4195014(4195014),
        e4195015(4195015),
        e4195016(4195016),
        e4195017(4195017),
        e4195018(4195018),
        e4195019(4195019),
        e4195020(4195020),
        e4195021(4195021),
        e4195022(4195022),
        e4195023(4195023),
        e4195024(4195024),
        e4195025(4195025),
        e4195026(4195026),
        e4195027(4195027),
        e4195028(4195028),
        e4195029(4195029),
        e4195030(4195030),
        e4195031(4195031),
        e4195032(4195032),
        e4195033(4195033),
        e4195034(4195034),
        e4195035(4195035),
        e4195036(4195036),
        e4195037(4195037),
        e4195038(4195038),
        e4195039(4195039),
        e4195040(4195040),
        e4195041(4195041),
        e4195042(4195042),
        e4195043(4195043),
        e4195044(4195044),
        e4195045(4195045),
        e4195046(4195046),
        e4195047(4195047),
        e4195048(4195048),
        e4195049(4195049),
        e4195050(4195050),
        e4195051(4195051),
        e4195052(4195052),
        e4195053(4195053),
        e4195054(4195054),
        e4195055(4195055),
        e4195056(4195056),
        e4195057(4195057),
        e4195058(4195058),
        e4195059(4195059),
        e4195060(4195060),
        e4195061(4195061),
        e4195062(4195062),
        e4195063(4195063),
        e4195064(4195064),
        e4195065(4195065),
        e4195066(4195066),
        e4195067(4195067),
        e4195068(4195068),
        e4195069(4195069),
        e4195070(4195070),
        e4195071(4195071),
        e4195072(4195072),
        e4195073(4195073),
        e4195074(4195074),
        e4195075(4195075),
        e4195076(4195076),
        e4195077(4195077),
        e4195078(4195078),
        e4195079(4195079),
        e4195080(4195080),
        e4195081(4195081),
        e4195082(4195082),
        e4195083(4195083),
        e4195084(4195084),
        e4195085(4195085),
        e4195086(4195086),
        e4195087(4195087),
        e4195088(4195088),
        e4195089(4195089),
        e4195090(4195090),
        e4195091(4195091),
        e4195092(4195092),
        e4195093(4195093),
        e4195094(4195094),
        e4195095(4195095),
        e4195096(4195096),
        e4195097(4195097),
        e4195098(4195098),
        e4195099(4195099),
        e4195100(4195100),
        e4195101(4195101),
        e4195102(4195102),
        e4195103(4195103),
        e4195104(4195104),
        e4195105(4195105),
        e4195106(4195106),
        e4195107(4195107),
        e4195108(4195108),
        e4195109(4195109),
        e4195110(4195110),
        e4195111(4195111),
        e4195112(4195112),
        e4195113(4195113),
        e4195114(4195114),
        e4195115(4195115),
        e4195116(4195116),
        e4195117(4195117),
        e4195118(4195118),
        e4195119(4195119),
        e4195120(4195120),
        e4195121(4195121),
        e4195122(4195122),
        e4195123(4195123),
        e4195124(4195124),
        e4195125(4195125),
        e4195126(4195126),
        e4195127(4195127),
        e4195128(4195128),
        e4195129(4195129),
        e4195130(4195130),
        e4195131(4195131),
        e4195132(4195132),
        e4195133(4195133),
        e4195134(4195134),
        e4195135(4195135),
        e4195136(4195136),
        e4195137(4195137),
        e4195138(4195138),
        e4195139(4195139),
        e4195140(4195140),
        e4195141(4195141),
        e4195142(4195142),
        e4195143(4195143),
        e4195144(4195144),
        e4195145(4195145),
        e4195146(4195146),
        e4195147(4195147),
        e4195148(4195148),
        e4195149(4195149),
        e4195150(4195150),
        e4195151(4195151),
        e4195152(4195152),
        e4195153(4195153),
        e4195154(4195154),
        e4195155(4195155),
        e4195156(4195156),
        e4195157(4195157),
        e4195158(4195158),
        e4195159(4195159),
        e4195160(4195160),
        e4195161(4195161),
        e4195162(4195162),
        e4195163(4195163),
        e4195164(4195164),
        e4195165(4195165),
        e4195166(4195166),
        e4195167(4195167),
        e4195168(4195168),
        e4195169(4195169),
        e4195170(4195170),
        e4195171(4195171),
        e4195172(4195172),
        e4195173(4195173),
        e4195174(4195174),
        e4195175(4195175),
        e4195176(4195176),
        e4195177(4195177),
        e4195178(4195178),
        e4195179(4195179),
        e4195180(4195180),
        e4195181(4195181),
        e4195182(4195182),
        e4195183(4195183),
        e4195184(4195184),
        e4195185(4195185),
        e4195186(4195186),
        e4195187(4195187),
        e4195188(4195188),
        e4195189(4195189),
        e4195190(4195190),
        e4195191(4195191),
        e4195192(4195192),
        e4195193(4195193),
        e4195194(4195194),
        e4195195(4195195),
        e4195196(4195196),
        e4195197(4195197),
        e4195198(4195198),
        e4195199(4195199),
        e4195200(4195200),
        e4195201(4195201),
        e4195202(4195202),
        e4195203(4195203),
        e4195204(4195204),
        e4195205(4195205),
        e4195206(4195206),
        e4195207(4195207),
        e4195208(4195208),
        e4195209(4195209),
        e4195210(4195210),
        e4195211(4195211),
        e4195212(4195212),
        e4195213(4195213),
        e4195214(4195214),
        e4195215(4195215),
        e4195216(4195216),
        e4195217(4195217),
        e4195218(4195218),
        e4195219(4195219),
        e4195220(4195220),
        e4195221(4195221),
        e4195222(4195222),
        e4195223(4195223),
        e4195224(4195224),
        e4195225(4195225),
        e4195226(4195226),
        e4195227(4195227),
        e4195228(4195228),
        e4195229(4195229),
        e4195230(4195230),
        e4195231(4195231),
        e4195232(4195232),
        e4195233(4195233),
        e4195234(4195234),
        e4195235(4195235),
        e4195236(4195236),
        e4195237(4195237),
        e4195238(4195238),
        e4195239(4195239),
        e4195240(4195240),
        e4195241(4195241),
        e4195242(4195242),
        e4195243(4195243),
        e4195244(4195244),
        e4195245(4195245),
        e4195246(4195246),
        e4195247(4195247),
        e4195248(4195248),
        e4195249(4195249),
        e4195250(4195250),
        e4195251(4195251),
        e4195252(4195252),
        e4195253(4195253),
        e4195254(4195254),
        e4195255(4195255),
        e4195256(4195256),
        e4195257(4195257),
        e4195258(4195258),
        e4195259(4195259),
        e4195260(4195260),
        e4195261(4195261),
        e4195262(4195262),
        e4195263(4195263),
        e4195264(4195264),
        e4195265(4195265),
        e4195266(4195266),
        e4195267(4195267),
        e4195268(4195268),
        e4195269(4195269),
        e4195270(4195270),
        e4195271(4195271),
        e4195272(4195272),
        e4195273(4195273),
        e4195274(4195274),
        e4195275(4195275),
        e4195276(4195276),
        e4195277(4195277),
        e4195278(4195278),
        e4195279(4195279),
        e4195280(4195280),
        e4195281(4195281),
        e4195282(4195282),
        e4195283(4195283),
        e4195284(4195284),
        e4195285(4195285),
        e4195286(4195286),
        e4195287(4195287),
        e4195288(4195288),
        e4195289(4195289),
        e4195290(4195290),
        e4195291(4195291),
        e4195292(4195292),
        e4195293(4195293),
        e4195294(4195294),
        e4195295(4195295),
        e4195296(4195296),
        e4195297(4195297),
        e4195298(4195298),
        e4195299(4195299),
        e4195300(4195300),
        e4195301(4195301),
        e4195302(4195302),
        e4195303(4195303),
        e4195304(4195304),
        e4195305(4195305),
        e4195306(4195306),
        e4195307(4195307),
        e4195308(4195308),
        e4195309(4195309),
        e4195310(4195310),
        e4195311(4195311),
        e4195312(4195312),
        e4195313(4195313),
        e4195314(4195314),
        e4195315(4195315),
        e4195316(4195316),
        e4195317(4195317),
        e4195318(4195318),
        e4195319(4195319),
        e4195320(4195320),
        e4195321(4195321),
        e4195322(4195322),
        e4195323(4195323),
        e4195324(4195324),
        e4195325(4195325),
        e4195326(4195326),
        e4195327(4195327),
        e4195328(4195328),
        e4195329(4195329),
        e4195330(4195330),
        e4195331(4195331),
        e4195332(4195332),
        e4195333(4195333),
        e4195334(4195334),
        e4195335(4195335),
        e4195336(4195336),
        e4195337(4195337),
        e4195338(4195338),
        e4195339(4195339),
        e4195340(4195340),
        e4195341(4195341),
        e4195342(4195342),
        e4195343(4195343),
        e4195344(4195344),
        e4195345(4195345),
        e4195346(4195346),
        e4195347(4195347),
        e4195348(4195348),
        e4195349(4195349),
        e4195350(4195350),
        e4195351(4195351),
        e4195352(4195352),
        e4195353(4195353),
        e4195354(4195354),
        e4195355(4195355),
        e4195356(4195356),
        e4195357(4195357),
        e4195358(4195358),
        e4195359(4195359),
        e4195360(4195360),
        e4195361(4195361),
        e4195362(4195362),
        e4195363(4195363),
        e4195364(4195364),
        e4195365(4195365),
        e4195366(4195366),
        e4195367(4195367),
        e4195368(4195368),
        e4195369(4195369),
        e4195370(4195370),
        e4195371(4195371),
        e4195372(4195372),
        e4195373(4195373),
        e4195374(4195374),
        e4195375(4195375),
        e4195376(4195376),
        e4195377(4195377),
        e4195378(4195378),
        e4195379(4195379),
        e4195380(4195380),
        e4195381(4195381),
        e4195382(4195382),
        e4195383(4195383),
        e4195384(4195384),
        e4195385(4195385),
        e4195386(4195386),
        e4195387(4195387),
        e4195388(4195388),
        e4195389(4195389),
        e4195390(4195390),
        e4195391(4195391),
        e4195392(4195392),
        e4195393(4195393),
        e4195394(4195394),
        e4195395(4195395),
        e4195396(4195396),
        e4195397(4195397),
        e4195398(4195398),
        e4195399(4195399),
        e4195400(4195400),
        e4195401(4195401),
        e4195402(4195402),
        e4195403(4195403),
        e4195404(4195404),
        e4195405(4195405),
        e4195406(4195406),
        e4195407(4195407),
        e4195408(4195408),
        e4195409(4195409),
        e4195410(4195410),
        e4195411(4195411),
        e4195412(4195412),
        e4195413(4195413),
        e4195414(4195414),
        e4195415(4195415),
        e4195416(4195416),
        e4195417(4195417),
        e4195418(4195418),
        e4195419(4195419),
        e4195420(4195420),
        e4195421(4195421),
        e4195422(4195422),
        e4195423(4195423),
        e4195424(4195424),
        e4195425(4195425),
        e4195426(4195426),
        e4195427(4195427),
        e4195428(4195428),
        e4195429(4195429),
        e4195430(4195430),
        e4195431(4195431),
        e4195432(4195432),
        e4195433(4195433),
        e4195434(4195434),
        e4195435(4195435),
        e4195436(4195436),
        e4195437(4195437),
        e4195438(4195438),
        e4195439(4195439),
        e4195440(4195440),
        e4195441(4195441),
        e4195442(4195442),
        e4195443(4195443),
        e4195444(4195444),
        e4195445(4195445),
        e4195446(4195446),
        e4195447(4195447),
        e4195448(4195448),
        e4195449(4195449),
        e4195450(4195450),
        e4195451(4195451),
        e4195452(4195452),
        e4195453(4195453),
        e4195454(4195454),
        e4195455(4195455),
        e4195456(4195456),
        e4195457(4195457),
        e4195458(4195458),
        e4195459(4195459),
        e4195460(4195460),
        e4195461(4195461),
        e4195462(4195462),
        e4195463(4195463),
        e4195464(4195464),
        e4195465(4195465),
        e4195466(4195466),
        e4195467(4195467),
        e4195468(4195468),
        e4195469(4195469),
        e4195470(4195470),
        e4195471(4195471),
        e4195472(4195472),
        e4195473(4195473),
        e4195474(4195474),
        e4195475(4195475),
        e4195476(4195476),
        e4195477(4195477),
        e4195478(4195478),
        e4195479(4195479),
        e4195480(4195480),
        e4195481(4195481),
        e4195482(4195482),
        e4195483(4195483),
        e4195484(4195484),
        e4195485(4195485),
        e4195486(4195486),
        e4195487(4195487),
        e4195488(4195488),
        e4195489(4195489),
        e4195490(4195490),
        e4195491(4195491),
        e4195492(4195492),
        e4195493(4195493),
        e4195494(4195494),
        e4195495(4195495),
        e4195496(4195496),
        e4195497(4195497),
        e4195498(4195498),
        e4195499(4195499),
        e4195500(4195500),
        e4195501(4195501),
        e4195502(4195502),
        e4195503(4195503),
        e4195504(4195504),
        e4195505(4195505),
        e4195506(4195506),
        e4195507(4195507),
        e4195508(4195508),
        e4195509(4195509),
        e4195510(4195510),
        e4195511(4195511),
        e4195512(4195512),
        e4195513(4195513),
        e4195514(4195514),
        e4195515(4195515),
        e4195516(4195516),
        e4195517(4195517),
        e4195518(4195518),
        e4195519(4195519),
        e4195520(4195520),
        e4195521(4195521),
        e4195522(4195522),
        e4195523(4195523),
        e4195524(4195524),
        e4195525(4195525),
        e4195526(4195526),
        e4195527(4195527),
        e4195528(4195528),
        e4195529(4195529),
        e4195530(4195530),
        e4195531(4195531),
        e4195532(4195532),
        e4195533(4195533),
        e4195534(4195534),
        e4195535(4195535),
        e4195536(4195536),
        e4195537(4195537),
        e4195538(4195538),
        e4195539(4195539),
        e4195540(4195540),
        e4195541(4195541),
        e4195542(4195542),
        e4195543(4195543),
        e4195544(4195544),
        e4195545(4195545),
        e4195546(4195546),
        e4195547(4195547),
        e4195548(4195548),
        e4195549(4195549),
        e4195550(4195550),
        e4195551(4195551),
        e4195552(4195552),
        e4195553(4195553),
        e4195554(4195554),
        e4195555(4195555),
        e4195556(4195556),
        e4195557(4195557),
        e4195558(4195558),
        e4195559(4195559),
        e4195560(4195560),
        e4195561(4195561),
        e4195562(4195562),
        e4195563(4195563),
        e4195564(4195564),
        e4195565(4195565),
        e4195566(4195566),
        e4195567(4195567),
        e4195568(4195568),
        e4195569(4195569),
        e4195570(4195570),
        e4195571(4195571),
        e4195572(4195572),
        e4195573(4195573),
        e4195574(4195574),
        e4195575(4195575),
        e4195576(4195576),
        e4195577(4195577),
        e4195578(4195578),
        e4195579(4195579),
        e4195580(4195580),
        e4195581(4195581),
        e4195582(4195582),
        e4195583(4195583),
        e4195584(4195584),
        e4195585(4195585),
        e4195586(4195586),
        e4195587(4195587),
        e4195588(4195588),
        e4195589(4195589),
        e4195590(4195590),
        e4195591(4195591),
        e4195592(4195592),
        e4195593(4195593),
        e4195594(4195594),
        e4195595(4195595),
        e4195596(4195596),
        e4195597(4195597),
        e4195598(4195598),
        e4195599(4195599),
        e4195600(4195600),
        e4195601(4195601),
        e4195602(4195602),
        e4195603(4195603),
        e4195604(4195604),
        e4195605(4195605),
        e4195606(4195606),
        e4195607(4195607),
        e4195608(4195608),
        e4195609(4195609),
        e4195610(4195610),
        e4195611(4195611),
        e4195612(4195612),
        e4195613(4195613),
        e4195614(4195614),
        e4195615(4195615),
        e4195616(4195616),
        e4195617(4195617),
        e4195618(4195618),
        e4195619(4195619),
        e4195620(4195620),
        e4195621(4195621),
        e4195622(4195622),
        e4195623(4195623),
        e4195624(4195624),
        e4195625(4195625),
        e4195626(4195626),
        e4195627(4195627),
        e4195628(4195628),
        e4195629(4195629),
        e4195630(4195630),
        e4195631(4195631),
        e4195632(4195632),
        e4195633(4195633),
        e4195634(4195634),
        e4195635(4195635),
        e4195636(4195636),
        e4195637(4195637),
        e4195638(4195638),
        e4195639(4195639),
        e4195640(4195640),
        e4195641(4195641),
        e4195642(4195642),
        e4195643(4195643),
        e4195644(4195644),
        e4195645(4195645),
        e4195646(4195646),
        e4195647(4195647),
        e4195648(4195648),
        e4195649(4195649),
        e4195650(4195650),
        e4195651(4195651),
        e4195652(4195652),
        e4195653(4195653),
        e4195654(4195654),
        e4195655(4195655),
        e4195656(4195656),
        e4195657(4195657),
        e4195658(4195658),
        e4195659(4195659),
        e4195660(4195660),
        e4195661(4195661),
        e4195662(4195662),
        e4195663(4195663),
        e4195664(4195664),
        e4195665(4195665),
        e4195666(4195666),
        e4195667(4195667),
        e4195668(4195668),
        e4195669(4195669),
        e4195670(4195670),
        e4195671(4195671),
        e4195672(4195672),
        e4195673(4195673),
        e4195674(4195674),
        e4195675(4195675),
        e4195676(4195676),
        e4195677(4195677),
        e4195678(4195678),
        e4195679(4195679),
        e4195680(4195680),
        e4195681(4195681),
        e4195682(4195682),
        e4195683(4195683),
        e4195684(4195684),
        e4195685(4195685),
        e4195686(4195686),
        e4195687(4195687),
        e4195688(4195688),
        e4195689(4195689),
        e4195690(4195690),
        e4195691(4195691),
        e4195692(4195692),
        e4195693(4195693),
        e4195694(4195694),
        e4195695(4195695),
        e4195696(4195696),
        e4195697(4195697),
        e4195698(4195698),
        e4195699(4195699),
        e4195700(4195700),
        e4195701(4195701),
        e4195702(4195702),
        e4195703(4195703),
        e4195704(4195704),
        e4195705(4195705),
        e4195706(4195706),
        e4195707(4195707),
        e4195708(4195708),
        e4195709(4195709),
        e4195710(4195710),
        e4195711(4195711),
        e4195712(4195712),
        e4195713(4195713),
        e4195714(4195714),
        e4195715(4195715),
        e4195716(4195716),
        e4195717(4195717),
        e4195718(4195718),
        e4195719(4195719),
        e4195720(4195720),
        e4195721(4195721),
        e4195722(4195722),
        e4195723(4195723),
        e4195724(4195724),
        e4195725(4195725),
        e4195726(4195726),
        e4195727(4195727),
        e4195728(4195728),
        e4195729(4195729),
        e4195730(4195730),
        e4195731(4195731),
        e4195732(4195732),
        e4195733(4195733),
        e4195734(4195734),
        e4195735(4195735),
        e4195736(4195736),
        e4195737(4195737),
        e4195738(4195738),
        e4195739(4195739),
        e4195740(4195740),
        e4195741(4195741),
        e4195742(4195742),
        e4195743(4195743),
        e4195744(4195744),
        e4195745(4195745),
        e4195746(4195746),
        e4195747(4195747),
        e4195748(4195748),
        e4195749(4195749),
        e4195750(4195750),
        e4195751(4195751),
        e4195752(4195752),
        e4195753(4195753),
        e4195754(4195754),
        e4195755(4195755),
        e4195756(4195756),
        e4195757(4195757),
        e4195758(4195758),
        e4195759(4195759),
        e4195760(4195760),
        e4195761(4195761),
        e4195762(4195762),
        e4195763(4195763),
        e4195764(4195764),
        e4195765(4195765),
        e4195766(4195766),
        e4195767(4195767),
        e4195768(4195768),
        e4195769(4195769),
        e4195770(4195770),
        e4195771(4195771),
        e4195772(4195772),
        e4195773(4195773),
        e4195774(4195774),
        e4195775(4195775),
        e4195776(4195776),
        e4195777(4195777),
        e4195778(4195778),
        e4195779(4195779),
        e4195780(4195780),
        e4195781(4195781),
        e4195782(4195782),
        e4195783(4195783),
        e4195784(4195784),
        e4195785(4195785),
        e4195786(4195786),
        e4195787(4195787),
        e4195788(4195788),
        e4195789(4195789),
        e4195790(4195790),
        e4195791(4195791),
        e4195792(4195792),
        e4195793(4195793),
        e4195794(4195794),
        e4195795(4195795),
        e4195796(4195796),
        e4195797(4195797),
        e4195798(4195798),
        e4195799(4195799),
        e4195800(4195800),
        e4195801(4195801),
        e4195802(4195802),
        e4195803(4195803),
        e4195804(4195804),
        e4195805(4195805),
        e4195806(4195806),
        e4195807(4195807),
        e4195808(4195808),
        e4195809(4195809),
        e4195810(4195810),
        e4195811(4195811),
        e4195812(4195812),
        e4195813(4195813),
        e4195814(4195814),
        e4195815(4195815),
        e4195816(4195816),
        e4195817(4195817),
        e4195818(4195818),
        e4195819(4195819),
        e4195820(4195820),
        e4195821(4195821),
        e4195822(4195822),
        e4195823(4195823),
        e4195824(4195824),
        e4195825(4195825),
        e4195826(4195826),
        e4195827(4195827),
        e4195828(4195828),
        e4195829(4195829),
        e4195830(4195830),
        e4195831(4195831),
        e4195832(4195832),
        e4195833(4195833),
        e4195834(4195834),
        e4195835(4195835),
        e4195836(4195836),
        e4195837(4195837),
        e4195838(4195838),
        e4195839(4195839),
        e4195840(4195840),
        e4195841(4195841),
        e4195842(4195842),
        e4195843(4195843),
        e4195844(4195844),
        e4195845(4195845),
        e4195846(4195846),
        e4195847(4195847),
        e4195848(4195848),
        e4195849(4195849),
        e4195850(4195850),
        e4195851(4195851),
        e4195852(4195852),
        e4195853(4195853),
        e4195854(4195854),
        e4195855(4195855),
        e4195856(4195856),
        e4195857(4195857),
        e4195858(4195858),
        e4195859(4195859),
        e4195860(4195860),
        e4195861(4195861),
        e4195862(4195862),
        e4195863(4195863),
        e4195864(4195864),
        e4195865(4195865),
        e4195866(4195866),
        e4195867(4195867),
        e4195868(4195868),
        e4195869(4195869),
        e4195870(4195870),
        e4195871(4195871),
        e4195872(4195872),
        e4195873(4195873),
        e4195874(4195874),
        e4195875(4195875),
        e4195876(4195876),
        e4195877(4195877),
        e4195878(4195878),
        e4195879(4195879),
        e4195880(4195880),
        e4195881(4195881),
        e4195882(4195882),
        e4195883(4195883),
        e4195884(4195884),
        e4195885(4195885),
        e4195886(4195886),
        e4195887(4195887),
        e4195888(4195888),
        e4195889(4195889),
        e4195890(4195890),
        e4195891(4195891),
        e4195892(4195892),
        e4195893(4195893),
        e4195894(4195894),
        e4195895(4195895),
        e4195896(4195896),
        e4195897(4195897),
        e4195898(4195898),
        e4195899(4195899),
        e4195900(4195900),
        e4195901(4195901),
        e4195902(4195902),
        e4195903(4195903),
        e4195904(4195904),
        e4195905(4195905),
        e4195906(4195906),
        e4195907(4195907),
        e4195908(4195908),
        e4195909(4195909),
        e4195910(4195910),
        e4195911(4195911),
        e4195912(4195912),
        e4195913(4195913),
        e4195914(4195914),
        e4195915(4195915),
        e4195916(4195916),
        e4195917(4195917),
        e4195918(4195918),
        e4195919(4195919),
        e4195920(4195920),
        e4195921(4195921),
        e4195922(4195922),
        e4195923(4195923),
        e4195924(4195924),
        e4195925(4195925),
        e4195926(4195926),
        e4195927(4195927),
        e4195928(4195928),
        e4195929(4195929),
        e4195930(4195930),
        e4195931(4195931),
        e4195932(4195932),
        e4195933(4195933),
        e4195934(4195934),
        e4195935(4195935),
        e4195936(4195936),
        e4195937(4195937),
        e4195938(4195938),
        e4195939(4195939),
        e4195940(4195940),
        e4195941(4195941),
        e4195942(4195942),
        e4195943(4195943),
        e4195944(4195944),
        e4195945(4195945),
        e4195946(4195946),
        e4195947(4195947),
        e4195948(4195948),
        e4195949(4195949),
        e4195950(4195950),
        e4195951(4195951),
        e4195952(4195952),
        e4195953(4195953),
        e4195954(4195954),
        e4195955(4195955),
        e4195956(4195956),
        e4195957(4195957),
        e4195958(4195958),
        e4195959(4195959),
        e4195960(4195960),
        e4195961(4195961),
        e4195962(4195962),
        e4195963(4195963),
        e4195964(4195964),
        e4195965(4195965),
        e4195966(4195966),
        e4195967(4195967),
        e4195968(4195968),
        e4195969(4195969),
        e4195970(4195970),
        e4195971(4195971),
        e4195972(4195972),
        e4195973(4195973),
        e4195974(4195974),
        e4195975(4195975),
        e4195976(4195976),
        e4195977(4195977),
        e4195978(4195978),
        e4195979(4195979),
        e4195980(4195980),
        e4195981(4195981),
        e4195982(4195982),
        e4195983(4195983),
        e4195984(4195984),
        e4195985(4195985),
        e4195986(4195986),
        e4195987(4195987),
        e4195988(4195988),
        e4195989(4195989),
        e4195990(4195990),
        e4195991(4195991),
        e4195992(4195992),
        e4195993(4195993),
        e4195994(4195994),
        e4195995(4195995),
        e4195996(4195996),
        e4195997(4195997),
        e4195998(4195998),
        e4195999(4195999),
        e4196000(4196000),
        e4196001(4196001),
        e4196002(4196002),
        e4196003(4196003),
        e4196004(4196004),
        e4196005(4196005),
        e4196006(4196006),
        e4196007(4196007),
        e4196008(4196008),
        e4196009(4196009),
        e4196010(4196010),
        e4196011(4196011),
        e4196012(4196012),
        e4196013(4196013),
        e4196014(4196014),
        e4196015(4196015),
        e4196016(4196016),
        e4196017(4196017),
        e4196018(4196018),
        e4196019(4196019),
        e4196020(4196020),
        e4196021(4196021),
        e4196022(4196022),
        e4196023(4196023),
        e4196024(4196024),
        e4196025(4196025),
        e4196026(4196026),
        e4196027(4196027),
        e4196028(4196028),
        e4196029(4196029),
        e4196030(4196030),
        e4196031(4196031),
        e4196032(4196032),
        e4196033(4196033),
        e4196034(4196034),
        e4196035(4196035),
        e4196036(4196036),
        e4196037(4196037),
        e4196038(4196038),
        e4196039(4196039),
        e4196040(4196040),
        e4196041(4196041),
        e4196042(4196042),
        e4196043(4196043),
        e4196044(4196044),
        e4196045(4196045),
        e4196046(4196046),
        e4196047(4196047),
        e4196048(4196048),
        e4196049(4196049),
        e4196050(4196050),
        e4196051(4196051),
        e4196052(4196052),
        e4196053(4196053),
        e4196054(4196054),
        e4196055(4196055),
        e4196056(4196056),
        e4196057(4196057),
        e4196058(4196058),
        e4196059(4196059),
        e4196060(4196060),
        e4196061(4196061),
        e4196062(4196062),
        e4196063(4196063),
        e4196064(4196064),
        e4196065(4196065),
        e4196066(4196066),
        e4196067(4196067),
        e4196068(4196068),
        e4196069(4196069),
        e4196070(4196070),
        e4196071(4196071),
        e4196072(4196072),
        e4196073(4196073),
        e4196074(4196074),
        e4196075(4196075),
        f4522066(4522066),
        f4522408(4522408),
        f4522414(4522414),
        f4522421(4522421),
        f4522435(4522435),
        f4522448(4522448),
        f4522454(4522454),
        f4522465(4522465),
        f4522472(4522472),
        f4522474(4522474),
        f4522480(4522480),
        f4522482(4522482),
        f4522500(4522500),
        f4522502(4522502),
        f4522519(4522519),
        f4523218(4523218),
        f4523256(4523256),
        f4523262(4523262),
        f4523300(4523300),
        f4523311(4523311),
        f4523313(4523313),
        f4523349(4523349),
        f4523352(4523352),
        f4524766(4524766),
        f4524769(4524769),
        f4524774(4524774),
        f4524776(4524776),
        f4524780(4524780),
        f4524782(4524782),
        f4524789(4524789),
        f4524796(4524796),
        f4524799(4524799),
        f4524836(4524836),
        f4524852(4524852),
        f4524855(4524855),
        f4524857(4524857),
        f4524859(4524859),
        f4524861(4524861),
        f4524863(4524863),
        f4524884(4524884),
        f4524886(4524886),
        f4524888(4524888),
        f4524890(4524890),
        f4524892(4524892),
        f4524896(4524896),
        f4524898(4524898),
        f4524902(4524902),
        f4524905(4524905),
        f4524916(4524916),
        f4524925(4524925),
        f4526538(4526538),
        f4526545(4526545),
        f4526547(4526547),
        f4526549(4526549),
        f4526551(4526551),
        f4526553(4526553),
        f4526561(4526561),
        f4526563(4526563),
        f4526566(4526566),
        f4526568(4526568),
        f4526570(4526570),
        f4526572(4526572),
        f4526574(4526574),
        f4526576(4526576),
        f4526578(4526578),
        f4526580(4526580),
        f4526584(4526584),
        f4526587(4526587),
        f4526605(4526605),
        f4526646(4526646),
        f4526653(4526653),
        f4526657(4526657),
        f4526662(4526662),
        f4528969(4528969),
        f4529292(4529292),
        f4529373(4529373),
        f4529375(4529375),
        f4529380(4529380),
        f4529401(4529401),
        f4529415(4529415),
        f4529458(4529458),
        f4529464(4529464),
        f4529597(4529597)
    }

CfprApConditionLifecycle ::= TEXTUAL-CONVENTION
    STATUS        current
    DESCRIPTION
        ""
    SYNTAX        BITS
    {
        flapping(0),
        soakingClear(1),
        soakingRaise(2),
        suppressed(3)
    }

CfprApConditionRemoteInvRslt ::= TEXTUAL-CONVENTION
    STATUS        current
    DESCRIPTION
        ""
    SYNTAX        BITS
    {
        failure(0),
        unidentifiedFail(1),
        internalError(2),
        timeout(3),
        endPointUnavailable(4),
        endPointFailed(5),
        endPointProtocolError(6),
        swDefect(7),
        fwDefect(8),
        hwDefect(9),
        resourceUnavailable(10),
        resourceCapacityExceeded(11),
        resourceDependency(12),
        capabilityNotImplementedIgnore(13),
        capabilityNotImplementedFailure(14),
        capabilityNotSupported(15),
        capabilityUnavailable(16),
        serviceNotImplementedIgnore(17),
        serviceNotImplementedFail(18),
        serviceNotSupported(19),
        serviceUnavailable(20),
        serviceProtocolError(21),
        fruIdentityIndeterminate(22),
        fruInfoMalformed(23),
        illegalFru(24),
        fruStateIndeterminate(25),
        fruNotReady(26),
        extendTimeout(27),
        taskReset(28),
        fruNotSupported(29),
        intermittentError(30)
    }

CfprApConditionRule ::= TEXTUAL-CONVENTION
    STATUS        current
    DESCRIPTION
        ""
    SYNTAX        INTEGER
    {
        generic(0),
        fabricVlanReqVlanPermitUnresolved(19),
        fabricVlanGroupReqVlanGroupPermitUnresolved(21),
        dcxNsFailed(56),
        computePhysicalInsufficientlyEquipped(57),
        computePhysicalIdentityUnestablishable(58),
        computeBoardPowerError(59),
        computeBoardPowerFail(60),
        computeAboardThermalProblem(61),
        computeAboardPowerUsageProblem(62),
        computePhysicalPowerProblem(63),
        computePhysicalThermalProblem(64),
        computePhysicalBiosPostTimeout(65),
        computePhysicalDiscoveryFailed(66),
        computePhysicalAssociationFailed(67),
        computePhysicalDisassociationFailed(68),
        computePhysicalInoperable(69),
        computePhysicalUnassignedMissing(70),
        computePhysicalAssignedMissing(71),
        computePhysicalUnidentified(72),
        computePhysicalUnassignedInaccessible(73),
        computePhysicalAssignedInaccessible(74),
        computePhysicalNetworkMisconfigured(75),
        computePhysicalAdapterMismatch(76),
        computeBoardCmosVoltageThresholdCritical(77),
        computeBoardCmosVoltageThresholdNonRecoverable(78),
        computeAboardMotherBoardVoltageThresholdUpperNonRecoverable(79),
        computeAboardMotherBoardVoltageThresholdLowerNonRecoverable(80),
        computeAboardMotherBoardVoltageUpperThresholdCritical(81),
        computeAboardMotherBoardVoltageLowerThresholdCritical(82),
        computePoolEmpty(83),
        computePhysicalPostFailure(84),
        computeRtcBatteryInoperable(85),
        computeIohubThermalNonCritical(86),
        computeIohubThermalThresholdCritical(87),
        computeIohubThermalThresholdNonRecoverable(88),
        firmwareBootUnitPowerCycleRequired(89),
        cimcvmediaActualMountEntryVmediaMountFailed(90),
        firmwarePackItemImageMissing(95),
        firmwareUpdatableImageUnusable(96),
        firmwareBootUnitCantBoot(97),
        firmwareBootUnitActivateStatusFailed(98),
        firmwareStatusCimcFirmwareMismatch(99),
        firmwareStatusPldFirmwareMismatch(100),
        firmwareAutoSyncPolicyDefaultHostPackageMissing(101),
        powerChassisMemberPowerGroupCapInsufficient(149),
        powerChassisMemberChassisFirmwareProblem(150),
        powerBudgetFirmwareMismatch(151),
        powerChassisMemberChassisPsuInsufficient(152),
        powerBudgetChassisPsuInsufficient(153),
        powerChassisMemberChassisPsuRedundanceFailure(154),
        powerBudgetPowerBudgetCmcProblem(155),
        powerBudgetPowerBudgetBmcProblem(156),
        powerBudgetPowerCapReachedCommit(157),
        powerBudgetTstateTransition(158),
        powerBudgetPowerBudgetDiscFail(159),
        powerPolicyPowerPolicyApplicationFail(160),
        powerGroupPowerGroupInsufficientBudget(161),
        powerGroupPowerGroupBudgetIncorrect(162),
        powerBudgetChassisPsuMixedMode(163),
        smSlotSmaHeartbeat(185),
        smSlotBladeNotWorking(186),
        smSlotDiskFormatFailed(187),
        smSlotBladeSwap(188),
        smSecSvcSwitchConfigFail(189),
        smAppInstanceAppNotResponding(190),
        smAppInstanceAppInstallFailed(191),
        smAppInstanceAppStartFailed(192),
        smAppInstanceAppUpdateFailed(193),
        smAppInstanceAppStopFailed(194),
        smAppInstanceAppInstanceError(195),
        smLogicalDeviceIncompleteConfig(196),
        smLogicalDeviceLogicalDeviceError(197),
        smAppLicenseAgreementNotAccepted(198),
        smAppInstanceAppInstanceUnsupported(199),
        smAppAppMetaCorrupted(200),
        swVlanPortNsVlancompNotSupport(299),
        dcxVifLinkState(300),
        vnicEtherConfigFailed(314),
        vnicEtherPinningMismatch(315),
        vnicEtherPinningMisconfig(316),
        vnicEtherIfVlanAccessFault(317),
        vnicEtherIfVlanUnresolvable(318),
        vnicEtherIfRemoteVlanUnresolvable(319),
        vnicEtherIfInvalidVlan(320),
        fabricVlanVlanConflictPermit(321),
        vnicProfileProfileConfigIncorrect(322),
        vnicIscsiConfigFailed(323),
        vnicEtherVirtualizationConflict(324),
        vnicEtherVirtualizationNetflowConflict(325),
        lsIssuesIscsiConfigFailed(326),
        macpoolPoolEmpty(332),
        callhomeEpNoSnmpPolicyForCallhome(335),
        adaptorUnitUnidentifiableFru(349),
        adaptorUnitExtnUnidentifiableFru(350),
        adaptorUnitMissing(351),
        adaptorUnitExtnMissing(352),
        adaptorUnitAdaptorReachability(353),
        adaptorHostIfLinkDown(354),
        adaptorExtIfLinkDown(355),
        adaptorHostEthIfMisConnect(356),
        adaptorHostEthIfMissing(357),
        adaptorExtEthIfMisConnect(358),
        adaptorExtEthIfMissing(359),
        memoryUnitDegraded(369),
        memoryUnitIdentityUnestablishable(370),
        memoryUnitInoperable(371),
        memoryUnitDisabled(372),
        memoryUnitThermalThresholdNonCritical(373),
        memoryBufferUnitThermalThresholdNonCritical(374),
        memoryUnitThermalThresholdCritical(375),
        memoryBufferUnitThermalThresholdCritical(376),
        memoryUnitThermalThresholdNonRecoverable(377),
        memoryBufferUnitThermalThresholdNonRecoverable(378),
        memoryArrayVoltageThresholdNonCritical(379),
        memoryArrayVoltageThresholdCritical(380),
        memoryArrayVoltageThresholdNonRecoverable(381),
        lsServerFailed(657),
        lsServerDiscoveryFailed(658),
        lsServerConfigFailure(659),
        lsServerMaintenanceFailed(660),
        lsServerRemoved(661),
        lsServerInaccessible(662),
        lsServerAssociationFailed(663),
        lsComputeBindingAssignmentRequirementsNotMet(664),
        lsServerUnassociated(665),
        lsServerSvnicNotPresent(666),
        lsServerServerUnfulfilled(667),
        lsmaintMaintPolicyUnresolvableScheduler(668),
        lsIssuesKvmPolicyUnsupported(669),
        iqnpoolPoolEmpty(675),
        etherSwitchIntfioSatelliteConnectionAbsent(687),
        etherSwitchIntfioSatelliteWiringProblem(688),
        etherSwitchIntfioSatelliteWiringNumbersUnexpected(689),
        equipmentPsuPowerSupplyProblem(690),
        equipmentPsuOffline(691),
        equipmentPsuPowerSupplyShutdown(692),
        equipmentChassisIdentityUnestablishable(693),
        equipmentFexIdentityUnestablishable(694),
        equipmentFexFexUnsupported(695),
        equipmentFanModuleDegraded(696),
        equipmentFanDegraded(697),
        equipmentChassisInoperable(698),
        equipmentChassisSeepromInoperable(699),
        equipmentFanModuleInoperable(700),
        equipmentFanInoperable(701),
        equipmentPsuInoperable(702),
        equipmentIocardRemoved(703),
        equipmentIocardInaccessible(704),
        equipmentIocardPostFailure(705),
        equipmentFexPostFailure(706),
        equipmentFanModuleMissing(707),
        equipmentFanMissing(708),
        equipmentPsuMissing(709),
        equipmentIocardThermalProblem(710),
        equipmentIocardThermalThresholdNonCritical(711),
        equipmentIocardThermalThresholdCritical(712),
        equipmentIocardThermalThresholdNonRecoverable(713),
        equipmentFanModuleThermalThresholdNonCritical(714),
        equipmentPsuThermalThresholdNonCritical(715),
        equipmentFanModuleThermalThresholdCritical(716),
        equipmentPsuThermalThresholdCritical(717),
        equipmentFanModuleThermalThresholdNonRecoverable(718),
        equipmentPsuThermalThresholdNonRecoverable(719),
        equipmentPsuVoltageThresholdNonCritical(720),
        equipmentPsuVoltageThresholdCritical(721),
        equipmentPsuVoltageThresholdNonRecoverable(722),
        equipmentPsuPerfThresholdNonCritical(723),
        equipmentPsuPerfThresholdCritical(724),
        equipmentPsuPerfThresholdNonRecoverable(725),
        equipmentFanPerfThresholdNonCritical(726),
        equipmentFanPerfThresholdCritical(727),
        equipmentFanPerfThresholdNonRecoverable(728),
        equipmentFanPerfThresholdLowerNonRecoverable(729),
        equipmentIocardFirmwareUpgrade(730),
        equipmentChassisUnsupportedConnectivity(731),
        equipmentChassisUnacknowledged(732),
        equipmentIocardUnsupportedConnectivity(733),
        equipmentIocardAutoUpgradingFirmware(734),
        equipmentIocardUnacknowledged(735),
        equipmentIocardPeerDisconnected(736),
        equipmentChassisIdentity(737),
        equipmentChassisInvalidFru(738),
        equipmentChassisPowerProblem(739),
        equipmentChassisThermalThresholdCritical(740),
        equipmentChassisThermalThresholdNonCritical(741),
        equipmentChassisThermalThresholdNonRecoverable(742),
        equipmentIocardIdentity(743),
        equipmentFexIdentity(744),
        equipmentFanModuleIdentity(745),
        equipmentPsuIdentity(746),
        equipmentPsuPowerThreshold(747),
        equipmentPsuInputError(748),
        equipmentSwitchCardPowerOff(749),
        equipmentSwitchCardAct2LiteFail(750),
        equipmentHealthLedCriticalError(751),
        equipmentTpmSlaveTpm(752),
        equipmentHealthLedMinorError(753),
        equipmentSwitchiocardRemoved(754),
        equipmentSwitchiocardThermalProblem(755),
        equipmentSwitchiocardThermalThresholdNonCritical(756),
        equipmentSwitchiocardThermalThresholdCritical(757),
        equipmentSwitchiocardThermalThresholdNonRecoverable(758),
        equipmentSwitchiocardIdentity(759),
        equipmentSwitchiocardCpuThermalThresholdCritical(760),
        extpolClientClientLostConnectivity(792),
        extpolClientGracePeriodWarning(793),
        extpolClientGracePeriodWarning2(794),
        extpolClientGracePeriodWarning3(795),
        extpolClientGracePeriodWarning4(796),
        extpolClientGracePeriodWarning5(797),
        extpolClientGracePeriodWarning6(798),
        extpolClientGracePeriodWarning7(799),
        extpolClientGracePeriodWarning1(800),
        storageLocalDiskInoperable(809),
        storageLocalDiskDegraded(810),
        storageLocalDiskSlotEpUnusable(811),
        storageItemCapacityExceeded(812),
        storageItemCapacityWarning(813),
        storageItemFilesystemIssues(814),
        storageRaidBatteryInoperable(815),
        storageMezzFlashLifeConfigurationError(816),
        storageMezzFlashLifeDegraded(817),
        storageRaidBatteryDegraded(818),
        storageRaidBatteryRelearnAborted(819),
        storageRaidBatteryRelearnFailed(820),
        storageInitiatorConfigurationError(821),
        storageControllerPatrolReadFailed(822),
        storageControllerInoperable(823),
        storageLocalDiskRebuildFailed(824),
        storageLocalDiskCopybackFailed(825),
        storageLocalDiskMissing(826),
        storageVirtualDriveInoperable(827),
        storageVirtualDriveDegraded(828),
        storageVirtualDriveReconstructionFailed(829),
        storageVirtualDriveConsistencyCheckFailed(830),
        storageFlexFlashControllerInoperable(831),
        storageFlexFlashCardInoperable(832),
        storageFlexFlashCardMissing(833),
        storageFlexFlashVirtualDriveDegraded(834),
        storageFlexFlashVirtualDriveInoperable(835),
        storageFlexFlashControllerUnhealthy(836),
        storageFlexFlashControllerMismatch(837),
        storageFlexFlashDriveUnhealthy(838),
        storageFlexFlashCardUnhealthy(839),
        ippoolPoolEmpty(844),
        aaaProviderGroupProvidergroup(850),
        aaaProviderGroupProvidergroupsize(851),
        aaaConfigServergroup(852),
        pkiKeyRingStatus(853),
        pkiKeyRingModulus(854),
        pkiTpStatus(855),
        aaaRoleRoleNotDeployed(856),
        aaaLocaleLocaleNotDeployed(857),
        aaaOrgLocaleOrgNotPresent(858),
        aaaUserRoleUserRoleNotDeployed(859),
        aaaUserLocaleUserLocaleNotDeployed(860),
        pkiKeyRingKeyRingNotDeployed(861),
        commSnmpSyscontactEmpty(862),
        commDateTimeCommTimeZoneInvalid(863),
        aaaUserLocalUserNotDeployed(864),
        commSnmpUserSnmpUserNotDeployed(865),
        commSvcEpCommSvcNotDeployed(866),
        sysdebugLogExportStatusLogExportFailure(871),
        sysdebugAutoCoreFileExportTargetAutoCoreTransferFailure(872),
        processorUnitInoperable(899),
        processorUnitThermalNonCritical(900),
        processorUnitThermalThresholdCritical(901),
        processorUnitThermalThresholdNonRecoverable(902),
        processorUnitVoltageThresholdNonCritical(903),
        processorUnitVoltageThresholdCritical(904),
        processorUnitVoltageThresholdNonRecoverable(905),
        processorUnitIdentityUnestablishable(906),
        processorUnitDisabled(907),
        extmgmtIfMgmtifdown(964),
        extmgmtArpTargetsArpTargetsNotValid(965),
        extmgmtNdiscTargetsNdiscTargetsNotValid(966),
        poolElementDuplicatedAssigned(967),
        networkElementInoperable(977),
        networkElementRemoved(978),
        swVlanPortNsResourceStatus(979),
        swVlanPortNsResourceStatusWarning(980),
        networkElementInventoryFailed(981),
        networkElementThermalThresholdCritical(982),
        networkElementMemoryerror(983),
        networkOperLevelExtraprimaryvlans(984),
        networkOperLevelExtrasecondaryvlans(985),
        swVlanExtrasecondaryvlansperprimary(986),
        fcpoolInitiatorsEmpty(987),
        osControllerFailedBladeBootup(996),
        osControllerFailedBootupRecovery(997),
        uuidpoolPoolEmpty(1014),
        capabilityCatalogueLoadErrors(1020),
        fabricComputeSlotEpMisplacedInChassisSlot(1038),
        fabricComputeSlotEpServerIdentificationProblem(1039),
        fabricVlanPrimaryVlanMissingForIsolated(1040),
        fabricVlanPrimaryVlanMissingForCommunity(1041),
        fabricLanPinGroupEmpty(1042),
        fabricEthLanPcEpDown(1043),
        fabricEthEstcPcEpDown(1044),
        fabricPinTargetDown(1045),
        fabricDceSwSrvPcEpDown(1046),
        fabricMonSpanConfigFail(1047),
        fabricEpMgrEpTransModeFail(1048),
        fabricVlanMismatchA(1049),
        fabricVlanMismatchB(1050),
        fabricVlanErrorAssocPrimary(1051),
        fabricPioEpErrorMisconfigured(1052),
        fabricEthLanEpMissingPrimaryVlan(1053),
        fabricEthLanEpUdldLinkDown(1054),
        fabricEthLanPcEpUdldLinkDown(1055),
        fabricEthLanPcMissingPrimaryVlan(1056),
        fabricEthLanEpOverlappingVlan(1057),
        fabricEthLanPcOverlappingVlan(1058),
        fabricVlanMisconfiguredMcastPolicy(1059),
        fabricNetflowMonSessionFlowMonConfigFail(1060),
        fabricNetflowMonSessionNetflowSessionConfigFail(1061),
        fabricPooledVlanNamedVlanUnresolved(1062),
        mgmtEntityDegraded(1115),
        mgmtEntityDown(1116),
        mgmtEntityElectionFailure(1117),
        mgmtEntityManagementServicesFailure(1118),
        mgmtEntityManagementServicesUnresponsive(1119),
        mgmtEntityHaNotReady(1120),
        mgmtEntityVersionIncompatible(1121),
        mgmtEntityDevice1SharedStorageError(1122),
        mgmtEntityDevice2SharedStorageError(1123),
        mgmtEntityDevice3SharedStorageError(1124),
        mgmtEntityHaSshKeysMismatched(1125),
        mgmtPmonEntryFprmProcessFailure(1126),
        sysdebugMepLogMEpLogLog(1127),
        sysdebugMepLogMEpLogVeryLow(1128),
        sysdebugMepLogMEpLogFull(1129),
        sysdebugMepLogTransferError(1130),
        mgmtIfMisConnect(1131),
        mgmtIfMissing(1132),
        mgmtIfNew(1133),
        mgmtConnectionDisabled(1134),
        mgmtConnectionUnused(1135),
        mgmtConnectionUnsupportedConnectivity(1136),
        mgmtControllerUnsupportedDimmBlacklisting(1137),
        mgmtInterfaceNamedInbandVlanUnresolved(1138),
        mgmtInterfaceInbandUnsupportedServer(1139),
        mgmtInterfaceInbandUnsupportedFirmware(1140),
        mgmtBackupPolicyConfigConfigurationBackupOutdated(1141),
        portPioLinkDown(1150),
        portPioFailed(1151),
        portPioHardwareFailure(1152),
        portPioSfpNotPresent(1153),
        portPioInvalidSfp(1154),
        etherServerIntfioHardwareFailure(1155),
        fabricExternalPcDown(1156),
        fabricInternalPcDown(1157),
        dcxVcDown(1158),
        dcxVcMgmtVifDown(1159),
        policyControlEpSuspendModeActive(1174),
        firmwareInfraPackInfraBundleVersionMissing(1309),
        firmwareSystemInfraBundleValidationFailure(1310),
        firmwareSystemInfraBundleUpgradeFailure(1311),
        firmwareSystemFirmwareUpgradeFailure(1312),
        firmwareSystemInfraBundleInstallAppFailure(1313),
        fsmSamDmeComputeServerDiscPolicyResolveScrubPolicy(16476),
        fsmSamDmeGmetaHolderInventory(16477),
        fsmSamDmeFirmwareDownloaderDownload(16517),
        fsmSamDmeFirmwareImageDelete(16518),
        fsmSamDmeFirmwareDistributableDelete(16519),
        fsmSamDmeMgmtControllerUpdateucsmanager(16520),
        fsmSamDmeMgmtControllerUpdateSwitch(16521),
        fsmSamDmeMgmtControllerUpdateiom(16522),
        fsmSamDmeFirmwarePlatformPackPlatformVersion(16523),
        fsmSamDmeFirmwareSystemDeploy(16524),
        fsmSamDmeFirmwareSupFirmwareDeploy(16525),
        fsmSamDmeFirmwareSystemApplyCatalogPack(16526),
        fsmSamDmeIdentIdentRequestUpdateIdent(16528),
        fsmSamDmeIdentMetaSystemSync(16529),
        fsmSamDmeIdentMetaSystemUcscUnivSync(16530),
        fsmSamDmeSmAppDelete(16585),
        fsmSamDmeSmSecSvcRestoreApplication(16586),
        fsmSamDmeSmAppUpdateApplication(16587),
        fsmSamDmeSmAppInstanceResetApplication(16588),
        fsmSamDmeSmSecSvcAutoDeploycsp(16589),
        fsmSamDmeSwAccessDomainDeploy(16667),
        fsmSamDmeSwEthLanBorderDeploy(16668),
        fsmSamDmeSwFcSanBorderDeploy(16669),
        fsmSamDmeSwUtilityDomainDeploy(16670),
        fsmSamDmeSwEthLanFlowMonDeploy(16671),
        fsmSamDmeSwPhysConfPhysical(16676),
        fsmSamDmeSwExtUtilityConfPortBreakout(16681),
        fsmSamDmeSwFcSanBorderActivateZoneSet(16682),
        fsmSamDmeCallhomeEpConfigCallhome(16718),
        fsmSamDmeAdaptorExtEthIfPathReset(16727),
        fsmSamDmeAdaptorHostEthIfCircuitReset(16730),
        fsmSamDmeAdaptorHostFcIfCircuitReset(16731),
        fsmSamDmeLicenseDownloaderDownload(16748),
        fsmSamDmeLicenseFileInstall(16749),
        fsmSamDmeLicenseFileClear(16750),
        fsmSamDmeLicenseInstanceUpdateFlexlm(16751),
        fsmSamDmeLicenseSmartConfigSetConfig(16752),
        fsmSamDmeLsServerConfigure(16770),
        fsmSamDmeComputeBladeDiag(16780),
        fsmSamDmeMgmtControllerExtMgmtInterfaceConfig(16803),
        fsmSamDmeComputePhysicalSwConnUpd(16804),
        fsmSamDmeEquipmentiocardResetIom(16805),
        fsmSamDmeComputePhysicalServiceInfraDeploy(16806),
        fsmSamDmeComputePhysicalServiceInfraWithdraw(16807),
        fsmSamDmeEquipmentiocardBaseFePresence(16815),
        fsmSamDmeEquipmentiocardBaseFeConn(16816),
        fsmSamDmeEquipmentChassisRemoveChassis(16817),
        fsmSamDmeEquipmentLocatorLedSetFeLocatorLed(16818),
        fsmSamDmeEquipmentLocatorLedSetFiLocatorLed(16819),
        fsmSamDmePortpioInCompatSfpPresence(16822),
        fsmSamDmePortpioInCompatSfpReplaced(16823),
        fsmSamDmeObserveObservedResolvePolicyFsm(17063),
        fsmSamDmeObserveObservedResolveResourceFsm(17064),
        fsmSamDmeObserveObservedResolvevmfsm(17065),
        fsmSamDmeObserveObservedResolveControllerFsm(17066),
        fsmSamDmeEquipmentBeaconLedIlluminate(17149),
        fsmSamDmeSdAppInstanceInstallApplication(17151),
        fsmSamDmeSdAppInstanceStartApplication(17152),
        fsmSamDmeSdLduProvisionldu(17153),
        fsmSamDmeSdAppInstanceUpgradeApplication(17154),
        fsmSamDmeSdAppInstanceStopApplication(17155),
        fsmSamDmeSdAppInstanceUninstallApplication(17156),
        fsmSamDmeSdSlotChangePlatformLogLevel(17157),
        fsmSamDmeSdAppInstanceBundleDataPorts(17158),
        fsmSamDmeSdLogicalDeviceConfigureLinks(17159),
        fsmSamDmeSdLinkUpdateInterfaceStatus(17160),
        fsmSamDmeSdClusterBootstrapUpdateClusterConfiguration(17161),
        fsmSamDmeSdSlotFormatDisk(17162),
        fsmSamDmeSdSlotSynchTimeZone(17163),
        fsmSamDmeSdAppAttributeCtrlGetAppAttributes(17164),
        fsmSamDmeSdMgmtInfoUpdateMgmtInfo(17165),
        fsmSamDmeSdNetMgmtBootstrapUpdateNetMgmtBootstrap(17166),
        fsmSamDmeSdUpgradeTaskStopUpgradeStartApp(17167),
        fsmSamDmeEtherServerIntfioConfigSpeed(17169),
        fsmSamDmeEtherFtwPortPairConfigFtw(17170),
        fsmSamDmeExtpolEpRegisterFsm(17185),
        fsmSamDmeExtpolRegistryCrossDomainConfig(17186),
        fsmSamDmeExtpolRegistryCrossDomainDelete(17187),
        fsmSamDmeStorageSystemSync(17224),
        fsmSamDmeSysfileMutationSingle(17226),
        fsmSamDmeSysfileMutationGlobal(17227),
        fsmSamDmeApplicationDownloaderDownload(17231),
        fsmSamDmeCommSvcEpUpdateSvcEp(17232),
        fsmSamDmeCommSvcEpRestartWebSvc(17233),
        fsmSamDmePkiEpUpdateEp(17251),
        fsmSamDmeAaaEpUpdateEp(17252),
        fsmSamDmeAaaRealmUpdateRealm(17253),
        fsmSamDmeAaaUserEpUpdateUserEp(17254),
        fsmSamDmeSysdebugManualCoreFileExportTargetExport(17265),
        fsmSamDmeSysdebugLogExportPolicyConfigure(17266),
        fsmSamDmeSysdebugAutoCoreFileExportTargetConfigure(17267),
        fsmSamDmeSysdebugTechSupportInitiate(17268),
        fsmSamDmeSysdebugTechSupportDeleteTechSupFile(17269),
        fsmSamDmeSysdebugTechSupportDownload(17270),
        fsmSamDmeSysdebugCoreDownload(17271),
        fsmSamDmeSysdebugLogControlEpLogControlPersist(17272),
        fsmSamDmeEpqosDefinitionDeploy(17336),
        fsmSamDmeEpqosDefinitionDelTaskRemove(17337),
        fsmSamDmeQosclassDefinitionConfigGlobalQos(17340),
        fsmSamDmeMgmtControllerRegistryConfig(17347),
        fsmSamDmeMgmtIfSwMgmtOobIfConfig(17358),
        fsmSamDmeMgmtIfSwMgmtInbandIfConfig(17359),
        fsmSamDmeMgmtipv6IfAddrSwMgmtOobIpv6IfConfig(17360),
        fsmSamDmeNhTableHolderConfigureLinks(17373),
        fsmSamDmeNhTableHolderBootstrapLinks(17374),
        fsmSamDmeStatsCollectionPolicyUpdateEp(17378),
        fsmSamDmeSyntheticFsObjCreate(17403),
        fsmSamDmeCapabilityUpdaterUpdater(17408),
        fsmSamDmeCapabilityCatalogueActivateCatalog(17409),
        fsmSamDmeCapabilityMgmtExtensionActivateMgmtExt(17410),
        fsmSamDmeCapabilityCatalogueDeployCatalogue(17411),
        fsmSamDmeSwEthMonDeploy(17420),
        fsmSamDmeSwFcMonDeploy(17421),
        fsmSamDmeSwSspEthMonDeploy(17469),
        fsmSamDmeSwSspEthMonSrcPhyEpDelete(17470),
        fsmSamDmeFabricVnetEpSyncEpPushVnetEpDeletion(17476),
        fsmSamDmeFabricLanCloudSwitchMode(17477),
        fsmSamDmeFabricSanCloudSwitchMode(17478),
        fsmSamDmeFabricEpMgrConfigure(17484),
        fsmSamDmeMgmtExportPolicyReportConfigCopy(17490),
        fsmSamDmeExtpolProviderReportConfigImport(17491),
        fsmSamDmeMgmtIfVirtualIfConfig(17492),
        fsmSamDmeMgmtIfEnableVip(17493),
        fsmSamDmeMgmtIfDisableVip(17494),
        fsmSamDmeMgmtIfEnableha(17495),
        fsmSamDmeMgmtBackupBackup(17496),
        fsmSamDmeMgmtImporterImport(17497),
        fsmSamDmeMgmtControllerSysConfig(17498),
        fsmSamDmeNfsMountInstMount(17531),
        fsmSamDmeNfsMountInstUnmount(17532),
        fsmSamDmeNfsMountDefReportNfsMountSuspend(17533),
        fsmSamDmeExtpolEpRepairCert(17554),
        fsmSamDmePolicyControlEpOperate(17555),
        fsmSamDmePolicyControlledTypeOperate(17556),
        fsmSamDmePolicyPolicyScopeReleasePolicyFsm(17559),
        fsmSamDmePolicyPolicyScopeReleaseOperationFsm(17560),
        fsmSamDmePolicyPolicyScopeReleaseStorageFsm(17561),
        fsmSamDmePolicyPolicyScopeResolveManyPolicyFsm(17562),
        fsmSamDmePolicyPolicyScopeResolveManyOperationFsm(17563),
        fsmSamDmePolicyPolicyScopeResolveManyStorageFsm(17564),
        fsmSamDmePolicyPolicyScopeReleaseManyPolicyFsm(17565),
        fsmSamDmePolicyPolicyScopeReleaseManyOperationFsm(17566),
        fsmSamDmePolicyPolicyScopeReleaseManyStorageFsm(17567),
        fsmSamDmePolicyPolicyScopeResolveAllPolicyFsm(17568),
        fsmSamDmePolicyPolicyScopeResolveAllOperationFsm(17569),
        fsmSamDmePolicyPolicyScopeResolveAllStorageFsm(17570),
        fsmSamDmePolicyPolicyScopeReleaseAllPolicyFsm(17571),
        fsmSamDmePolicyPolicyScopeReleaseAllOperationFsm(17572),
        fsmSamDmePolicyPolicyScopeReleaseAllStorageFsm(17573),
        fsmSamDmeFirmwareInfraPackInfraVersion(17690),
        tcaComputeMbPowerStatsInputVoltage(34261),
        tcaComputeMbPowerStatsInputVoltageMin(34263),
        tcaComputeMbPowerStatsInputVoltageMax(34264),
        tcaComputeMbPowerStatsInputVoltageAvg(34265),
        tcaComputeMbPowerStatsInputCurrent(34269),
        tcaComputeMbPowerStatsInputCurrentMin(34271),
        tcaComputeMbPowerStatsInputCurrentMax(34272),
        tcaComputeMbPowerStatsInputCurrentAvg(34273),
        tcaComputeMbPowerStatsConsumedPower(34277),
        tcaComputeMbPowerStatsConsumedPowerMin(34279),
        tcaComputeMbPowerStatsConsumedPowerMax(34280),
        tcaComputeMbPowerStatsConsumedPowerAvg(34281),
        tcaComputeMbTempStatsFmTempSenIo(34287),
        tcaComputeMbTempStatsFmTempSenIoMin(34289),
        tcaComputeMbTempStatsFmTempSenIoMax(34290),
        tcaComputeMbTempStatsFmTempSenIoAvg(34291),
        tcaComputeMbTempStatsFmTempSenRear(34295),
        tcaComputeMbTempStatsFmTempSenRearMin(34297),
        tcaComputeMbTempStatsFmTempSenRearMax(34298),
        tcaComputeMbTempStatsFmTempSenRearAvg(34299),
        tcaComputeMbTempStatsFmTempSenRearl(34303),
        tcaComputeMbTempStatsFmTempSenRearlmin(34305),
        tcaComputeMbTempStatsFmTempSenRearlmax(34306),
        tcaComputeMbTempStatsFmTempSenRearlavg(34307),
        tcaComputeMbTempStatsFmTempSenRearr(34311),
        tcaComputeMbTempStatsFmTempSenRearrmin(34313),
        tcaComputeMbTempStatsFmTempSenRearrmax(34314),
        tcaComputeMbTempStatsFmTempSenRearravg(34315),
        tcaComputeRackUnitMbTempStatsFrontTemp(34321),
        tcaComputeRackUnitMbTempStatsFrontTempMin(34323),
        tcaComputeRackUnitMbTempStatsFrontTempMax(34324),
        tcaComputeRackUnitMbTempStatsFrontTempAvg(34325),
        tcaComputeRackUnitMbTempStatsRearTemp(34329),
        tcaComputeRackUnitMbTempStatsRearTempMin(34331),
        tcaComputeRackUnitMbTempStatsRearTempMax(34332),
        tcaComputeRackUnitMbTempStatsRearTempAvg(34333),
        tcaComputeRackUnitMbTempStatsAmbientTemp(34337),
        tcaComputeRackUnitMbTempStatsAmbientTempMin(34339),
        tcaComputeRackUnitMbTempStatsAmbientTempMax(34340),
        tcaComputeRackUnitMbTempStatsAmbientTempAvg(34341),
        tcaComputeRackUnitMbTempStatsIoh1Temp(34345),
        tcaComputeRackUnitMbTempStatsIoh1TempMin(34347),
        tcaComputeRackUnitMbTempStatsIoh1TempMax(34348),
        tcaComputeRackUnitMbTempStatsIoh1TempAvg(34349),
        tcaComputeRackUnitMbTempStatsIoh2Temp(34353),
        tcaComputeRackUnitMbTempStatsIoh2TempMin(34355),
        tcaComputeRackUnitMbTempStatsIoh2TempMax(34356),
        tcaComputeRackUnitMbTempStatsIoh2TempAvg(34357),
        tcaComputeIohubEnvStatsTemperature(34363),
        tcaComputeIohubEnvStatsTemperatureMin(34365),
        tcaComputeIohubEnvStatsTemperatureMax(34366),
        tcaComputeIohubEnvStatsTemperatureAvg(34367),
        tcaComputePcieFatalProtocolStatsFlowControlErrors(34372),
        tcaComputePcieFatalProtocolStatsDllpErrors(34383),
        tcaComputePcieFatalReceiveStatsUnsupportedRequestErrors(34395),
        tcaComputePcieFatalReceiveStatsErrFatalErrors(34406),
        tcaComputePcieFatalReceiveStatsErrNonFatalErrors(34417),
        tcaComputePcieFatalReceiveStatsBufferOverflowErrors(34428),
        tcaComputePcieFatalCompletionStatsUnexpectedErrors(34440),
        tcaComputePcieFatalCompletionStatsTimeoutErrors(34451),
        tcaComputePcieFatalCompletionStatsAbortErrors(34462),
        tcaComputePcieFatalStatsSurpriseLinkDownErrors(34474),
        tcaComputePcieFatalStatsPoisonedtlperrors(34485),
        tcaComputePcieFatalStatsAcsViolationErrors(34496),
        tcaComputePcieFatalStatsMalformedtlperrors(34507),
        tcaPowerGroupStatsPower(34841),
        tcaPowerGroupStatsPowerMin(34843),
        tcaPowerGroupStatsPowerMax(34844),
        tcaPowerGroupStatsPowerAvg(34845),
        tcaSwEnvStatsMainBoardOutlet1(35108),
        tcaSwEnvStatsMainBoardOutlet1Min(35110),
        tcaSwEnvStatsMainBoardOutlet1Max(35111),
        tcaSwEnvStatsMainBoardOutlet1Avg(35112),
        tcaSwEnvStatsMainBoardOutlet2(35116),
        tcaSwEnvStatsMainBoardOutlet2Min(35118),
        tcaSwEnvStatsMainBoardOutlet2Max(35119),
        tcaSwEnvStatsMainBoardOutlet2Avg(35120),
        tcaSwEnvStatsFanCtrlrInlet1(35124),
        tcaSwEnvStatsFanCtrlrInlet1Min(35126),
        tcaSwEnvStatsFanCtrlrInlet1Max(35127),
        tcaSwEnvStatsFanCtrlrInlet1Avg(35128),
        tcaSwEnvStatsFanCtrlrInlet2(35132),
        tcaSwEnvStatsFanCtrlrInlet2Min(35134),
        tcaSwEnvStatsFanCtrlrInlet2Max(35135),
        tcaSwEnvStatsFanCtrlrInlet2Avg(35136),
        tcaSwEnvStatsFanCtrlrInlet3(35140),
        tcaSwEnvStatsFanCtrlrInlet3Min(35142),
        tcaSwEnvStatsFanCtrlrInlet3Max(35143),
        tcaSwEnvStatsFanCtrlrInlet3Avg(35144),
        tcaSwEnvStatsFanCtrlrInlet4(35148),
        tcaSwEnvStatsFanCtrlrInlet4Min(35150),
        tcaSwEnvStatsFanCtrlrInlet4Max(35151),
        tcaSwEnvStatsFanCtrlrInlet4Avg(35152),
        tcaSwEnvStatsPsuCtrlrInlet1(35156),
        tcaSwEnvStatsPsuCtrlrInlet1Min(35158),
        tcaSwEnvStatsPsuCtrlrInlet1Max(35159),
        tcaSwEnvStatsPsuCtrlrInlet1Avg(35160),
        tcaSwEnvStatsPsuCtrlrInlet2(35164),
        tcaSwEnvStatsPsuCtrlrInlet2Min(35166),
        tcaSwEnvStatsPsuCtrlrInlet2Max(35167),
        tcaSwEnvStatsPsuCtrlrInlet2Avg(35168),
        tcaSwCardEnvStatsSlotOutlet1(35174),
        tcaSwCardEnvStatsSlotOutlet1Min(35176),
        tcaSwCardEnvStatsSlotOutlet1Max(35177),
        tcaSwCardEnvStatsSlotOutlet1Avg(35178),
        tcaSwCardEnvStatsSlotOutlet2(35182),
        tcaSwCardEnvStatsSlotOutlet2Min(35184),
        tcaSwCardEnvStatsSlotOutlet2Max(35185),
        tcaSwCardEnvStatsSlotOutlet2Avg(35186),
        tcaSwCardEnvStatsSlotOutlet3(35190),
        tcaSwCardEnvStatsSlotOutlet3Min(35192),
        tcaSwCardEnvStatsSlotOutlet3Max(35193),
        tcaSwCardEnvStatsSlotOutlet3Avg(35194),
        tcaSwSystemStatsMemAvailable(35200),
        tcaSwSystemStatsMemAvailableMin(35202),
        tcaSwSystemStatsMemAvailableMax(35203),
        tcaSwSystemStatsMemAvailableAvg(35204),
        tcaSwSystemStatsMemCached(35208),
        tcaSwSystemStatsMemCachedMin(35210),
        tcaSwSystemStatsMemCachedMax(35211),
        tcaSwSystemStatsMemCachedAvg(35212),
        tcaSwSystemStatsLoad(35216),
        tcaSwSystemStatsLoadMin(35218),
        tcaSwSystemStatsLoadMax(35219),
        tcaSwSystemStatsLoadAvg(35220),
        tcaAdaptorEthPortStatsTotalPacketsDelta(35844),
        tcaAdaptorEthPortStatsTotalPacketsDeltaMin(35845),
        tcaAdaptorEthPortStatsTotalPacketsDeltaMax(35846),
        tcaAdaptorEthPortStatsTotalPacketsDeltaAvg(35847),
        tcaAdaptorEthPortStatsGoodPacketsDelta(35854),
        tcaAdaptorEthPortStatsGoodPacketsDeltaMin(35855),
        tcaAdaptorEthPortStatsGoodPacketsDeltaMax(35856),
        tcaAdaptorEthPortStatsGoodPacketsDeltaAvg(35857),
        tcaAdaptorEthPortStatsVlanPacketsDelta(35864),
        tcaAdaptorEthPortStatsVlanPacketsDeltaMin(35865),
        tcaAdaptorEthPortStatsVlanPacketsDeltaMax(35866),
        tcaAdaptorEthPortStatsVlanPacketsDeltaAvg(35867),
        tcaAdaptorEthPortStatsPausePacketsDelta(35874),
        tcaAdaptorEthPortStatsPausePacketsDeltaMin(35875),
        tcaAdaptorEthPortStatsPausePacketsDeltaMax(35876),
        tcaAdaptorEthPortStatsPausePacketsDeltaAvg(35877),
        tcaAdaptorEthPortStatsPerPriorityPausePacketsDelta(35884),
        tcaAdaptorEthPortStatsPerPriorityPausePacketsDeltaMin(35885),
        tcaAdaptorEthPortStatsPerPriorityPausePacketsDeltaMax(35886),
        tcaAdaptorEthPortStatsPerPriorityPausePacketsDeltaAvg(35887),
        tcaAdaptorEthPortStatsPppPacketsDelta(35894),
        tcaAdaptorEthPortStatsPppPacketsDeltaMin(35895),
        tcaAdaptorEthPortStatsPppPacketsDeltaMax(35896),
        tcaAdaptorEthPortStatsPppPacketsDeltaAvg(35897),
        tcaAdaptorEthPortBySizeSmallStatsLessThan64Delta(35907),
        tcaAdaptorEthPortBySizeSmallStatsLessThan64DeltaMin(35908),
        tcaAdaptorEthPortBySizeSmallStatsLessThan64DeltaMax(35909),
        tcaAdaptorEthPortBySizeSmallStatsLessThan64DeltaAvg(35910),
        tcaAdaptorEthPortBySizeSmallStatsEquals64Delta(35917),
        tcaAdaptorEthPortBySizeSmallStatsEquals64DeltaMin(35918),
        tcaAdaptorEthPortBySizeSmallStatsEquals64DeltaMax(35919),
        tcaAdaptorEthPortBySizeSmallStatsEquals64DeltaAvg(35920),
        tcaAdaptorEthPortBySizeSmallStatsLessThan128Delta(35927),
        tcaAdaptorEthPortBySizeSmallStatsLessThan128DeltaMin(35928),
        tcaAdaptorEthPortBySizeSmallStatsLessThan128DeltaMax(35929),
        tcaAdaptorEthPortBySizeSmallStatsLessThan128DeltaAvg(35930),
        tcaAdaptorEthPortBySizeSmallStatsLessThan256Delta(35937),
        tcaAdaptorEthPortBySizeSmallStatsLessThan256DeltaMin(35938),
        tcaAdaptorEthPortBySizeSmallStatsLessThan256DeltaMax(35939),
        tcaAdaptorEthPortBySizeSmallStatsLessThan256DeltaAvg(35940),
        tcaAdaptorEthPortBySizeSmallStatsLessThan512Delta(35947),
        tcaAdaptorEthPortBySizeSmallStatsLessThan512DeltaMin(35948),
        tcaAdaptorEthPortBySizeSmallStatsLessThan512DeltaMax(35949),
        tcaAdaptorEthPortBySizeSmallStatsLessThan512DeltaAvg(35950),
        tcaAdaptorEthPortBySizeSmallStatsLessThan1024Delta(35957),
        tcaAdaptorEthPortBySizeSmallStatsLessThan1024DeltaMin(35958),
        tcaAdaptorEthPortBySizeSmallStatsLessThan1024DeltaMax(35959),
        tcaAdaptorEthPortBySizeSmallStatsLessThan1024DeltaAvg(35960),
        tcaAdaptorEthPortBySizeLargeStatsLessThanOrEqualTo1518Delta(35970),
        tcaAdaptorEthPortBySizeLargeStatsLessThanOrEqualTo1518DeltaMin(35971),
        tcaAdaptorEthPortBySizeLargeStatsLessThanOrEqualTo1518DeltaMax(35972),
        tcaAdaptorEthPortBySizeLargeStatsLessThanOrEqualTo1518DeltaAvg(35973),
        tcaAdaptorEthPortBySizeLargeStatsLessThan2048Delta(35980),
        tcaAdaptorEthPortBySizeLargeStatsLessThan2048DeltaMin(35981),
        tcaAdaptorEthPortBySizeLargeStatsLessThan2048DeltaMax(35982),
        tcaAdaptorEthPortBySizeLargeStatsLessThan2048DeltaAvg(35983),
        tcaAdaptorEthPortBySizeLargeStatsLessThan4096Delta(35990),
        tcaAdaptorEthPortBySizeLargeStatsLessThan4096DeltaMin(35991),
        tcaAdaptorEthPortBySizeLargeStatsLessThan4096DeltaMax(35992),
        tcaAdaptorEthPortBySizeLargeStatsLessThan4096DeltaAvg(35993),
        tcaAdaptorEthPortBySizeLargeStatsLessThan8192Delta(36000),
        tcaAdaptorEthPortBySizeLargeStatsLessThan8192DeltaMin(36001),
        tcaAdaptorEthPortBySizeLargeStatsLessThan8192DeltaMax(36002),
        tcaAdaptorEthPortBySizeLargeStatsLessThan8192DeltaAvg(36003),
        tcaAdaptorEthPortBySizeLargeStatsLessThan9216Delta(36010),
        tcaAdaptorEthPortBySizeLargeStatsLessThan9216DeltaMin(36011),
        tcaAdaptorEthPortBySizeLargeStatsLessThan9216DeltaMax(36012),
        tcaAdaptorEthPortBySizeLargeStatsLessThan9216DeltaAvg(36013),
        tcaAdaptorEthPortBySizeLargeStatsGreaterThanOrEqualTo9216Delta(36020),
        tcaAdaptorEthPrtBySizeLargeStatsGreaterThanOrEqualTo9216DeltaMin(36021),
        tcaAdaptorEthPrtBySizeLargeStatsGreaterThanOrEqualTo9216DeltaMax(36022),
        tcaAdaptorEthPrtBySizeLargeStatsGreaterThanOrEqualTo9216DeltaAvg(36023),
        tcaAdaptorEthPortBySizeLargeStatsNoBreakdownGreaterThan1518Delta(36030),
        tcaAdaptorEthPortBySizeLargeStatsNoBrkdnGreaterThan1518DeltaMin(36031),
        tcaAdaptorEthPortBySizeLargeStatsNoBrkdnGreaterThan1518DeltaMax(36032),
        tcaAdaptorEthPortBySizeLargeStatsNoBrkdnGreaterThan1518DeltaAvg(36033),
        tcaAdaptorEthPortOutsizedStatsOversizedPacketsDelta(36043),
        tcaAdaptorEthPortOutsizedStatsOversizedPacketsDeltaMin(36044),
        tcaAdaptorEthPortOutsizedStatsOversizedPacketsDeltaMax(36045),
        tcaAdaptorEthPortOutsizedStatsOversizedPacketsDeltaAvg(36046),
        tcaAdaptorEthPortOutsizedStatsOversizedGoodCrcPacketsDelta(36053),
        tcaAdaptorEthPortOutsizedStatsOversizedGoodCrcPacketsDeltaMin(36054),
        tcaAdaptorEthPortOutsizedStatsOversizedGoodCrcPacketsDeltaMax(36055),
        tcaAdaptorEthPortOutsizedStatsOversizedGoodCrcPacketsDeltaAvg(36056),
        tcaAdaptorEthPortOutsizedStatsOversizedBadCrcPacketsDelta(36063),
        tcaAdaptorEthPortOutsizedStatsOversizedBadCrcPacketsDeltaMin(36064),
        tcaAdaptorEthPortOutsizedStatsOversizedBadCrcPacketsDeltaMax(36065),
        tcaAdaptorEthPortOutsizedStatsOversizedBadCrcPacketsDeltaAvg(36066),
        tcaAdaptorEthPortOutsizedStatsUndersizedGoodCrcPacketsDelta(36073),
        tcaAdaptorEthPortOutsizedStatsUndersizedGoodCrcPacketsDeltaMin(36074),
        tcaAdaptorEthPortOutsizedStatsUndersizedGoodCrcPacketsDeltaMax(36075),
        tcaAdaptorEthPortOutsizedStatsUndersizedGoodCrcPacketsDeltaAvg(36076),
        tcaAdaptorEthPortOutsizedStatsUndersizedBadCrcPacketsDelta(36083),
        tcaAdaptorEthPortOutsizedStatsUndersizedBadCrcPacketsDeltaMin(36084),
        tcaAdaptorEthPortOutsizedStatsUndersizedBadCrcPacketsDeltaMax(36085),
        tcaAdaptorEthPortOutsizedStatsUndersizedBadCrcPacketsDeltaAvg(36086),
        tcaAdaptorEthPortMcastStatsUnicastPacketsDelta(36096),
        tcaAdaptorEthPortMcastStatsUnicastPacketsDeltaMin(36097),
        tcaAdaptorEthPortMcastStatsUnicastPacketsDeltaMax(36098),
        tcaAdaptorEthPortMcastStatsUnicastPacketsDeltaAvg(36099),
        tcaAdaptorEthPortMcastStatsMulticastPacketsDelta(36106),
        tcaAdaptorEthPortMcastStatsMulticastPacketsDeltaMin(36107),
        tcaAdaptorEthPortMcastStatsMulticastPacketsDeltaMax(36108),
        tcaAdaptorEthPortMcastStatsMulticastPacketsDeltaAvg(36109),
        tcaAdaptorEthPortMcastStatsBroadcastPacketsDelta(36116),
        tcaAdaptorEthPortMcastStatsBroadcastPacketsDeltaMin(36117),
        tcaAdaptorEthPortMcastStatsBroadcastPacketsDeltaMax(36118),
        tcaAdaptorEthPortMcastStatsBroadcastPacketsDeltaAvg(36119),
        tcaAdaptorEthPortErrStatsMacDiscardedPacketsDelta(36129),
        tcaAdaptorEthPortErrStatsMacDiscardedPacketsDeltaMin(36130),
        tcaAdaptorEthPortErrStatsMacDiscardedPacketsDeltaMax(36131),
        tcaAdaptorEthPortErrStatsMacDiscardedPacketsDeltaAvg(36132),
        tcaAdaptorEthPortErrStatsBadCrcPacketsDelta(36139),
        tcaAdaptorEthPortErrStatsBadCrcPacketsDeltaMin(36140),
        tcaAdaptorEthPortErrStatsBadCrcPacketsDeltaMax(36141),
        tcaAdaptorEthPortErrStatsBadCrcPacketsDeltaAvg(36142),
        tcaAdaptorEthPortErrStatsBadLengthPacketsDelta(36149),
        tcaAdaptorEthPortErrStatsBadLengthPacketsDeltaMin(36150),
        tcaAdaptorEthPortErrStatsBadLengthPacketsDeltaMax(36151),
        tcaAdaptorEthPortErrStatsBadLengthPacketsDeltaAvg(36152),
        tcaAdaptorFcPortStatsRxFramesDelta(36161),
        tcaAdaptorFcPortStatsRxFramesDeltaMin(36162),
        tcaAdaptorFcPortStatsRxFramesDeltaMax(36163),
        tcaAdaptorFcPortStatsRxFramesDeltaAvg(36164),
        tcaAdaptorFcPortStatsTxFramesDelta(36171),
        tcaAdaptorFcPortStatsTxFramesDeltaMin(36172),
        tcaAdaptorFcPortStatsTxFramesDeltaMax(36173),
        tcaAdaptorFcPortStatsTxFramesDeltaAvg(36174),
        tcaAdaptorFcPortStatsRxBadFramesDelta(36181),
        tcaAdaptorFcPortStatsRxBadFramesDeltaMin(36182),
        tcaAdaptorFcPortStatsRxBadFramesDeltaMax(36183),
        tcaAdaptorFcPortStatsRxBadFramesDeltaAvg(36184),
        tcaAdaptorFcPortStatsTxBadFramesDelta(36191),
        tcaAdaptorFcPortStatsTxBadFramesDeltaMin(36192),
        tcaAdaptorFcPortStatsTxBadFramesDeltaMax(36193),
        tcaAdaptorFcPortStatsTxBadFramesDeltaAvg(36194),
        tcaAdaptorVnicStatsPacketsTxDelta(36203),
        tcaAdaptorVnicStatsPacketsTxDeltaMin(36204),
        tcaAdaptorVnicStatsPacketsTxDeltaMax(36205),
        tcaAdaptorVnicStatsPacketsTxDeltaAvg(36206),
        tcaAdaptorVnicStatsPacketsRxDelta(36213),
        tcaAdaptorVnicStatsPacketsRxDeltaMin(36214),
        tcaAdaptorVnicStatsPacketsRxDeltaMax(36215),
        tcaAdaptorVnicStatsPacketsRxDeltaAvg(36216),
        tcaAdaptorVnicStatsBytesTxDelta(36223),
        tcaAdaptorVnicStatsBytesTxDeltaMin(36224),
        tcaAdaptorVnicStatsBytesTxDeltaMax(36225),
        tcaAdaptorVnicStatsBytesTxDeltaAvg(36226),
        tcaAdaptorVnicStatsBytesRxDelta(36233),
        tcaAdaptorVnicStatsBytesRxDeltaMin(36234),
        tcaAdaptorVnicStatsBytesRxDeltaMax(36235),
        tcaAdaptorVnicStatsBytesRxDeltaAvg(36236),
        tcaAdaptorVnicStatsErrorsTxDelta(36243),
        tcaAdaptorVnicStatsErrorsTxDeltaMin(36244),
        tcaAdaptorVnicStatsErrorsTxDeltaMax(36245),
        tcaAdaptorVnicStatsErrorsTxDeltaAvg(36246),
        tcaAdaptorVnicStatsErrorsRxDelta(36253),
        tcaAdaptorVnicStatsErrorsRxDeltaMin(36254),
        tcaAdaptorVnicStatsErrorsRxDeltaMax(36255),
        tcaAdaptorVnicStatsErrorsRxDeltaAvg(36256),
        tcaAdaptorVnicStatsDroppedTxDelta(36263),
        tcaAdaptorVnicStatsDroppedTxDeltaMin(36264),
        tcaAdaptorVnicStatsDroppedTxDeltaMax(36265),
        tcaAdaptorVnicStatsDroppedTxDeltaAvg(36266),
        tcaAdaptorVnicStatsDroppedRxDelta(36273),
        tcaAdaptorVnicStatsDroppedRxDeltaMin(36274),
        tcaAdaptorVnicStatsDroppedRxDeltaMax(36275),
        tcaAdaptorVnicStatsDroppedRxDeltaAvg(36276),
        tcaAdaptorFcIffc4StatsInputRequestsDelta(36285),
        tcaAdaptorFcIffc4StatsInputRequestsDeltaMin(36286),
        tcaAdaptorFcIffc4StatsInputRequestsDeltaMax(36287),
        tcaAdaptorFcIffc4StatsInputRequestsDeltaAvg(36288),
        tcaAdaptorFcIffc4StatsOutputRequestsDelta(36295),
        tcaAdaptorFcIffc4StatsOutputRequestsDeltaMin(36296),
        tcaAdaptorFcIffc4StatsOutputRequestsDeltaMax(36297),
        tcaAdaptorFcIffc4StatsOutputRequestsDeltaAvg(36298),
        tcaAdaptorFcIffc4StatsControlRequestsDelta(36305),
        tcaAdaptorFcIffc4StatsControlRequestsDeltaMin(36306),
        tcaAdaptorFcIffc4StatsControlRequestsDeltaMax(36307),
        tcaAdaptorFcIffc4StatsControlRequestsDeltaAvg(36308),
        tcaAdaptorFcIffc4StatsInputMegabytesDelta(36315),
        tcaAdaptorFcIffc4StatsInputMegabytesDeltaMin(36316),
        tcaAdaptorFcIffc4StatsInputMegabytesDeltaMax(36317),
        tcaAdaptorFcIffc4StatsInputMegabytesDeltaAvg(36318),
        tcaAdaptorFcIffc4StatsOutputMegabytesDelta(36325),
        tcaAdaptorFcIffc4StatsOutputMegabytesDeltaMin(36326),
        tcaAdaptorFcIffc4StatsOutputMegabytesDeltaMax(36327),
        tcaAdaptorFcIffc4StatsOutputMegabytesDeltaAvg(36328),
        tcaAdaptorMenloBaseErrorStatsCorrectableErrorsDelta(36337),
        tcaAdaptorMenloBaseErrorStatsCorrectableErrorsDeltaMin(36338),
        tcaAdaptorMenloBaseErrorStatsCorrectableErrorsDeltaMax(36339),
        tcaAdaptorMenloBaseErrorStatsCorrectableErrorsDeltaAvg(36340),
        tcaAdaptorMenloBaseErrorStatsUncorrectableErrorsDelta(36347),
        tcaAdaptorMenloBaseErrorStatsUncorrectableErrorsDeltaMin(36348),
        tcaAdaptorMenloBaseErrorStatsUncorrectableErrorsDeltaMax(36349),
        tcaAdaptorMenloBaseErrorStatsUncorrectableErrorsDeltaAvg(36350),
        tcaAdaptorMenloMcpuStatsDropAclDelta(36360),
        tcaAdaptorMenloMcpuStatsDropAclDeltaMin(36361),
        tcaAdaptorMenloMcpuStatsDropAclDeltaMax(36362),
        tcaAdaptorMenloMcpuStatsDropAclDeltaAvg(36363),
        tcaAdaptorMenloMcpuStatsDropOverrunDelta(36370),
        tcaAdaptorMenloMcpuStatsDropOverrunDeltaMin(36371),
        tcaAdaptorMenloMcpuStatsDropOverrunDeltaMax(36372),
        tcaAdaptorMenloMcpuStatsDropOverrunDeltaAvg(36373),
        tcaAdaptorMenloMcpuStatsDropRuntDelta(36380),
        tcaAdaptorMenloMcpuStatsDropRuntDeltaMin(36381),
        tcaAdaptorMenloMcpuStatsDropRuntDeltaMax(36382),
        tcaAdaptorMenloMcpuStatsDropRuntDeltaAvg(36383),
        tcaAdaptorMenloMcpuStatsTruncateOverrunDelta(36390),
        tcaAdaptorMenloMcpuStatsTruncateOverrunDeltaMin(36391),
        tcaAdaptorMenloMcpuStatsTruncateOverrunDeltaMax(36392),
        tcaAdaptorMenloMcpuStatsTruncateOverrunDeltaAvg(36393),
        tcaAdaptorMenloMcpuErrorStatsCorrectableErrorsDelta(36403),
        tcaAdaptorMenloMcpuErrorStatsCorrectableErrorsDeltaMin(36404),
        tcaAdaptorMenloMcpuErrorStatsCorrectableErrorsDeltaMax(36405),
        tcaAdaptorMenloMcpuErrorStatsCorrectableErrorsDeltaAvg(36406),
        tcaAdaptorMenloMcpuErrorStatsPopErrorsDelta(36413),
        tcaAdaptorMenloMcpuErrorStatsPopErrorsDeltaMin(36414),
        tcaAdaptorMenloMcpuErrorStatsPopErrorsDeltaMax(36415),
        tcaAdaptorMenloMcpuErrorStatsPopErrorsDeltaAvg(36416),
        tcaAdaptorMenloMcpuErrorStatsPushErrorsDelta(36423),
        tcaAdaptorMenloMcpuErrorStatsPushErrorsDeltaMin(36424),
        tcaAdaptorMenloMcpuErrorStatsPushErrorsDeltaMax(36425),
        tcaAdaptorMenloMcpuErrorStatsPushErrorsDeltaAvg(36426),
        tcaAdaptorMenloMcpuErrorStatsUncorrectableErrorsDelta(36433),
        tcaAdaptorMenloMcpuErrorStatsUncorrectableErrorsDeltaMin(36434),
        tcaAdaptorMenloMcpuErrorStatsUncorrectableErrorsDeltaMax(36435),
        tcaAdaptorMenloMcpuErrorStatsUncorrectableErrorsDeltaAvg(36436),
        tcaAdaptorMenloEthStatsDropOverrunDelta(36446),
        tcaAdaptorMenloEthStatsDropOverrunDeltaMin(36447),
        tcaAdaptorMenloEthStatsDropOverrunDeltaMax(36448),
        tcaAdaptorMenloEthStatsDropOverrunDeltaAvg(36449),
        tcaAdaptorMenloEthStatsDropRuntDelta(36456),
        tcaAdaptorMenloEthStatsDropRuntDeltaMin(36457),
        tcaAdaptorMenloEthStatsDropRuntDeltaMax(36458),
        tcaAdaptorMenloEthStatsDropRuntDeltaAvg(36459),
        tcaAdaptorMenloEthStatsTruncateOverrunDelta(36466),
        tcaAdaptorMenloEthStatsTruncateOverrunDeltaMin(36467),
        tcaAdaptorMenloEthStatsTruncateOverrunDeltaMax(36468),
        tcaAdaptorMenloEthStatsTruncateOverrunDeltaAvg(36469),
        tcaAdaptorMenloEthErrorStatsCorrectableErrorsDelta(36479),
        tcaAdaptorMenloEthErrorStatsCorrectableErrorsDeltaMin(36480),
        tcaAdaptorMenloEthErrorStatsCorrectableErrorsDeltaMax(36481),
        tcaAdaptorMenloEthErrorStatsCorrectableErrorsDeltaAvg(36482),
        tcaAdaptorMenloEthErrorStatsDropAclDelta(36489),
        tcaAdaptorMenloEthErrorStatsDropAclDeltaMin(36490),
        tcaAdaptorMenloEthErrorStatsDropAclDeltaMax(36491),
        tcaAdaptorMenloEthErrorStatsDropAclDeltaAvg(36492),
        tcaAdaptorMenloEthErrorStatsPopErrorsDelta(36499),
        tcaAdaptorMenloEthErrorStatsPopErrorsDeltaMin(36500),
        tcaAdaptorMenloEthErrorStatsPopErrorsDeltaMax(36501),
        tcaAdaptorMenloEthErrorStatsPopErrorsDeltaAvg(36502),
        tcaAdaptorMenloEthErrorStatsPushErrorsDelta(36509),
        tcaAdaptorMenloEthErrorStatsPushErrorsDeltaMin(36510),
        tcaAdaptorMenloEthErrorStatsPushErrorsDeltaMax(36511),
        tcaAdaptorMenloEthErrorStatsPushErrorsDeltaAvg(36512),
        tcaAdaptorMenloEthErrorStatsUncorrectableErrorsDelta(36519),
        tcaAdaptorMenloEthErrorStatsUncorrectableErrorsDeltaMin(36520),
        tcaAdaptorMenloEthErrorStatsUncorrectableErrorsDeltaMax(36521),
        tcaAdaptorMenloEthErrorStatsUncorrectableErrorsDeltaAvg(36522),
        tcaAdaptorMenloFcStatsDropAclDelta(36532),
        tcaAdaptorMenloFcStatsDropAclDeltaMin(36533),
        tcaAdaptorMenloFcStatsDropAclDeltaMax(36534),
        tcaAdaptorMenloFcStatsDropAclDeltaAvg(36535),
        tcaAdaptorMenloFcStatsDropOverrunDelta(36542),
        tcaAdaptorMenloFcStatsDropOverrunDeltaMin(36543),
        tcaAdaptorMenloFcStatsDropOverrunDeltaMax(36544),
        tcaAdaptorMenloFcStatsDropOverrunDeltaAvg(36545),
        tcaAdaptorMenloFcStatsDropRuntDelta(36552),
        tcaAdaptorMenloFcStatsDropRuntDeltaMin(36553),
        tcaAdaptorMenloFcStatsDropRuntDeltaMax(36554),
        tcaAdaptorMenloFcStatsDropRuntDeltaAvg(36555),
        tcaAdaptorMenloFcStatsTruncateOverrunDelta(36562),
        tcaAdaptorMenloFcStatsTruncateOverrunDeltaMin(36563),
        tcaAdaptorMenloFcStatsTruncateOverrunDeltaMax(36564),
        tcaAdaptorMenloFcStatsTruncateOverrunDeltaAvg(36565),
        tcaAdaptorMenloFcErrorStatsCorrectableErrorsDelta(36575),
        tcaAdaptorMenloFcErrorStatsCorrectableErrorsDeltaMin(36576),
        tcaAdaptorMenloFcErrorStatsCorrectableErrorsDeltaMax(36577),
        tcaAdaptorMenloFcErrorStatsCorrectableErrorsDeltaAvg(36578),
        tcaAdaptorMenloFcErrorStatsPopErrorsDelta(36585),
        tcaAdaptorMenloFcErrorStatsPopErrorsDeltaMin(36586),
        tcaAdaptorMenloFcErrorStatsPopErrorsDeltaMax(36587),
        tcaAdaptorMenloFcErrorStatsPopErrorsDeltaAvg(36588),
        tcaAdaptorMenloFcErrorStatsPushErrorsDelta(36595),
        tcaAdaptorMenloFcErrorStatsPushErrorsDeltaMin(36596),
        tcaAdaptorMenloFcErrorStatsPushErrorsDeltaMax(36597),
        tcaAdaptorMenloFcErrorStatsPushErrorsDeltaAvg(36598),
        tcaAdaptorMenloFcErrorStatsUncorrectableErrorsDelta(36605),
        tcaAdaptorMenloFcErrorStatsUncorrectableErrorsDeltaMin(36606),
        tcaAdaptorMenloFcErrorStatsUncorrectableErrorsDeltaMax(36607),
        tcaAdaptorMenloFcErrorStatsUncorrectableErrorsDeltaAvg(36608),
        tcaAdaptorMenloqstatsDropOverrunN0Delta(36619),
        tcaAdaptorMenloqstatsDropOverrunN0DeltaMin(36620),
        tcaAdaptorMenloqstatsDropOverrunN0DeltaMax(36621),
        tcaAdaptorMenloqstatsDropOverrunN0DeltaAvg(36622),
        tcaAdaptorMenloqstatsDropOverrunN1Delta(36629),
        tcaAdaptorMenloqstatsDropOverrunN1DeltaMin(36630),
        tcaAdaptorMenloqstatsDropOverrunN1DeltaMax(36631),
        tcaAdaptorMenloqstatsDropOverrunN1DeltaAvg(36632),
        tcaAdaptorMenloqstatsTruncateOverrunN0Delta(36639),
        tcaAdaptorMenloqstatsTruncateOverrunN0DeltaMin(36640),
        tcaAdaptorMenloqstatsTruncateOverrunN0DeltaMax(36641),
        tcaAdaptorMenloqstatsTruncateOverrunN0DeltaAvg(36642),
        tcaAdaptorMenloqstatsTruncateOverrunN1Delta(36649),
        tcaAdaptorMenloqstatsTruncateOverrunN1DeltaMin(36650),
        tcaAdaptorMenloqstatsTruncateOverrunN1DeltaMax(36651),
        tcaAdaptorMenloqstatsTruncateOverrunN1DeltaAvg(36652),
        tcaAdaptorMenloqerrorStatsCorrectableErrorsDelta(36663),
        tcaAdaptorMenloqerrorStatsCorrectableErrorsDeltaMin(36664),
        tcaAdaptorMenloqerrorStatsCorrectableErrorsDeltaMax(36665),
        tcaAdaptorMenloqerrorStatsCorrectableErrorsDeltaAvg(36666),
        tcaAdaptorMenloqerrorStatsPopErrorsDelta(36673),
        tcaAdaptorMenloqerrorStatsPopErrorsDeltaMin(36674),
        tcaAdaptorMenloqerrorStatsPopErrorsDeltaMax(36675),
        tcaAdaptorMenloqerrorStatsPopErrorsDeltaAvg(36676),
        tcaAdaptorMenloqerrorStatsPushErrorsDelta(36683),
        tcaAdaptorMenloqerrorStatsPushErrorsDeltaMin(36684),
        tcaAdaptorMenloqerrorStatsPushErrorsDeltaMax(36685),
        tcaAdaptorMenloqerrorStatsPushErrorsDeltaAvg(36686),
        tcaAdaptorMenloqerrorStatsUncorrectableErrorsDelta(36693),
        tcaAdaptorMenloqerrorStatsUncorrectableErrorsDeltaMin(36694),
        tcaAdaptorMenloqerrorStatsUncorrectableErrorsDeltaMax(36695),
        tcaAdaptorMenloqerrorStatsUncorrectableErrorsDeltaAvg(36696),
        tcaAdaptorMenloNetEgStatsLearnReqDropDelta(36706),
        tcaAdaptorMenloNetEgStatsLearnReqDropDeltaMin(36707),
        tcaAdaptorMenloNetEgStatsLearnReqDropDeltaMax(36708),
        tcaAdaptorMenloNetEgStatsLearnReqDropDeltaAvg(36709),
        tcaAdaptorMenloNetEgStatsDropCmdDelta(36716),
        tcaAdaptorMenloNetEgStatsDropCmdDeltaMin(36717),
        tcaAdaptorMenloNetEgStatsDropCmdDeltaMax(36718),
        tcaAdaptorMenloNetEgStatsDropCmdDeltaAvg(36719),
        tcaAdaptorMenloNetEgStatsDropLifCfgInvalidDelta(36726),
        tcaAdaptorMenloNetEgStatsDropLifCfgInvalidDeltaMin(36727),
        tcaAdaptorMenloNetEgStatsDropLifCfgInvalidDeltaMax(36728),
        tcaAdaptorMenloNetEgStatsDropLifCfgInvalidDeltaAvg(36729),
        tcaAdaptorMenloNetEgStatsDropLifMapNoHitDelta(36736),
        tcaAdaptorMenloNetEgStatsDropLifMapNoHitDeltaMin(36737),
        tcaAdaptorMenloNetEgStatsDropLifMapNoHitDeltaMax(36738),
        tcaAdaptorMenloNetEgStatsDropLifMapNoHitDeltaAvg(36739),
        tcaAdaptorMenloNetEgStatsDropSrcBindDelta(36746),
        tcaAdaptorMenloNetEgStatsDropSrcBindDeltaMin(36747),
        tcaAdaptorMenloNetEgStatsDropSrcBindDeltaMax(36748),
        tcaAdaptorMenloNetEgStatsDropSrcBindDeltaAvg(36749),
        tcaAdaptorMenloNetInStatsFwdLookupNoHitDelta(36759),
        tcaAdaptorMenloNetInStatsFwdLookupNoHitDeltaMin(36760),
        tcaAdaptorMenloNetInStatsFwdLookupNoHitDeltaMax(36761),
        tcaAdaptorMenloNetInStatsFwdLookupNoHitDeltaAvg(36762),
        tcaAdaptorMenloNetInStatsDropFcMulticastDelta(36769),
        tcaAdaptorMenloNetInStatsDropFcMulticastDeltaMin(36770),
        tcaAdaptorMenloNetInStatsDropFcMulticastDeltaMax(36771),
        tcaAdaptorMenloNetInStatsDropFcMulticastDeltaAvg(36772),
        tcaAdaptorMenloNetInStatsDropFcLifInvalidDelta(36779),
        tcaAdaptorMenloNetInStatsDropFcLifInvalidDeltaMin(36780),
        tcaAdaptorMenloNetInStatsDropFcLifInvalidDeltaMax(36781),
        tcaAdaptorMenloNetInStatsDropFcLifInvalidDeltaAvg(36782),
        tcaAdaptorMenloNetInStatsDropNullPifDelta(36789),
        tcaAdaptorMenloNetInStatsDropNullPifDeltaMin(36790),
        tcaAdaptorMenloNetInStatsDropNullPifDeltaMax(36791),
        tcaAdaptorMenloNetInStatsDropNullPifDeltaAvg(36792),
        tcaAdaptorMenloHostPortStatsRxPausecfcdelta(36802),
        tcaAdaptorMenloHostPortStatsRxPausecfcdeltaMin(36803),
        tcaAdaptorMenloHostPortStatsRxPausecfcdeltaMax(36804),
        tcaAdaptorMenloHostPortStatsRxPausecfcdeltaAvg(36805),
        tcaAdaptorMenloHostPortStatsRxPausepfcdelta(36812),
        tcaAdaptorMenloHostPortStatsRxPausepfcdeltaMin(36813),
        tcaAdaptorMenloHostPortStatsRxPausepfcdeltaMax(36814),
        tcaAdaptorMenloHostPortStatsRxPausepfcdeltaAvg(36815),
        tcaAdaptorMenloHostPortStatsTxPausecfcdelta(36822),
        tcaAdaptorMenloHostPortStatsTxPausecfcdeltaMin(36823),
        tcaAdaptorMenloHostPortStatsTxPausecfcdeltaMax(36824),
        tcaAdaptorMenloHostPortStatsTxPausecfcdeltaAvg(36825),
        tcaAdaptorMenloHostPortStatsTxPausepfcdelta(36832),
        tcaAdaptorMenloHostPortStatsTxPausepfcdeltaMin(36833),
        tcaAdaptorMenloHostPortStatsTxPausepfcdeltaMax(36834),
        tcaAdaptorMenloHostPortStatsTxPausepfcdeltaAvg(36835),
        tcaAdaptorMenloDcePortStatsRxPausecfcdelta(36845),
        tcaAdaptorMenloDcePortStatsRxPausecfcdeltaMin(36846),
        tcaAdaptorMenloDcePortStatsRxPausecfcdeltaMax(36847),
        tcaAdaptorMenloDcePortStatsRxPausecfcdeltaAvg(36848),
        tcaAdaptorMenloDcePortStatsRxPausepfcdelta(36855),
        tcaAdaptorMenloDcePortStatsRxPausepfcdeltaMin(36856),
        tcaAdaptorMenloDcePortStatsRxPausepfcdeltaMax(36857),
        tcaAdaptorMenloDcePortStatsRxPausepfcdeltaAvg(36858),
        tcaAdaptorMenloDcePortStatsTxPausecfcdelta(36865),
        tcaAdaptorMenloDcePortStatsTxPausecfcdeltaMin(36866),
        tcaAdaptorMenloDcePortStatsTxPausecfcdeltaMax(36867),
        tcaAdaptorMenloDcePortStatsTxPausecfcdeltaAvg(36868),
        tcaAdaptorMenloDcePortStatsTxPausepfcdelta(36875),
        tcaAdaptorMenloDcePortStatsTxPausepfcdeltaMin(36876),
        tcaAdaptorMenloDcePortStatsTxPausepfcdeltaMax(36877),
        tcaAdaptorMenloDcePortStatsTxPausepfcdeltaAvg(36878),
        tcaAdaptorEtherIfStatsTxBytesDelta(36887),
        tcaAdaptorEtherIfStatsTxBytesDeltaMin(36888),
        tcaAdaptorEtherIfStatsTxBytesDeltaMax(36889),
        tcaAdaptorEtherIfStatsTxBytesDeltaAvg(36890),
        tcaAdaptorEtherIfStatsTxPacketsDelta(36897),
        tcaAdaptorEtherIfStatsTxPacketsDeltaMin(36898),
        tcaAdaptorEtherIfStatsTxPacketsDeltaMax(36899),
        tcaAdaptorEtherIfStatsTxPacketsDeltaAvg(36900),
        tcaAdaptorEtherIfStatsTxErrorsDelta(36907),
        tcaAdaptorEtherIfStatsTxErrorsDeltaMin(36908),
        tcaAdaptorEtherIfStatsTxErrorsDeltaMax(36909),
        tcaAdaptorEtherIfStatsTxErrorsDeltaAvg(36910),
        tcaAdaptorEtherIfStatsTxDroppedDelta(36917),
        tcaAdaptorEtherIfStatsTxDroppedDeltaMin(36918),
        tcaAdaptorEtherIfStatsTxDroppedDeltaMax(36919),
        tcaAdaptorEtherIfStatsTxDroppedDeltaAvg(36920),
        tcaAdaptorEtherIfStatsRxBytesDelta(36927),
        tcaAdaptorEtherIfStatsRxBytesDeltaMin(36928),
        tcaAdaptorEtherIfStatsRxBytesDeltaMax(36929),
        tcaAdaptorEtherIfStatsRxBytesDeltaAvg(36930),
        tcaAdaptorEtherIfStatsRxPacketsDelta(36937),
        tcaAdaptorEtherIfStatsRxPacketsDeltaMin(36938),
        tcaAdaptorEtherIfStatsRxPacketsDeltaMax(36939),
        tcaAdaptorEtherIfStatsRxPacketsDeltaAvg(36940),
        tcaAdaptorEtherIfStatsRxErrorsDelta(36947),
        tcaAdaptorEtherIfStatsRxErrorsDeltaMin(36948),
        tcaAdaptorEtherIfStatsRxErrorsDeltaMax(36949),
        tcaAdaptorEtherIfStatsRxErrorsDeltaAvg(36950),
        tcaAdaptorEtherIfStatsRxDroppedDelta(36957),
        tcaAdaptorEtherIfStatsRxDroppedDeltaMin(36958),
        tcaAdaptorEtherIfStatsRxDroppedDeltaMax(36959),
        tcaAdaptorEtherIfStatsRxDroppedDeltaAvg(36960),
        tcaAdaptorFcIfFrameStatsTxFramesDelta(36969),
        tcaAdaptorFcIfFrameStatsTxFramesDeltaMin(36970),
        tcaAdaptorFcIfFrameStatsTxFramesDeltaMax(36971),
        tcaAdaptorFcIfFrameStatsTxFramesDeltaAvg(36972),
        tcaAdaptorFcIfFrameStatsRxFramesDelta(36979),
        tcaAdaptorFcIfFrameStatsRxFramesDeltaMin(36980),
        tcaAdaptorFcIfFrameStatsRxFramesDeltaMax(36981),
        tcaAdaptorFcIfFrameStatsRxFramesDeltaAvg(36982),
        tcaAdaptorFcIfFrameStatsErrorFramesDelta(36989),
        tcaAdaptorFcIfFrameStatsErrorFramesDeltaMin(36990),
        tcaAdaptorFcIfFrameStatsErrorFramesDeltaMax(36991),
        tcaAdaptorFcIfFrameStatsErrorFramesDeltaAvg(36992),
        tcaAdaptorFcIfFrameStatsDumpedFramesDelta(36999),
        tcaAdaptorFcIfFrameStatsDumpedFramesDeltaMin(37000),
        tcaAdaptorFcIfFrameStatsDumpedFramesDeltaMax(37001),
        tcaAdaptorFcIfFrameStatsDumpedFramesDeltaAvg(37002),
        tcaAdaptorFcIfEventStatsLipCountDelta(37011),
        tcaAdaptorFcIfEventStatsLipCountDeltaMin(37012),
        tcaAdaptorFcIfEventStatsLipCountDeltaMax(37013),
        tcaAdaptorFcIfEventStatsLipCountDeltaAvg(37014),
        tcaAdaptorFcIfEventStatsInvalidcrccountDelta(37021),
        tcaAdaptorFcIfEventStatsInvalidcrccountDeltaMin(37022),
        tcaAdaptorFcIfEventStatsInvalidcrccountDeltaMax(37023),
        tcaAdaptorFcIfEventStatsInvalidcrccountDeltaAvg(37024),
        tcaAdaptorFcIfEventStatsNoscountDelta(37031),
        tcaAdaptorFcIfEventStatsNoscountDeltaMin(37032),
        tcaAdaptorFcIfEventStatsNoscountDeltaMax(37033),
        tcaAdaptorFcIfEventStatsNoscountDeltaAvg(37034),
        tcaAdaptorFcIfEventStatsLinkFailureCountDelta(37041),
        tcaAdaptorFcIfEventStatsLinkFailureCountDeltaMin(37042),
        tcaAdaptorFcIfEventStatsLinkFailureCountDeltaMax(37043),
        tcaAdaptorFcIfEventStatsLinkFailureCountDeltaAvg(37044),
        tcaAdaptorFcIfEventStatsLossOfSyncCountDelta(37051),
        tcaAdaptorFcIfEventStatsLossOfSyncCountDeltaMin(37052),
        tcaAdaptorFcIfEventStatsLossOfSyncCountDeltaMax(37053),
        tcaAdaptorFcIfEventStatsLossOfSyncCountDeltaAvg(37054),
        tcaAdaptorFcIfEventStatsLossOfSignalCountDelta(37061),
        tcaAdaptorFcIfEventStatsLossOfSignalCountDeltaMin(37062),
        tcaAdaptorFcIfEventStatsLossOfSignalCountDeltaMax(37063),
        tcaAdaptorFcIfEventStatsLossOfSignalCountDeltaAvg(37064),
        tcaAdaptorFcIfEventStatsSeqProtocolErrCountDelta(37071),
        tcaAdaptorFcIfEventStatsSeqProtocolErrCountDeltaMin(37072),
        tcaAdaptorFcIfEventStatsSeqProtocolErrCountDeltaMax(37073),
        tcaAdaptorFcIfEventStatsSeqProtocolErrCountDeltaAvg(37074),
        tcaAdaptorFcIfEventStatsSecondsSinceLastResetDelta(37081),
        tcaAdaptorFcIfEventStatsSecondsSinceLastResetDeltaMin(37082),
        tcaAdaptorFcIfEventStatsSecondsSinceLastResetDeltaMax(37083),
        tcaAdaptorFcIfEventStatsSecondsSinceLastResetDeltaAvg(37084),
        tcaMemoryRuntimeTotal(37200),
        tcaMemoryRuntimeTotalMin(37202),
        tcaMemoryRuntimeTotalMax(37203),
        tcaMemoryRuntimeTotalAvg(37204),
        tcaMemoryRuntimeAvailable(37208),
        tcaMemoryRuntimeAvailableMin(37210),
        tcaMemoryRuntimeAvailableMax(37211),
        tcaMemoryRuntimeAvailableAvg(37212),
        tcaMemoryRuntimeCached(37216),
        tcaMemoryRuntimeCachedMin(37218),
        tcaMemoryRuntimeCachedMax(37219),
        tcaMemoryRuntimeCachedAvg(37220),
        tcaMemoryArrayEnvStatsInputCurrent(37226),
        tcaMemoryArrayEnvStatsInputCurrentMin(37228),
        tcaMemoryArrayEnvStatsInputCurrentMax(37229),
        tcaMemoryArrayEnvStatsInputCurrentAvg(37230),
        tcaMemoryBufferUnitEnvStatsTemperature(37236),
        tcaMemoryBufferUnitEnvStatsTemperatureMin(37238),
        tcaMemoryBufferUnitEnvStatsTemperatureMax(37239),
        tcaMemoryBufferUnitEnvStatsTemperatureAvg(37240),
        tcaMemoryUnitEnvStatsTemperature(37246),
        tcaMemoryUnitEnvStatsTemperatureMin(37248),
        tcaMemoryUnitEnvStatsTemperatureMax(37249),
        tcaMemoryUnitEnvStatsTemperatureAvg(37250),
        tcaMemoryErrorStatsEccMultibitErrors(37255),
        tcaMemoryErrorStatsEccSinglebitErrors(37266),
        tcaMemoryErrorStatsAddressParityErrors(37277),
        tcaMemoryErrorStatsMismatchErrors(37288),
        tcaEquipmentChassisStatsInputPower(37879),
        tcaEquipmentChassisStatsInputPowerMin(37881),
        tcaEquipmentChassisStatsInputPowerMax(37882),
        tcaEquipmentChassisStatsInputPowerAvg(37883),
        tcaEquipmentChassisStatsOutputPower(37887),
        tcaEquipmentChassisStatsOutputPowerMin(37889),
        tcaEquipmentChassisStatsOutputPowerMax(37890),
        tcaEquipmentChassisStatsOutputPowerAvg(37891),
        tcaEquipmentChassisStatsInletTemp1(37895),
        tcaEquipmentChassisStatsInletTemp1Min(37897),
        tcaEquipmentChassisStatsInletTemp1Max(37898),
        tcaEquipmentChassisStatsInletTemp1Avg(37899),
        tcaEquipmentChassisStatsInletTemp2(37903),
        tcaEquipmentChassisStatsInletTemp2Min(37905),
        tcaEquipmentChassisStatsInletTemp2Max(37906),
        tcaEquipmentChassisStatsInletTemp2Avg(37907),
        tcaEquipmentChassisStatsOutletTemp1(37911),
        tcaEquipmentChassisStatsOutletTemp1Min(37913),
        tcaEquipmentChassisStatsOutletTemp1Max(37914),
        tcaEquipmentChassisStatsOutletTemp1Avg(37915),
        tcaEquipmentChassisStatsOutletTemp2(37919),
        tcaEquipmentChassisStatsOutletTemp2Min(37921),
        tcaEquipmentChassisStatsOutletTemp2Max(37922),
        tcaEquipmentChassisStatsOutletTemp2Avg(37923),
        tcaEquipmentIocardStatsAmbientTemp(37929),
        tcaEquipmentIocardStatsAmbientTempMin(37931),
        tcaEquipmentIocardStatsAmbientTempMax(37932),
        tcaEquipmentIocardStatsAmbientTempAvg(37933),
        tcaEquipmentIocardStatsTemp(37937),
        tcaEquipmentIocardStatsTempMin(37939),
        tcaEquipmentIocardStatsTempMax(37940),
        tcaEquipmentIocardStatsTempAvg(37941),
        tcaEquipmentIocardStatsProcTemp(37945),
        tcaEquipmentIocardStatsProcTempMin(37947),
        tcaEquipmentIocardStatsProcTempMax(37948),
        tcaEquipmentIocardStatsProcTempAvg(37949),
        tcaEquipmentIocardStatsDimmTemp(37953),
        tcaEquipmentIocardStatsDimmTempMin(37955),
        tcaEquipmentIocardStatsDimmTempMax(37956),
        tcaEquipmentIocardStatsDimmTempAvg(37957),
        tcaEquipmentPsuStatsAmbientTemp(37963),
        tcaEquipmentPsuStatsAmbientTempMin(37965),
        tcaEquipmentPsuStatsAmbientTempMax(37966),
        tcaEquipmentPsuStatsAmbientTempAvg(37967),
        tcaEquipmentPsuStatsOutputCurrent(37971),
        tcaEquipmentPsuStatsOutputCurrentMin(37973),
        tcaEquipmentPsuStatsOutputCurrentMax(37974),
        tcaEquipmentPsuStatsOutputCurrentAvg(37975),
        tcaEquipmentPsuStatsOutputPower(37979),
        tcaEquipmentPsuStatsOutputPowerMin(37981),
        tcaEquipmentPsuStatsOutputPowerMax(37982),
        tcaEquipmentPsuStatsOutputPowerAvg(37983),
        tcaEquipmentPsuStatsOutput12v(37987),
        tcaEquipmentPsuStatsOutput12vMin(37989),
        tcaEquipmentPsuStatsOutput12vMax(37990),
        tcaEquipmentPsuStatsOutput12vAvg(37991),
        tcaEquipmentPsuStatsOutput3v3(37995),
        tcaEquipmentPsuStatsOutput3v3Min(37997),
        tcaEquipmentPsuStatsOutput3v3Max(37998),
        tcaEquipmentPsuStatsOutput3v3Avg(37999),
        tcaEquipmentPsuStatsInput210v(38003),
        tcaEquipmentPsuStatsInput210vMin(38005),
        tcaEquipmentPsuStatsInput210vMax(38006),
        tcaEquipmentPsuStatsInput210vAvg(38007),
        tcaEquipmentPsuStatsInputPower(38014),
        tcaEquipmentPsuStatsInputPowerMin(38016),
        tcaEquipmentPsuStatsInputPowerMax(38017),
        tcaEquipmentPsuStatsInputPowerAvg(38018),
        tcaEquipmentPsuStatsInputCurrent(38022),
        tcaEquipmentPsuStatsInputCurrentMin(38024),
        tcaEquipmentPsuStatsInputCurrentMax(38025),
        tcaEquipmentPsuStatsInputCurrentAvg(38026),
        tcaEquipmentPsuStatsFanSpeed(38030),
        tcaEquipmentPsuStatsFanSpeedMin(38032),
        tcaEquipmentPsuStatsFanSpeedMax(38033),
        tcaEquipmentPsuStatsFanSpeedAvg(38034),
        tcaEquipmentPsuInputStatsCurrent(38040),
        tcaEquipmentPsuInputStatsCurrentMin(38042),
        tcaEquipmentPsuInputStatsCurrentMax(38043),
        tcaEquipmentPsuInputStatsCurrentAvg(38044),
        tcaEquipmentPsuInputStatsVoltage(38048),
        tcaEquipmentPsuInputStatsVoltageMin(38050),
        tcaEquipmentPsuInputStatsVoltageMax(38051),
        tcaEquipmentPsuInputStatsVoltageAvg(38052),
        tcaEquipmentPsuInputStatsPower(38056),
        tcaEquipmentPsuInputStatsPowerMin(38058),
        tcaEquipmentPsuInputStatsPowerMax(38059),
        tcaEquipmentPsuInputStatsPowerAvg(38060),
        tcaEquipmentPsuOutputStatsCurrent(38067),
        tcaEquipmentPsuOutputStatsCurrentMin(38069),
        tcaEquipmentPsuOutputStatsCurrentMax(38070),
        tcaEquipmentPsuOutputStatsCurrentAvg(38071),
        tcaEquipmentPsuOutputStatsVoltage(38075),
        tcaEquipmentPsuOutputStatsVoltageMin(38077),
        tcaEquipmentPsuOutputStatsVoltageMax(38078),
        tcaEquipmentPsuOutputStatsVoltageAvg(38079),
        tcaEquipmentPsuOutputStatsPower(38083),
        tcaEquipmentPsuOutputStatsPowerMin(38085),
        tcaEquipmentPsuOutputStatsPowerMax(38086),
        tcaEquipmentPsuOutputStatsPowerAvg(38087),
        tcaEquipmentFanModuleStatsAmbientTemp(38094),
        tcaEquipmentFanModuleStatsAmbientTempMin(38096),
        tcaEquipmentFanModuleStatsAmbientTempMax(38097),
        tcaEquipmentFanModuleStatsAmbientTempAvg(38098),
        tcaEquipmentFanStatsSpeed(38104),
        tcaEquipmentFanStatsSpeedMin(38106),
        tcaEquipmentFanStatsSpeedMax(38107),
        tcaEquipmentFanStatsSpeedAvg(38108),
        tcaEquipmentFexEnvStatsOutlet1(38114),
        tcaEquipmentFexEnvStatsOutlet1Min(38116),
        tcaEquipmentFexEnvStatsOutlet1Max(38117),
        tcaEquipmentFexEnvStatsOutlet1Avg(38118),
        tcaEquipmentFexEnvStatsOutlet2(38122),
        tcaEquipmentFexEnvStatsOutlet2Min(38124),
        tcaEquipmentFexEnvStatsOutlet2Max(38125),
        tcaEquipmentFexEnvStatsOutlet2Avg(38126),
        tcaEquipmentFexEnvStatsInlet(38130),
        tcaEquipmentFexEnvStatsInletMin(38132),
        tcaEquipmentFexEnvStatsInletMax(38133),
        tcaEquipmentFexEnvStatsInletAvg(38134),
        tcaEquipmentFexEnvStatsInlet1(38138),
        tcaEquipmentFexEnvStatsInlet1Min(38140),
        tcaEquipmentFexEnvStatsInlet1Max(38141),
        tcaEquipmentFexEnvStatsInlet1Avg(38142),
        tcaEquipmentFexEnvStatsDie1(38146),
        tcaEquipmentFexEnvStatsDie1Min(38148),
        tcaEquipmentFexEnvStatsDie1Max(38149),
        tcaEquipmentFexEnvStatsDie1Avg(38150),
        tcaEquipmentFexPowerSummaryTotalPower(38157),
        tcaEquipmentFexPowerSummaryTotalPowerMin(38159),
        tcaEquipmentFexPowerSummaryTotalPowerMax(38160),
        tcaEquipmentFexPowerSummaryTotalPowerAvg(38161),
        tcaEquipmentFexPowerSummaryReservedPower(38165),
        tcaEquipmentFexPowerSummaryReservedPowerMin(38167),
        tcaEquipmentFexPowerSummaryReservedPowerMax(38168),
        tcaEquipmentFexPowerSummaryReservedPowerAvg(38169),
        tcaEquipmentFexPowerSummaryModulePower(38173),
        tcaEquipmentFexPowerSummaryModulePowerMin(38175),
        tcaEquipmentFexPowerSummaryModulePowerMax(38176),
        tcaEquipmentFexPowerSummaryModulePowerAvg(38177),
        tcaEquipmentFexPowerSummaryAvailablePower(38181),
        tcaEquipmentFexPowerSummaryAvailablePowerMin(38183),
        tcaEquipmentFexPowerSummaryAvailablePowerMax(38184),
        tcaEquipmentFexPowerSummaryAvailablePowerAvg(38185),
        tcaEquipmentFexPsuInputStatsCurrent(38191),
        tcaEquipmentFexPsuInputStatsCurrentMin(38193),
        tcaEquipmentFexPsuInputStatsCurrentMax(38194),
        tcaEquipmentFexPsuInputStatsCurrentAvg(38195),
        tcaEquipmentFexPsuInputStatsVoltage(38199),
        tcaEquipmentFexPsuInputStatsVoltageMin(38201),
        tcaEquipmentFexPsuInputStatsVoltageMax(38202),
        tcaEquipmentFexPsuInputStatsVoltageAvg(38203),
        tcaEquipmentFexPsuInputStatsPower(38207),
        tcaEquipmentFexPsuInputStatsPowerMin(38209),
        tcaEquipmentFexPsuInputStatsPowerMax(38210),
        tcaEquipmentFexPsuInputStatsPowerAvg(38211),
        tcaEquipmentRackUnitPsuStatsAmbientTemp(38218),
        tcaEquipmentRackUnitPsuStatsAmbientTempMin(38220),
        tcaEquipmentRackUnitPsuStatsAmbientTempMax(38221),
        tcaEquipmentRackUnitPsuStatsAmbientTempAvg(38222),
        tcaEquipmentRackUnitPsuStatsOutputCurrent(38226),
        tcaEquipmentRackUnitPsuStatsOutputCurrentMin(38228),
        tcaEquipmentRackUnitPsuStatsOutputCurrentMax(38229),
        tcaEquipmentRackUnitPsuStatsOutputCurrentAvg(38230),
        tcaEquipmentRackUnitPsuStatsOutputPower(38234),
        tcaEquipmentRackUnitPsuStatsOutputPowerMin(38236),
        tcaEquipmentRackUnitPsuStatsOutputPowerMax(38237),
        tcaEquipmentRackUnitPsuStatsOutputPowerAvg(38238),
        tcaEquipmentRackUnitPsuStatsInputPower(38242),
        tcaEquipmentRackUnitPsuStatsInputPowerMin(38244),
        tcaEquipmentRackUnitPsuStatsInputPowerMax(38245),
        tcaEquipmentRackUnitPsuStatsInputPowerAvg(38246),
        tcaEquipmentRackUnitPsuStatsOutputVoltage(38250),
        tcaEquipmentRackUnitPsuStatsOutputVoltageMin(38252),
        tcaEquipmentRackUnitPsuStatsOutputVoltageMax(38253),
        tcaEquipmentRackUnitPsuStatsOutputVoltageAvg(38254),
        tcaEquipmentRackUnitPsuStatsInputVoltage(38258),
        tcaEquipmentRackUnitPsuStatsInputVoltageMin(38260),
        tcaEquipmentRackUnitPsuStatsInputVoltageMax(38261),
        tcaEquipmentRackUnitPsuStatsInputVoltageAvg(38262),
        tcaEquipmentNetworkElementFanStatsSpeed(38268),
        tcaEquipmentNetworkElementFanStatsSpeedMin(38270),
        tcaEquipmentNetworkElementFanStatsSpeedMax(38271),
        tcaEquipmentNetworkElementFanStatsSpeedAvg(38272),
        tcaEquipmentNetworkElementFanStatsDrivePercentage(38276),
        tcaEquipmentNetworkElementFanStatsDrivePercentageMin(38278),
        tcaEquipmentNetworkElementFanStatsDrivePercentageMax(38279),
        tcaEquipmentNetworkElementFanStatsDrivePercentageAvg(38280),
        tcaEquipmentRackUnitFanStatsSpeed(38287),
        tcaEquipmentRackUnitFanStatsSpeedMin(38289),
        tcaEquipmentRackUnitFanStatsSpeedMax(38290),
        tcaEquipmentRackUnitFanStatsSpeedAvg(38291),
        tcaEtherTxStatsTotalBytesDelta(38506),
        tcaEtherTxStatsTotalBytesDeltaMin(38507),
        tcaEtherTxStatsTotalBytesDeltaMax(38508),
        tcaEtherTxStatsTotalBytesDeltaAvg(38509),
        tcaEtherTxStatsTotalPacketsDelta(38516),
        tcaEtherTxStatsTotalPacketsDeltaMin(38517),
        tcaEtherTxStatsTotalPacketsDeltaMax(38518),
        tcaEtherTxStatsTotalPacketsDeltaAvg(38519),
        tcaEtherTxStatsUnicastPacketsDelta(38526),
        tcaEtherTxStatsUnicastPacketsDeltaMin(38527),
        tcaEtherTxStatsUnicastPacketsDeltaMax(38528),
        tcaEtherTxStatsUnicastPacketsDeltaAvg(38529),
        tcaEtherTxStatsMulticastPacketsDelta(38536),
        tcaEtherTxStatsMulticastPacketsDeltaMin(38537),
        tcaEtherTxStatsMulticastPacketsDeltaMax(38538),
        tcaEtherTxStatsMulticastPacketsDeltaAvg(38539),
        tcaEtherTxStatsBroadcastPacketsDelta(38546),
        tcaEtherTxStatsBroadcastPacketsDeltaMin(38547),
        tcaEtherTxStatsBroadcastPacketsDeltaMax(38548),
        tcaEtherTxStatsBroadcastPacketsDeltaAvg(38549),
        tcaEtherTxStatsJumboPacketsDelta(38556),
        tcaEtherTxStatsJumboPacketsDeltaMin(38557),
        tcaEtherTxStatsJumboPacketsDeltaMax(38558),
        tcaEtherTxStatsJumboPacketsDeltaAvg(38559),
        tcaEtherRxStatsTotalBytesDelta(38568),
        tcaEtherRxStatsTotalBytesDeltaMin(38569),
        tcaEtherRxStatsTotalBytesDeltaMax(38570),
        tcaEtherRxStatsTotalBytesDeltaAvg(38571),
        tcaEtherRxStatsTotalPacketsDelta(38578),
        tcaEtherRxStatsTotalPacketsDeltaMin(38579),
        tcaEtherRxStatsTotalPacketsDeltaMax(38580),
        tcaEtherRxStatsTotalPacketsDeltaAvg(38581),
        tcaEtherRxStatsUnicastPacketsDelta(38588),
        tcaEtherRxStatsUnicastPacketsDeltaMin(38589),
        tcaEtherRxStatsUnicastPacketsDeltaMax(38590),
        tcaEtherRxStatsUnicastPacketsDeltaAvg(38591),
        tcaEtherRxStatsMulticastPacketsDelta(38598),
        tcaEtherRxStatsMulticastPacketsDeltaMin(38599),
        tcaEtherRxStatsMulticastPacketsDeltaMax(38600),
        tcaEtherRxStatsMulticastPacketsDeltaAvg(38601),
        tcaEtherRxStatsBroadcastPacketsDelta(38608),
        tcaEtherRxStatsBroadcastPacketsDeltaMin(38609),
        tcaEtherRxStatsBroadcastPacketsDeltaMax(38610),
        tcaEtherRxStatsBroadcastPacketsDeltaAvg(38611),
        tcaEtherRxStatsJumboPacketsDelta(38618),
        tcaEtherRxStatsJumboPacketsDeltaMin(38619),
        tcaEtherRxStatsJumboPacketsDeltaMax(38620),
        tcaEtherRxStatsJumboPacketsDeltaAvg(38621),
        tcaEtherErrStatsAlignDelta(38630),
        tcaEtherErrStatsAlignDeltaMin(38631),
        tcaEtherErrStatsAlignDeltaMax(38632),
        tcaEtherErrStatsAlignDeltaAvg(38633),
        tcaEtherErrStatsFcsDelta(38640),
        tcaEtherErrStatsFcsDeltaMin(38641),
        tcaEtherErrStatsFcsDeltaMax(38642),
        tcaEtherErrStatsFcsDeltaAvg(38643),
        tcaEtherErrStatsXmitDelta(38650),
        tcaEtherErrStatsXmitDeltaMin(38651),
        tcaEtherErrStatsXmitDeltaMax(38652),
        tcaEtherErrStatsXmitDeltaAvg(38653),
        tcaEtherErrStatsRcvDelta(38660),
        tcaEtherErrStatsRcvDeltaMin(38661),
        tcaEtherErrStatsRcvDeltaMax(38662),
        tcaEtherErrStatsRcvDeltaAvg(38663),
        tcaEtherErrStatsUnderSizeDelta(38670),
        tcaEtherErrStatsUnderSizeDeltaMin(38671),
        tcaEtherErrStatsUnderSizeDeltaMax(38672),
        tcaEtherErrStatsUnderSizeDeltaAvg(38673),
        tcaEtherErrStatsOutDiscardDelta(38680),
        tcaEtherErrStatsOutDiscardDeltaMin(38681),
        tcaEtherErrStatsOutDiscardDeltaMax(38682),
        tcaEtherErrStatsOutDiscardDeltaAvg(38683),
        tcaEtherErrStatsDeferredTxDelta(38690),
        tcaEtherErrStatsDeferredTxDeltaMin(38691),
        tcaEtherErrStatsDeferredTxDeltaMax(38692),
        tcaEtherErrStatsDeferredTxDeltaAvg(38693),
        tcaEtherErrStatsIntMacTxDelta(38700),
        tcaEtherErrStatsIntMacTxDeltaMin(38701),
        tcaEtherErrStatsIntMacTxDeltaMax(38702),
        tcaEtherErrStatsIntMacTxDeltaAvg(38703),
        tcaEtherErrStatsIntMacRxDelta(38710),
        tcaEtherErrStatsIntMacRxDeltaMin(38711),
        tcaEtherErrStatsIntMacRxDeltaMax(38712),
        tcaEtherErrStatsIntMacRxDeltaAvg(38713),
        tcaEtherNiErrStatsFrameTxDelta(38722),
        tcaEtherNiErrStatsFrameTxDeltaMin(38723),
        tcaEtherNiErrStatsFrameTxDeltaMax(38724),
        tcaEtherNiErrStatsFrameTxDeltaAvg(38725),
        tcaEtherNiErrStatsTooLongDelta(38732),
        tcaEtherNiErrStatsTooLongDeltaMin(38733),
        tcaEtherNiErrStatsTooLongDeltaMax(38734),
        tcaEtherNiErrStatsTooLongDeltaAvg(38735),
        tcaEtherNiErrStatsTooShortDelta(38742),
        tcaEtherNiErrStatsTooShortDeltaMin(38743),
        tcaEtherNiErrStatsTooShortDeltaMax(38744),
        tcaEtherNiErrStatsTooShortDeltaAvg(38745),
        tcaEtherNiErrStatsCrcDelta(38752),
        tcaEtherNiErrStatsCrcDeltaMin(38753),
        tcaEtherNiErrStatsCrcDeltaMax(38754),
        tcaEtherNiErrStatsCrcDeltaAvg(38755),
        tcaEtherNiErrStatsInRangeDelta(38762),
        tcaEtherNiErrStatsInRangeDeltaMin(38763),
        tcaEtherNiErrStatsInRangeDeltaMax(38764),
        tcaEtherNiErrStatsInRangeDeltaAvg(38765),
        tcaEtherLossStatsSingleCollisionDelta(38774),
        tcaEtherLossStatsSingleCollisionDeltaMin(38775),
        tcaEtherLossStatsSingleCollisionDeltaMax(38776),
        tcaEtherLossStatsSingleCollisionDeltaAvg(38777),
        tcaEtherLossStatsMultiCollisionDelta(38784),
        tcaEtherLossStatsMultiCollisionDeltaMin(38785),
        tcaEtherLossStatsMultiCollisionDeltaMax(38786),
        tcaEtherLossStatsMultiCollisionDeltaAvg(38787),
        tcaEtherLossStatsLateCollisionDelta(38794),
        tcaEtherLossStatsLateCollisionDeltaMin(38795),
        tcaEtherLossStatsLateCollisionDeltaMax(38796),
        tcaEtherLossStatsLateCollisionDeltaAvg(38797),
        tcaEtherLossStatsExcessCollisionDelta(38804),
        tcaEtherLossStatsExcessCollisionDeltaMin(38805),
        tcaEtherLossStatsExcessCollisionDeltaMax(38806),
        tcaEtherLossStatsExcessCollisionDeltaAvg(38807),
        tcaEtherLossStatsCarrierSenseDelta(38814),
        tcaEtherLossStatsCarrierSenseDeltaMin(38815),
        tcaEtherLossStatsCarrierSenseDeltaMax(38816),
        tcaEtherLossStatsCarrierSenseDeltaAvg(38817),
        tcaEtherLossStatsGiantsDelta(38824),
        tcaEtherLossStatsGiantsDeltaMin(38825),
        tcaEtherLossStatsGiantsDeltaMax(38826),
        tcaEtherLossStatsGiantsDeltaAvg(38827),
        tcaEtherLossStatsSymbolDelta(38834),
        tcaEtherLossStatsSymbolDeltaMin(38835),
        tcaEtherLossStatsSymbolDeltaMax(38836),
        tcaEtherLossStatsSymbolDeltaAvg(38837),
        tcaEtherLossStatsSqetestDelta(38844),
        tcaEtherLossStatsSqetestDeltaMin(38845),
        tcaEtherLossStatsSqetestDeltaMax(38846),
        tcaEtherLossStatsSqetestDeltaAvg(38847),
        tcaEtherPauseStatsRecvPauseDelta(38856),
        tcaEtherPauseStatsRecvPauseDeltaMin(38857),
        tcaEtherPauseStatsRecvPauseDeltaMax(38858),
        tcaEtherPauseStatsRecvPauseDeltaAvg(38859),
        tcaEtherPauseStatsXmitPauseDelta(38866),
        tcaEtherPauseStatsXmitPauseDeltaMin(38867),
        tcaEtherPauseStatsXmitPauseDeltaMax(38868),
        tcaEtherPauseStatsXmitPauseDeltaAvg(38869),
        tcaEtherPauseStatsResetsDelta(38876),
        tcaEtherPauseStatsResetsDeltaMin(38877),
        tcaEtherPauseStatsResetsDeltaMax(38878),
        tcaEtherPauseStatsResetsDeltaAvg(38879),
        tcaEtherFcoeInterfaceStatsPacketsTxDelta(38888),
        tcaEtherFcoeInterfaceStatsPacketsTxDeltaMin(38889),
        tcaEtherFcoeInterfaceStatsPacketsTxDeltaMax(38890),
        tcaEtherFcoeInterfaceStatsPacketsTxDeltaAvg(38891),
        tcaEtherFcoeInterfaceStatsPacketsRxDelta(38898),
        tcaEtherFcoeInterfaceStatsPacketsRxDeltaMin(38899),
        tcaEtherFcoeInterfaceStatsPacketsRxDeltaMax(38900),
        tcaEtherFcoeInterfaceStatsPacketsRxDeltaAvg(38901),
        tcaEtherFcoeInterfaceStatsBytesTxDelta(38908),
        tcaEtherFcoeInterfaceStatsBytesTxDeltaMin(38909),
        tcaEtherFcoeInterfaceStatsBytesTxDeltaMax(38910),
        tcaEtherFcoeInterfaceStatsBytesTxDeltaAvg(38911),
        tcaEtherFcoeInterfaceStatsBytesRxDelta(38918),
        tcaEtherFcoeInterfaceStatsBytesRxDeltaMin(38919),
        tcaEtherFcoeInterfaceStatsBytesRxDeltaMax(38920),
        tcaEtherFcoeInterfaceStatsBytesRxDeltaAvg(38921),
        tcaEtherFcoeInterfaceStatsErrorsTxDelta(38928),
        tcaEtherFcoeInterfaceStatsErrorsTxDeltaMin(38929),
        tcaEtherFcoeInterfaceStatsErrorsTxDeltaMax(38930),
        tcaEtherFcoeInterfaceStatsErrorsTxDeltaAvg(38931),
        tcaEtherFcoeInterfaceStatsErrorsRxDelta(38938),
        tcaEtherFcoeInterfaceStatsErrorsRxDeltaMin(38939),
        tcaEtherFcoeInterfaceStatsErrorsRxDeltaMax(38940),
        tcaEtherFcoeInterfaceStatsErrorsRxDeltaAvg(38941),
        tcaEtherFcoeInterfaceStatsDroppedTxDelta(38948),
        tcaEtherFcoeInterfaceStatsDroppedTxDeltaMin(38949),
        tcaEtherFcoeInterfaceStatsDroppedTxDeltaMax(38950),
        tcaEtherFcoeInterfaceStatsDroppedTxDeltaAvg(38951),
        tcaEtherFcoeInterfaceStatsDroppedRxDelta(38958),
        tcaEtherFcoeInterfaceStatsDroppedRxDeltaMin(38959),
        tcaEtherFcoeInterfaceStatsDroppedRxDeltaMax(38960),
        tcaEtherFcoeInterfaceStatsDroppedRxDeltaAvg(38961),
        tcaProcessorRuntimeLoad(39841),
        tcaProcessorRuntimeLoadMin(39843),
        tcaProcessorRuntimeLoadMax(39844),
        tcaProcessorRuntimeLoadAvg(39845),
        tcaProcessorEnvStatsTemperature(39852),
        tcaProcessorEnvStatsTemperatureMin(39854),
        tcaProcessorEnvStatsTemperatureMax(39855),
        tcaProcessorEnvStatsTemperatureAvg(39856),
        tcaProcessorEnvStatsInputCurrent(39860),
        tcaProcessorEnvStatsInputCurrentMin(39862),
        tcaProcessorEnvStatsInputCurrentMax(39863),
        tcaProcessorEnvStatsInputCurrentAvg(39864),
        tcaProcessorErrorStatsMirroringIntraSockErrors(39869),
        tcaProcessorErrorStatsMirroringInterSockErrors(39880),
        tcaProcessorErrorStatsSparingErrors(39891),
        tcaProcessorErrorStatsSmiLinkCorrErrors(39902),
        tcaProcessorErrorStatsSmiLinkUncorrErrors(39913),
        tcaFcStatsBytesRxDelta(40569),
        tcaFcStatsBytesRxDeltaMin(40570),
        tcaFcStatsBytesRxDeltaMax(40571),
        tcaFcStatsBytesRxDeltaAvg(40572),
        tcaFcStatsPacketsRxDelta(40579),
        tcaFcStatsPacketsRxDeltaMin(40580),
        tcaFcStatsPacketsRxDeltaMax(40581),
        tcaFcStatsPacketsRxDeltaAvg(40582),
        tcaFcStatsBytesTxDelta(40589),
        tcaFcStatsBytesTxDeltaMin(40590),
        tcaFcStatsBytesTxDeltaMax(40591),
        tcaFcStatsBytesTxDeltaAvg(40592),
        tcaFcStatsPacketsTxDelta(40599),
        tcaFcStatsPacketsTxDeltaMin(40600),
        tcaFcStatsPacketsTxDeltaMax(40601),
        tcaFcStatsPacketsTxDeltaAvg(40602),
        tcaFcErrStatsCrcRxDelta(40611),
        tcaFcErrStatsCrcRxDeltaMin(40612),
        tcaFcErrStatsCrcRxDeltaMax(40613),
        tcaFcErrStatsCrcRxDeltaAvg(40614),
        tcaFcErrStatsDiscardRxDelta(40621),
        tcaFcErrStatsDiscardRxDeltaMin(40622),
        tcaFcErrStatsDiscardRxDeltaMax(40623),
        tcaFcErrStatsDiscardRxDeltaAvg(40624),
        tcaFcErrStatsTooLongRxDelta(40631),
        tcaFcErrStatsTooLongRxDeltaMin(40632),
        tcaFcErrStatsTooLongRxDeltaMax(40633),
        tcaFcErrStatsTooLongRxDeltaAvg(40634),
        tcaFcErrStatsTooShortRxDelta(40641),
        tcaFcErrStatsTooShortRxDeltaMin(40642),
        tcaFcErrStatsTooShortRxDeltaMax(40643),
        tcaFcErrStatsTooShortRxDeltaAvg(40644),
        tcaFcErrStatsRxDelta(40651),
        tcaFcErrStatsRxDeltaMin(40652),
        tcaFcErrStatsRxDeltaMax(40653),
        tcaFcErrStatsRxDeltaAvg(40654),
        tcaFcErrStatsDiscardTxDelta(40661),
        tcaFcErrStatsDiscardTxDeltaMin(40662),
        tcaFcErrStatsDiscardTxDeltaMax(40663),
        tcaFcErrStatsDiscardTxDeltaAvg(40664),
        tcaFcErrStatsTxDelta(40671),
        tcaFcErrStatsTxDeltaMin(40672),
        tcaFcErrStatsTxDeltaMax(40673),
        tcaFcErrStatsTxDeltaAvg(40674),
        tcaFcErrStatsLinkFailuresDelta(40681),
        tcaFcErrStatsLinkFailuresDeltaMin(40682),
        tcaFcErrStatsLinkFailuresDeltaMax(40683),
        tcaFcErrStatsLinkFailuresDeltaAvg(40684),
        tcaFcErrStatsSyncLossesDelta(40691),
        tcaFcErrStatsSyncLossesDeltaMin(40692),
        tcaFcErrStatsSyncLossesDeltaMax(40693),
        tcaFcErrStatsSyncLossesDeltaAvg(40694),
        tcaFcErrStatsSignalLossesDelta(40701),
        tcaFcErrStatsSignalLossesDeltaMin(40702),
        tcaFcErrStatsSignalLossesDeltaMax(40703),
        tcaFcErrStatsSignalLossesDeltaAvg(40704),
        tcaEquipmentCardStatsTemp(42989),
        tcaEquipmentCardStatsTempMin(42991),
        tcaEquipmentCardStatsTempMax(42992),
        tcaEquipmentCardStatsTempAvg(42993),
        fsmSamDmeComputeServerDiscPolicyResolveScrubPolicyRemoteInv(77916),
        fsmSamDmeGmetaHolderInventoryRemoteInv(77917),
        fsmSamDmeFirmwareDownloaderDownloadRemoteInv(77957),
        fsmSamDmeFirmwareImageDeleteRemoteInv(77958),
        fsmSamDmeFirmwareDistributableDeleteRemoteInv(77959),
        fsmSamDmeMgmtControllerUpdateucsmanagerRemoteInv(77960),
        fsmSamDmeMgmtControllerUpdateSwitchRemoteInv(77961),
        fsmSamDmeMgmtControllerUpdateiomRemoteInv(77962),
        fsmSamDmeFirmwarePlatformPackPlatformVersionRemoteInv(77963),
        fsmSamDmeFirmwareSystemDeployRemoteInv(77964),
        fsmSamDmeFirmwareSupFirmwareDeployRemoteInv(77965),
        fsmSamDmeFirmwareSystemApplyCatalogPackRemoteInv(77966),
        fsmSamDmeIdentIdentRequestUpdateIdentRemoteInv(77968),
        fsmSamDmeIdentMetaSystemSyncRemoteInv(77969),
        fsmSamDmeIdentMetaSystemUcscUnivSyncRemoteInv(77970),
        fsmSamDmeSmAppDeleteRemoteInv(78025),
        fsmSamDmeSmSecSvcRestoreApplicationRemoteInv(78026),
        fsmSamDmeSmAppUpdateApplicationRemoteInv(78027),
        fsmSamDmeSmAppInstanceResetApplicationRemoteInv(78028),
        fsmSamDmeSmSecSvcAutoDeploycspRemoteInv(78029),
        fsmSamDmeSwAccessDomainDeployRemoteInv(78107),
        fsmSamDmeSwEthLanBorderDeployRemoteInv(78108),
        fsmSamDmeSwFcSanBorderDeployRemoteInv(78109),
        fsmSamDmeSwUtilityDomainDeployRemoteInv(78110),
        fsmSamDmeSwEthLanFlowMonDeployRemoteInv(78111),
        fsmSamDmeSwPhysConfPhysicalRemoteInv(78116),
        fsmSamDmeSwExtUtilityConfPortBreakoutRemoteInv(78121),
        fsmSamDmeSwFcSanBorderActivateZoneSetRemoteInv(78122),
        fsmSamDmeCallhomeEpConfigCallhomeRemoteInv(78158),
        fsmSamDmeAdaptorExtEthIfPathResetRemoteInv(78167),
        fsmSamDmeAdaptorHostEthIfCircuitResetRemoteInv(78170),
        fsmSamDmeAdaptorHostFcIfCircuitResetRemoteInv(78171),
        fsmSamDmeLicenseDownloaderDownloadRemoteInv(78188),
        fsmSamDmeLicenseFileInstallRemoteInv(78189),
        fsmSamDmeLicenseFileClearRemoteInv(78190),
        fsmSamDmeLicenseInstanceUpdateFlexlmRemoteInv(78191),
        fsmSamDmeLicenseSmartConfigSetConfigRemoteInv(78192),
        fsmSamDmeLsServerConfigureRemoteInv(78210),
        fsmSamDmeComputeBladeDiagRemoteInv(78220),
        fsmSamDmeMgmtControllerExtMgmtInterfaceConfigRemoteInv(78243),
        fsmSamDmeComputePhysicalSwConnUpdRemoteInv(78244),
        fsmSamDmeEquipmentiocardResetIomRemoteInv(78245),
        fsmSamDmeComputePhysicalServiceInfraDeployRemoteInv(78246),
        fsmSamDmeComputePhysicalServiceInfraWithdrawRemoteInv(78247),
        fsmSamDmeEquipmentiocardBaseFePresenceRemoteInv(78255),
        fsmSamDmeEquipmentiocardBaseFeConnRemoteInv(78256),
        fsmSamDmeEquipmentChassisRemoveChassisRemoteInv(78257),
        fsmSamDmeEquipmentLocatorLedSetFeLocatorLedRemoteInv(78258),
        fsmSamDmeEquipmentLocatorLedSetFiLocatorLedRemoteInv(78259),
        fsmSamDmePortpioInCompatSfpPresenceRemoteInv(78262),
        fsmSamDmePortpioInCompatSfpReplacedRemoteInv(78263),
        fsmSamDmeObserveObservedResolvePolicyFsmRemoteInv(78503),
        fsmSamDmeObserveObservedResolveResourceFsmRemoteInv(78504),
        fsmSamDmeObserveObservedResolvevmfsmRemoteInv(78505),
        fsmSamDmeObserveObservedResolveControllerFsmRemoteInv(78506),
        fsmSamDmeEquipmentBeaconLedIlluminateRemoteInv(78589),
        fsmSamDmeSdAppInstanceInstallApplicationRemoteInv(78591),
        fsmSamDmeSdAppInstanceStartApplicationRemoteInv(78592),
        fsmSamDmeSdLduProvisionlduRemoteInv(78593),
        fsmSamDmeSdAppInstanceUpgradeApplicationRemoteInv(78594),
        fsmSamDmeSdAppInstanceStopApplicationRemoteInv(78595),
        fsmSamDmeSdAppInstanceUninstallApplicationRemoteInv(78596),
        fsmSamDmeSdSlotChangePlatformLogLevelRemoteInv(78597),
        fsmSamDmeSdAppInstanceBundleDataPortsRemoteInv(78598),
        fsmSamDmeSdLogicalDeviceConfigureLinksRemoteInv(78599),
        fsmSamDmeSdLinkUpdateInterfaceStatusRemoteInv(78600),
        fsmSamDmeSdClusterBootstrapUpdateClusterConfigurationRemoteInv(78601),
        fsmSamDmeSdSlotFormatDiskRemoteInv(78602),
        fsmSamDmeSdSlotSynchTimeZoneRemoteInv(78603),
        fsmSamDmeSdAppAttributeCtrlGetAppAttributesRemoteInv(78604),
        fsmSamDmeSdMgmtInfoUpdateMgmtInfoRemoteInv(78605),
        fsmSamDmeSdNetMgmtBootstrapUpdateNetMgmtBootstrapRemoteInv(78606),
        fsmSamDmeSdUpgradeTaskStopUpgradeStartAppRemoteInv(78607),
        fsmSamDmeEtherServerIntfioConfigSpeedRemoteInv(78609),
        fsmSamDmeEtherFtwPortPairConfigFtwRemoteInv(78610),
        fsmSamDmeExtpolEpRegisterFsmRemoteInv(78625),
        fsmSamDmeExtpolRegistryCrossDomainConfigRemoteInv(78626),
        fsmSamDmeExtpolRegistryCrossDomainDeleteRemoteInv(78627),
        fsmSamDmeStorageSystemSyncRemoteInv(78664),
        fsmSamDmeSysfileMutationSingleRemoteInv(78666),
        fsmSamDmeSysfileMutationGlobalRemoteInv(78667),
        fsmSamDmeApplicationDownloaderDownloadRemoteInv(78671),
        fsmSamDmeCommSvcEpUpdateSvcEpRemoteInv(78672),
        fsmSamDmeCommSvcEpRestartWebSvcRemoteInv(78673),
        fsmSamDmePkiEpUpdateEpRemoteInv(78691),
        fsmSamDmeAaaEpUpdateEpRemoteInv(78692),
        fsmSamDmeAaaRealmUpdateRealmRemoteInv(78693),
        fsmSamDmeAaaUserEpUpdateUserEpRemoteInv(78694),
        fsmSamDmeSysdebugManualCoreFileExportTargetExportRemoteInv(78705),
        fsmSamDmeSysdebugLogExportPolicyConfigureRemoteInv(78706),
        fsmSamDmeSysdebugAutoCoreFileExportTargetConfigureRemoteInv(78707),
        fsmSamDmeSysdebugTechSupportInitiateRemoteInv(78708),
        fsmSamDmeSysdebugTechSupportDeleteTechSupFileRemoteInv(78709),
        fsmSamDmeSysdebugTechSupportDownloadRemoteInv(78710),
        fsmSamDmeSysdebugCoreDownloadRemoteInv(78711),
        fsmSamDmeSysdebugLogControlEpLogControlPersistRemoteInv(78712),
        fsmSamDmeEpqosDefinitionDeployRemoteInv(78776),
        fsmSamDmeEpqosDefinitionDelTaskRemoveRemoteInv(78777),
        fsmSamDmeQosclassDefinitionConfigGlobalQoSremoteInv(78780),
        fsmSamDmeMgmtControllerRegistryConfigRemoteInv(78787),
        fsmSamDmeMgmtIfSwMgmtOobIfConfigRemoteInv(78798),
        fsmSamDmeMgmtIfSwMgmtInbandIfConfigRemoteInv(78799),
        fsmSamDmeMgmtipv6IfAddrSwMgmtOobIpv6IfConfigRemoteInv(78800),
        fsmSamDmeNhTableHolderConfigureLinksRemoteInv(78813),
        fsmSamDmeNhTableHolderBootstrapLinksRemoteInv(78814),
        fsmSamDmeStatsCollectionPolicyUpdateEpRemoteInv(78818),
        fsmSamDmeSyntheticFsObjCreateRemoteInv(78843),
        fsmSamDmeCapabilityUpdaterUpdaterRemoteInv(78848),
        fsmSamDmeCapabilityCatalogueActivateCatalogRemoteInv(78849),
        fsmSamDmeCapabilityMgmtExtensionActivateMgmtExtRemoteInv(78850),
        fsmSamDmeCapabilityCatalogueDeployCatalogueRemoteInv(78851),
        fsmSamDmeSwEthMonDeployRemoteInv(78860),
        fsmSamDmeSwFcMonDeployRemoteInv(78861),
        fsmSamDmeSwSspEthMonDeployRemoteInv(78909),
        fsmSamDmeSwSspEthMonSrcPhyEpDeleteRemoteInv(78910),
        fsmSamDmeFabricVnetEpSyncEpPushVnetEpDeletionRemoteInv(78916),
        fsmSamDmeFabricLanCloudSwitchModeRemoteInv(78917),
        fsmSamDmeFabricSanCloudSwitchModeRemoteInv(78918),
        fsmSamDmeFabricEpMgrConfigureRemoteInv(78924),
        fsmSamDmeMgmtExportPolicyReportConfigCopyRemoteInv(78930),
        fsmSamDmeExtpolProviderReportConfigImportRemoteInv(78931),
        fsmSamDmeMgmtIfVirtualIfConfigRemoteInv(78932),
        fsmSamDmeMgmtIfEnableVipRemoteInv(78933),
        fsmSamDmeMgmtIfDisableVipRemoteInv(78934),
        fsmSamDmeMgmtIfEnablehaRemoteInv(78935),
        fsmSamDmeMgmtBackupBackupRemoteInv(78936),
        fsmSamDmeMgmtImporterImportRemoteInv(78937),
        fsmSamDmeMgmtControllerSysConfigRemoteInv(78938),
        fsmSamDmeNfsMountInstMountRemoteInv(78971),
        fsmSamDmeNfsMountInstUnmountRemoteInv(78972),
        fsmSamDmeNfsMountDefReportNfsMountSuspendRemoteInv(78973),
        fsmSamDmeExtpolEpRepairCertRemoteInv(78994),
        fsmSamDmePolicyControlEpOperateRemoteInv(78995),
        fsmSamDmePolicyControlledTypeOperateRemoteInv(78996),
        fsmSamDmePolicyPolicyScopeReleasePolicyFsmRemoteInv(78999),
        fsmSamDmePolicyPolicyScopeReleaseOperationFsmRemoteInv(79000),
        fsmSamDmePolicyPolicyScopeReleaseStorageFsmRemoteInv(79001),
        fsmSamDmePolicyPolicyScopeResolveManyPolicyFsmRemoteInv(79002),
        fsmSamDmePolicyPolicyScopeResolveManyOperationFsmRemoteInv(79003),
        fsmSamDmePolicyPolicyScopeResolveManyStorageFsmRemoteInv(79004),
        fsmSamDmePolicyPolicyScopeReleaseManyPolicyFsmRemoteInv(79005),
        fsmSamDmePolicyPolicyScopeReleaseManyOperationFsmRemoteInv(79006),
        fsmSamDmePolicyPolicyScopeReleaseManyStorageFsmRemoteInv(79007),
        fsmSamDmePolicyPolicyScopeResolveAllPolicyFsmRemoteInv(79008),
        fsmSamDmePolicyPolicyScopeResolveAllOperationFsmRemoteInv(79009),
        fsmSamDmePolicyPolicyScopeResolveAllStorageFsmRemoteInv(79010),
        fsmSamDmePolicyPolicyScopeReleaseAllPolicyFsmRemoteInv(79011),
        fsmSamDmePolicyPolicyScopeReleaseAllOperationFsmRemoteInv(79012),
        fsmSamDmePolicyPolicyScopeReleaseAllStorageFsmRemoteInv(79013),
        fsmSamDmeFirmwareInfraPackInfraVersionRemoteInv(79130),
        fsmSamDmeComputeServerDiscPolicyResolveScrubPolicyFsmFail(999516),
        fsmSamDmeGmetaHolderInventoryFsmFail(999517),
        fsmSamDmeFirmwareDownloaderDownloadFsmFail(999557),
        fsmSamDmeFirmwareImageDeleteFsmFail(999558),
        fsmSamDmeFirmwareDistributableDeleteFsmFail(999559),
        fsmSamDmeMgmtControllerUpdateucsmanagerFsmFail(999560),
        fsmSamDmeMgmtControllerUpdateSwitchFsmFail(999561),
        fsmSamDmeMgmtControllerUpdateiomFsmFail(999562),
        fsmSamDmeFirmwarePlatformPackPlatformVersionFsmFail(999563),
        fsmSamDmeFirmwareSystemDeployFsmFail(999564),
        fsmSamDmeFirmwareSupFirmwareDeployFsmFail(999565),
        fsmSamDmeFirmwareSystemApplyCatalogPackFsmFail(999566),
        fsmSamDmeIdentIdentRequestUpdateIdentFsmFail(999568),
        fsmSamDmeIdentMetaSystemSyncFsmFail(999569),
        fsmSamDmeIdentMetaSystemUcscUnivSyncFsmFail(999570),
        fsmSamDmeSmAppDeleteFsmFail(999625),
        fsmSamDmeSmSecSvcRestoreApplicationFsmFail(999626),
        fsmSamDmeSmAppUpdateApplicationFsmFail(999627),
        fsmSamDmeSmAppInstanceResetApplicationFsmFail(999628),
        fsmSamDmeSmSecSvcAutoDeploycspFsmFail(999629),
        fsmSamDmeSwAccessDomainDeployFsmFail(999707),
        fsmSamDmeSwEthLanBorderDeployFsmFail(999708),
        fsmSamDmeSwFcSanBorderDeployFsmFail(999709),
        fsmSamDmeSwUtilityDomainDeployFsmFail(999710),
        fsmSamDmeSwEthLanFlowMonDeployFsmFail(999711),
        fsmSamDmeSwPhysConfPhysicalFsmFail(999716),
        fsmSamDmeSwExtUtilityConfPortBreakoutFsmFail(999721),
        fsmSamDmeSwFcSanBorderActivateZoneSetFsmFail(999722),
        fsmSamDmeCallhomeEpConfigCallhomeFsmFail(999758),
        fsmSamDmeAdaptorExtEthIfPathResetFsmFail(999767),
        fsmSamDmeAdaptorHostEthIfCircuitResetFsmFail(999770),
        fsmSamDmeAdaptorHostFcIfCircuitResetFsmFail(999771),
        fsmSamDmeLicenseDownloaderDownloadFsmFail(999788),
        fsmSamDmeLicenseFileInstallFsmFail(999789),
        fsmSamDmeLicenseFileClearFsmFail(999790),
        fsmSamDmeLicenseInstanceUpdateFlexlmFsmFail(999791),
        fsmSamDmeLicenseSmartConfigSetConfigFsmFail(999792),
        fsmSamDmeLsServerConfigureFsmFail(999810),
        fsmSamDmeComputeBladeDiagFsmFail(999820),
        fsmSamDmeMgmtControllerExtMgmtInterfaceConfigFsmFail(999843),
        fsmSamDmeComputePhysicalSwConnUpdFsmFail(999844),
        fsmSamDmeEquipmentiocardResetIomFsmFail(999845),
        fsmSamDmeComputePhysicalServiceInfraDeployFsmFail(999846),
        fsmSamDmeComputePhysicalServiceInfraWithdrawFsmFail(999847),
        fsmSamDmeEquipmentiocardBaseFePresenceFsmFail(999855),
        fsmSamDmeEquipmentiocardBaseFeConnFsmFail(999856),
        fsmSamDmeEquipmentChassisRemoveChassisFsmFail(999857),
        fsmSamDmeEquipmentLocatorLedSetFeLocatorLedFsmFail(999858),
        fsmSamDmeEquipmentLocatorLedSetFiLocatorLedFsmFail(999859),
        fsmSamDmePortpioInCompatSfpPresenceFsmFail(999862),
        fsmSamDmePortpioInCompatSfpReplacedFsmFail(999863),
        fsmSamDmeObserveObservedResolvePolicyFsmFsmFail(1000103),
        fsmSamDmeObserveObservedResolveResourceFsmFsmFail(1000104),
        fsmSamDmeObserveObservedResolvevmfsmFsmFail(1000105),
        fsmSamDmeObserveObservedResolveControllerFsmFsmFail(1000106),
        fsmSamDmeEquipmentBeaconLedIlluminateFsmFail(1000189),
        fsmSamDmeSdAppInstanceInstallApplicationFsmFail(1000191),
        fsmSamDmeSdAppInstanceStartApplicationFsmFail(1000192),
        fsmSamDmeSdLduProvisionlduFsmFail(1000193),
        fsmSamDmeSdAppInstanceUpgradeApplicationFsmFail(1000194),
        fsmSamDmeSdAppInstanceStopApplicationFsmFail(1000195),
        fsmSamDmeSdAppInstanceUninstallApplicationFsmFail(1000196),
        fsmSamDmeSdSlotChangePlatformLogLevelFsmFail(1000197),
        fsmSamDmeSdAppInstanceBundleDataPortsFsmFail(1000198),
        fsmSamDmeSdLogicalDeviceConfigureLinksFsmFail(1000199),
        fsmSamDmeSdLinkUpdateInterfaceStatusFsmFail(1000200),
        fsmSamDmeSdClusterBootstrapUpdateClusterConfigurationFsmFail(1000201),
        fsmSamDmeSdSlotFormatDiskFsmFail(1000202),
        fsmSamDmeSdSlotSynchTimeZoneFsmFail(1000203),
        fsmSamDmeSdAppAttributeCtrlGetAppAttributesFsmFail(1000204),
        fsmSamDmeSdMgmtInfoUpdateMgmtInfoFsmFail(1000205),
        fsmSamDmeSdNetMgmtBootstrapUpdateNetMgmtBootstrapFsmFail(1000206),
        fsmSamDmeSdUpgradeTaskStopUpgradeStartAppFsmFail(1000207),
        fsmSamDmeEtherServerIntfioConfigSpeedFsmFail(1000209),
        fsmSamDmeEtherFtwPortPairConfigFtwFsmFail(1000210),
        fsmSamDmeExtpolEpRegisterFsmFsmFail(1000225),
        fsmSamDmeExtpolRegistryCrossDomainConfigFsmFail(1000226),
        fsmSamDmeExtpolRegistryCrossDomainDeleteFsmFail(1000227),
        fsmSamDmeStorageSystemSyncFsmFail(1000264),
        fsmSamDmeSysfileMutationSingleFsmFail(1000266),
        fsmSamDmeSysfileMutationGlobalFsmFail(1000267),
        fsmSamDmeApplicationDownloaderDownloadFsmFail(1000271),
        fsmSamDmeCommSvcEpUpdateSvcEpFsmFail(1000272),
        fsmSamDmeCommSvcEpRestartWebSvcFsmFail(1000273),
        fsmSamDmePkiEpUpdateEpFsmFail(1000291),
        fsmSamDmeAaaEpUpdateEpFsmFail(1000292),
        fsmSamDmeAaaRealmUpdateRealmFsmFail(1000293),
        fsmSamDmeAaaUserEpUpdateUserEpFsmFail(1000294),
        fsmSamDmeSysdebugManualCoreFileExportTargetExportFsmFail(1000305),
        fsmSamDmeSysdebugLogExportPolicyConfigureFsmFail(1000306),
        fsmSamDmeSysdebugAutoCoreFileExportTargetConfigureFsmFail(1000307),
        fsmSamDmeSysdebugTechSupportInitiateFsmFail(1000308),
        fsmSamDmeSysdebugTechSupportDeleteTechSupFileFsmFail(1000309),
        fsmSamDmeSysdebugTechSupportDownloadFsmFail(1000310),
        fsmSamDmeSysdebugCoreDownloadFsmFail(1000311),
        fsmSamDmeSysdebugLogControlEpLogControlPersistFsmFail(1000312),
        fsmSamDmeEpqosDefinitionDeployFsmFail(1000376),
        fsmSamDmeEpqosDefinitionDelTaskRemoveFsmFail(1000377),
        fsmSamDmeQosclassDefinitionConfigGlobalQoSfsmFail(1000380),
        fsmSamDmeMgmtControllerRegistryConfigFsmFail(1000387),
        fsmSamDmeMgmtIfSwMgmtOobIfConfigFsmFail(1000398),
        fsmSamDmeMgmtIfSwMgmtInbandIfConfigFsmFail(1000399),
        fsmSamDmeMgmtipv6IfAddrSwMgmtOobIpv6IfConfigFsmFail(1000400),
        fsmSamDmeNhTableHolderConfigureLinksFsmFail(1000413),
        fsmSamDmeNhTableHolderBootstrapLinksFsmFail(1000414),
        fsmSamDmeStatsCollectionPolicyUpdateEpFsmFail(1000418),
        fsmSamDmeSyntheticFsObjCreateFsmFail(1000443),
        fsmSamDmeCapabilityUpdaterUpdaterFsmFail(1000448),
        fsmSamDmeCapabilityCatalogueActivateCatalogFsmFail(1000449),
        fsmSamDmeCapabilityMgmtExtensionActivateMgmtExtFsmFail(1000450),
        fsmSamDmeCapabilityCatalogueDeployCatalogueFsmFail(1000451),
        fsmSamDmeSwEthMonDeployFsmFail(1000460),
        fsmSamDmeSwFcMonDeployFsmFail(1000461),
        fsmSamDmeSwSspEthMonDeployFsmFail(1000509),
        fsmSamDmeSwSspEthMonSrcPhyEpDeleteFsmFail(1000510),
        fsmSamDmeFabricVnetEpSyncEpPushVnetEpDeletionFsmFail(1000516),
        fsmSamDmeFabricLanCloudSwitchModeFsmFail(1000517),
        fsmSamDmeFabricSanCloudSwitchModeFsmFail(1000518),
        fsmSamDmeFabricEpMgrConfigureFsmFail(1000524),
        fsmSamDmeMgmtExportPolicyReportConfigCopyFsmFail(1000530),
        fsmSamDmeExtpolProviderReportConfigImportFsmFail(1000531),
        fsmSamDmeMgmtIfVirtualIfConfigFsmFail(1000532),
        fsmSamDmeMgmtIfEnableVipFsmFail(1000533),
        fsmSamDmeMgmtIfDisableVipFsmFail(1000534),
        fsmSamDmeMgmtIfEnablehaFsmFail(1000535),
        fsmSamDmeMgmtBackupBackupFsmFail(1000536),
        fsmSamDmeMgmtImporterImportFsmFail(1000537),
        fsmSamDmeMgmtControllerSysConfigFsmFail(1000538),
        fsmSamDmeNfsMountInstMountFsmFail(1000571),
        fsmSamDmeNfsMountInstUnmountFsmFail(1000572),
        fsmSamDmeNfsMountDefReportNfsMountSuspendFsmFail(1000573),
        fsmSamDmeExtpolEpRepairCertFsmFail(1000594),
        fsmSamDmePolicyControlEpOperateFsmFail(1000595),
        fsmSamDmePolicyControlledTypeOperateFsmFail(1000596),
        fsmSamDmePolicyPolicyScopeReleasePolicyFsmFsmFail(1000599),
        fsmSamDmePolicyPolicyScopeReleaseOperationFsmFsmFail(1000600),
        fsmSamDmePolicyPolicyScopeReleaseStorageFsmFsmFail(1000601),
        fsmSamDmePolicyPolicyScopeResolveManyPolicyFsmFsmFail(1000602),
        fsmSamDmePolicyPolicyScopeResolveManyOperationFsmFsmFail(1000603),
        fsmSamDmePolicyPolicyScopeResolveManyStorageFsmFsmFail(1000604),
        fsmSamDmePolicyPolicyScopeReleaseManyPolicyFsmFsmFail(1000605),
        fsmSamDmePolicyPolicyScopeReleaseManyOperationFsmFsmFail(1000606),
        fsmSamDmePolicyPolicyScopeReleaseManyStorageFsmFsmFail(1000607),
        fsmSamDmePolicyPolicyScopeResolveAllPolicyFsmFsmFail(1000608),
        fsmSamDmePolicyPolicyScopeResolveAllOperationFsmFsmFail(1000609),
        fsmSamDmePolicyPolicyScopeResolveAllStorageFsmFsmFail(1000610),
        fsmSamDmePolicyPolicyScopeReleaseAllPolicyFsmFsmFail(1000611),
        fsmSamDmePolicyPolicyScopeReleaseAllOperationFsmFsmFail(1000612),
        fsmSamDmePolicyPolicyScopeReleaseAllStorageFsmFsmFail(1000613),
        fsmSamDmeFirmwareInfraPackInfraVersionFsmFail(1000730),
        unrFaultSuppressTaskSuppressPolicyName(4522066),
        unrVnicIpV4PooledAddrName(4522408),
        unrVnicIpV4MgmtPooledAddrName(4522414),
        unrVnicIpV6MgmtPooledAddrName(4522421),
        unrVnicIpv4PooledIscsiAddrIdentPoolName(4522435),
        unrVnicFcNodeIdentPoolName(4522448),
        unrVnicIscsiNodeIqnIdentPoolName(4522454),
        unrVnicIscsiStaticTargetIfAuthProfileName(4522465),
        unrVnicIscsiBootVnicIqnIdentPoolName(4522472),
        unrVnicIscsiBootVnicAuthProfileName(4522474),
        unrVnicConnDefLanConnPolicyName(4522480),
        unrVnicConnDefSanConnPolicyName(4522482),
        unrVnicUsnicConPolicyRefConPolicyName(4522500),
        unrVnicDynamicConPolicyRefConPolicyName(4522502),
        unrVnicVmqConPolicyRefConPolicyName(4522519),
        unrFabricVlanMcastPolicyName(4523218),
        unrFabricFcoeSanPcLacpPolicyName(4523256),
        unrFabricFcoeSanEpEthLinkProfileName(4523262),
        unrFabricEthLanPcLacpPolicyName(4523300),
        unrFabricEthLinkProfileUdldLinkPolicyName(4523311),
        unrFabricEthLinkProfileCdpLinkPolicyName(4523313),
        unrFabricEthEstcPcNwCtrlPolicyName(4523349),
        unrFabricEthEstcPcLacpPolicyName(4523352),
        unrVnicTemplStatsPolicyName(4524766),
        unrVnicSanConnTemplQosPolicyName(4524769),
        unrVnicSanConnTemplIdentPoolName(4524774),
        unrVnicLanConnTemplQosPolicyName(4524776),
        unrVnicLanConnTemplNwCtrlPolicyName(4524780),
        unrVnicLanConnTemplIdentPoolName(4524782),
        unrVnicFcGroupTemplStorageConnPolicyName(4524789),
        unrVnicProfileQosPolicyName(4524796),
        unrVnicProfileNwCtrlPolicyName(4524799),
        unrVnicVnicStatsPolicyName(4524836),
        unrVnicEtherBaseNwCtrlPolicyName(4524852),
        unrVnicEtherBasePinToGroupName(4524855),
        unrVnicEtherBaseAdaptorProfileName(4524857),
        unrVnicEtherBaseIdentPoolName(4524859),
        unrVnicEtherBaseNwTemplName(4524861),
        unrVnicEtherBaseQosPolicyName(4524863),
        unrVnicFcBasePinToGroupName(4524884),
        unrVnicFcBaseAdaptorProfileName(4524886),
        unrVnicFcBaseIdentPoolName(4524888),
        unrVnicFcBaseNwTemplName(4524890),
        unrVnicFcBaseQosPolicyName(4524892),
        unrVnicIscsiBaseIdentPoolName(4524896),
        unrVnicIscsiBaseAdaptorProfileName(4524898),
        unrVnicIscsiIqnIdentPoolName(4524902),
        unrVnicIscsiAuthProfileName(4524905),
        unrVnicAgroupStatsPolicyName(4524916),
        unrVnicFcGroupDefStorageConnPolicyName(4524925),
        unrLsServerSrcTemplName(4526538),
        unrLsServerIdentPoolName(4526545),
        unrLsServerBootPolicyName(4526547),
        unrLsServerVmediaPolicyName(4526549),
        unrLsServerLocalDiskPolicyName(4526551),
        unrLsServerKvmMgmtPolicyName(4526553),
        unrLsServerScrubPolicyName(4526561),
        unrLsServerDynamicConPolicyName(4526563),
        unrLsServerHostFwPolicyName(4526566),
        unrLsServerMgmtFwPolicyName(4526568),
        unrLsServerMgmtAccessPolicyName(4526570),
        unrLsServerSolPolicyName(4526572),
        unrLsServerStatsPolicyName(4526574),
        unrLsServerVconProfileName(4526576),
        unrLsServerBiosProfileName(4526578),
        unrLsServerPowerPolicyName(4526580),
        unrLsServerMaintPolicyName(4526584),
        unrLsServerExtippoolName(4526587),
        unrLsRequirementName(4526605),
        unrExtvmmVmnetworkDefinitionExtIpPoolName(4526646),
        unrExtvmmVmnetworkFabricNetworkName(4526653),
        unrExtvmmVmndrefVmNetworkDefName(4526657),
        unrExtvmmFndreferenceFnDefName(4526662),
        unrTrigTriggerableScheduler(4528969),
        unrFabricFcoeSanPcEpEthLinkProfileName(4529292),
        unrFabricFlowMonitorFlowMonRecordDef(4529373),
        unrFabricFlowMonitorFlowTimeoutPolicy(4529375),
        unrFabricNetflowMonitorRefNfMonitorName(4529380),
        unrFabricFlowMonExporterFlowExpProfile(4529401),
        unrFabricNetflowMonExporterRefNfMonExporterName(4529415),
        unrFabricEthLanEpEthLinkProfileName(4529458),
        unrFabricEthLanPcEpEthLinkProfileName(4529464),
        unrFabricEthEstcEpNwCtrlPolicyName(4529597)
    }

CfprApConditionSeverity ::= TEXTUAL-CONVENTION
    STATUS        current
    DESCRIPTION
        ""
    SYNTAX        INTEGER
    {
        cleared(0),
        info(1),
        condition(2),
        warning(3),
        minor(4),
        major(5),
        critical(6)
    }

CfprApConditionTag ::= TEXTUAL-CONVENTION
    STATUS        current
    DESCRIPTION
        ""
    SYNTAX        BITS
    {
        server(0),
        network(1),
        storage(2),
        pod(3),
        security(4),
        operations(5),
        fsmstagefail(6),
        fsmstageretry(7),
        fsmstageremoteinv(8)
    }

CfprApConditionType ::= TEXTUAL-CONVENTION
    STATUS        current
    DESCRIPTION
        ""
    SYNTAX        INTEGER
    {
        generic(0),
        fsm(1),
        network(2),
        server(3),
        configuration(4),
        sysdebug(5),
        equipment(6),
        environmental(7),
        management(8),
        connectivity(9),
        operational(10),
        security(11),
        any(65535)
    }

CfprApConfigImpactResponseState ::= TEXTUAL-CONVENTION
    STATUS        current
    DESCRIPTION
        ""
    SYNTAX        INTEGER
    {
        notStarted(0),
        waiting(1),
        complete(2)
    }

CfprApConfigSorterDirection ::= TEXTUAL-CONVENTION
    STATUS        current
    DESCRIPTION
        ""
    SYNTAX        INTEGER
    {
        ascending(0),
        descending(1)
    }

CfprApDcxAdminState ::= TEXTUAL-CONVENTION
    STATUS        current
    DESCRIPTION
        ""
    SYNTAX        INTEGER
    {
        enabled(0),
        disabled(1)
    }

CfprApDcxNsAllocStatus ::= TEXTUAL-CONVENTION
    STATUS        current
    DESCRIPTION
        ""
    SYNTAX        INTEGER
    {
        available(0),
        full(1),
        exceeded(2)
    }

CfprApDcxOperState ::= TEXTUAL-CONVENTION
    STATUS        current
    DESCRIPTION
        ""
    SYNTAX        INTEGER
    {
        unknown(0),
        adminDown(1),
        linkDown(2),
        error(3),
        active(4),
        passive(5)
    }

CfprApDcxProtState ::= TEXTUAL-CONVENTION
    STATUS        current
    DESCRIPTION
        ""
    SYNTAX        INTEGER
    {
        noProtection(0),
        active(1),
        passive(2)
    }

CfprApDcxState ::= TEXTUAL-CONVENTION
    STATUS        current
    DESCRIPTION
        ""
    SYNTAX        INTEGER
    {
        unknown(0),
        present(1),
        creating(2),
        modifying(3),
        destroying(4),
        createPend(5),
        modifyPend(6),
        destroyPend(7)
    }

CfprApDcxVIfProtRole ::= TEXTUAL-CONVENTION
    STATUS        current
    DESCRIPTION
        ""
    SYNTAX        INTEGER
    {
        unprotected(0),
        primary(1),
        backup(2)
    }

CfprApDiagAdminState ::= TEXTUAL-CONVENTION
    STATUS        current
    DESCRIPTION
        ""
    SYNTAX        INTEGER
    {
        ready(0),
        trigger(1),
        cancel(2)
    }

CfprApDiagBladeTestType ::= TEXTUAL-CONVENTION
    STATUS        current
    DESCRIPTION
        ""
    SYNTAX        INTEGER
    {
        disk(0),
        processor(1),
        memory(2),
        memtest(3),
        stress(4),
        pci(5)
    }

CfprApDiagFailureAction ::= TEXTUAL-CONVENTION
    STATUS        current
    DESCRIPTION
        ""
    SYNTAX        BITS
    {
        techSupport(0),
        waitDebug(1),
        skipRemaining(2)
    }

CfprApDiagNetworkTestType ::= TEXTUAL-CONVENTION
    STATUS        current
    DESCRIPTION
        ""
    SYNTAX        INTEGER
    {
        eth(0),
        fc(1)
    }

CfprApDiagSrvCtrlType ::= TEXTUAL-CONVENTION
    STATUS        current
    DESCRIPTION
        ""
    SYNTAX        INTEGER
    {
        full(1),
        efi(33)
    }

CfprApDiagStatus ::= TEXTUAL-CONVENTION
    STATUS        current
    DESCRIPTION
        ""
    SYNTAX        INTEGER
    {
        complete(0),
        inProgress(1),
        failed(2),
        notRun(3),
        cancelled(4),
        scheduled(5)
    }

CfprApDiagStatusIssues ::= TEXTUAL-CONVENTION
    STATUS        current
    DESCRIPTION
        ""
    SYNTAX        BITS
    {
        testFailure(0),
        runCancelled(1),
        componentError(2),
        stagesCompleted(3),
        stageFailed(4)
    }

CfprApDiagSuccessAction ::= TEXTUAL-CONVENTION
    STATUS        current
    DESCRIPTION
        ""
    SYNTAX        BITS
    {
        techSupport(0),
        waitDebug(1)
    }

CfprApDiagTestOrder ::= TEXTUAL-CONVENTION
    STATUS        current
    DESCRIPTION
        ""
    SYNTAX        Gauge32 (1..64)

CfprApDomainFeatureType ::= TEXTUAL-CONVENTION
    STATUS        current
    DESCRIPTION
        ""
    SYNTAX        INTEGER
    {
        major(0),
        minor(1)
    }

CfprApDomainFunctionalState ::= TEXTUAL-CONVENTION
    STATUS        current
    DESCRIPTION
        ""
    SYNTAX        INTEGER
    {
        enabled(0),
        disabled(1)
    }

CfprApDpsecForgedTransmit ::= TEXTUAL-CONVENTION
    STATUS        current
    DESCRIPTION
        ""
    SYNTAX        INTEGER
    {
        allow(0),
        deny(1)
    }

CfprApEpqosDefinitionDelTaskFsmCurrentFsm ::= TEXTUAL-CONVENTION
    STATUS        current
    DESCRIPTION
        ""
    SYNTAX        INTEGER
    {
        nop(0),
        remove(387)
    }

CfprApEpqosDefinitionDelTaskFsmStageName ::= TEXTUAL-CONVENTION
    STATUS        current
    DESCRIPTION
        ""
    SYNTAX        INTEGER
    {
        nop(0),
        removeBegin(387),
        removeLocal(388),
        removePeer(389),
        removeFail(572),
        removeSuccess(573)
    }

CfprApEpqosDefinitionDelTaskFsmTaskItem ::= TEXTUAL-CONVENTION
    STATUS        current
    DESCRIPTION
        ""
    SYNTAX        INTEGER
    {
        nop(0),
        remove(387)
    }

CfprApEpqosDefinitionFsmCurrentFsm ::= TEXTUAL-CONVENTION
    STATUS        current
    DESCRIPTION
        ""
    SYNTAX        INTEGER
    {
        nop(0),
        deploy(384)
    }

CfprApEpqosDefinitionFsmStageName ::= TEXTUAL-CONVENTION
    STATUS        current
    DESCRIPTION
        ""
    SYNTAX        INTEGER
    {
        nop(0),
        deployBegin(384),
        deployLocal(385),
        deployPeer(386),
        deployFail(574),
        deploySuccess(575)
    }

CfprApEpqosDefinitionFsmTaskItem ::= TEXTUAL-CONVENTION
    STATUS        current
    DESCRIPTION
        ""
    SYNTAX        INTEGER
    {
        nop(0),
        deploy(384)
    }

CfprApEquipmentActiveStatus ::= TEXTUAL-CONVENTION
    STATUS        current
    DESCRIPTION
        ""
    SYNTAX        INTEGER
    {
        unknown(0),
        activated(1),
        deactivated(2)
    }

CfprApEquipmentAdminPowerState ::= TEXTUAL-CONVENTION
    STATUS        current
    DESCRIPTION
        ""
    SYNTAX        INTEGER
    {
        policy(1),
        cycleImmediate(2),
        cycleWait(3)
    }

CfprApEquipmentAirflowDirection ::= TEXTUAL-CONVENTION
    STATUS        current
    DESCRIPTION
        ""
    SYNTAX        INTEGER
    {
        unknown(0),
        frontToBack(1),
        backToFront(2)
    }

CfprApEquipmentAsicType ::= TEXTUAL-CONVENTION
    STATUS        current
    DESCRIPTION
        ""
    SYNTAX        INTEGER
    {
        unknown(0),
        gatos(1),
        carmel(2)
    }

CfprApEquipmentBeaconLedFsmCurrentFsm ::= TEXTUAL-CONVENTION
    STATUS        current
    DESCRIPTION
        ""
    SYNTAX        INTEGER
    {
        nop(0),
        illuminate(247)
    }

CfprApEquipmentBeaconLedFsmStageName ::= TEXTUAL-CONVENTION
    STATUS        current
    DESCRIPTION
        ""
    SYNTAX        INTEGER
    {
        nop(0),
        illuminateBegin(247),
        illuminateExecuteA(248),
        illuminateExecuteB(249),
        illuminateFail(576),
        illuminateSuccess(577)
    }

CfprApEquipmentBeaconLedFsmTaskItem ::= TEXTUAL-CONVENTION
    STATUS        current
    DESCRIPTION
        ""
    SYNTAX        INTEGER
    {
        nop(0),
        illuminate(247)
    }

CfprApEquipmentBeaconLedState ::= TEXTUAL-CONVENTION
    STATUS        current
    DESCRIPTION
        ""
    SYNTAX        INTEGER
    {
        on(1),
        off(2),
        blinking(3),
        eth(4),
        fc(5)
    }

CfprApEquipmentBiosUpdateMethod ::= TEXTUAL-CONVENTION
    STATUS        current
    DESCRIPTION
        ""
    SYNTAX        INTEGER
    {
        unknown(0),
        managementController(1),
        pnuos(2)
    }

CfprApEquipmentBoardAggregationRole ::= TEXTUAL-CONVENTION
    STATUS        current
    DESCRIPTION
        ""
    SYNTAX        INTEGER
    {
        none(0),
        single(1),
        multiMaster(2),
        multiSlave(3)
    }

CfprApEquipmentBoardConnectorType ::= TEXTUAL-CONVENTION
    STATUS        current
    DESCRIPTION
        ""
    SYNTAX        INTEGER
    {
        connUnlinked(1),
        connLinked(2)
    }

CfprApEquipmentCardStatsThresholded ::= TEXTUAL-CONVENTION
    STATUS        current
    DESCRIPTION
        ""
    SYNTAX        BITS
    {
        temp(0),
        tempAvg(1),
        tempMax(2),
        tempMin(3)
    }

CfprApEquipmentCardStatsHistThresholded ::= TEXTUAL-CONVENTION
    STATUS        current
    DESCRIPTION
        ""
    SYNTAX        BITS
    {
        temp(0),
        tempAvg(1),
        tempMax(2),
        tempMin(3)
    }

CfprApEquipmentChassisId ::= TEXTUAL-CONVENTION
    STATUS        current
    DESCRIPTION
        ""
    SYNTAX        Gauge32 (1..255)

CfprApEquipmentChassisAdminState ::= TEXTUAL-CONVENTION
    STATUS        current
    DESCRIPTION
        ""
    SYNTAX        INTEGER
    {
        acknowledged(1),
        reAcknowledge(2),
        decommission(3),
        remove(4),
        enablePortChannel(5),
        disablePortChannel(6),
        autoAcknowledge(7)
    }

CfprApEquipmentChassisConfigProgressIndicator ::= TEXTUAL-CONVENTION
    STATUS        current
    DESCRIPTION
        ""
    SYNTAX        INTEGER
    {
        ackNotInProgress(0),
        ackInProgress(1)
    }

CfprApEquipmentChassisConfigState ::= TEXTUAL-CONVENTION
    STATUS        current
    DESCRIPTION
        ""
    SYNTAX        INTEGER
    {
        unInitialized(0),
        unAcknowledged(1),
        unsupportedConnectivity(2),
        ok(3),
        removing(4),
        ackInProgress(6),
        evaluation(7),
        acknowledged(8),
        autoAck(9)
    }

CfprApEquipmentChassisFsmCurrentFsm ::= TEXTUAL-CONVENTION
    STATUS        current
    DESCRIPTION
        ""
    SYNTAX        INTEGER
    {
        nop(0),
        removeChassis(225)
    }

CfprApEquipmentChassisFsmStageName ::= TEXTUAL-CONVENTION
    STATUS        current
    DESCRIPTION
        ""
    SYNTAX        INTEGER
    {
        nop(0),
        removeChassisBegin(225),
        removeChassisDecomission(226),
        removeChassisDisableEndPoint(227),
        removeChassisUnIdentifyLocal(228),
        removeChassisUnIdentifyPeer(229),
        removeChassisWait(230),
        removeChassisFail(578),
        removeChassisSuccess(579)
    }

CfprApEquipmentChassisFsmTaskItem ::= TEXTUAL-CONVENTION
    STATUS        current
    DESCRIPTION
        ""
    SYNTAX        INTEGER
    {
        nop(0),
        removeChassis(225)
    }

CfprApEquipmentChassisIssues ::= TEXTUAL-CONVENTION
    STATUS        current
    DESCRIPTION
        ""
    SYNTAX        BITS
    {
        chassisThermal(0),
        chassisInoperable(1),
        chassisVoltage(2),
        chassisPerf(3),
        chassisPower(4),
        removed(5),
        config(6),
        chassisPostFailure(7),
        psuThermal(8),
        psuInoperable(9),
        psuVoltage(10),
        psuPerf(11),
        psuPower(12),
        fanThermal(13),
        fanInoperable(14),
        fanVoltage(15),
        fanPerf(16),
        fanPower(17),
        iocardThermal(18),
        iocardInoperable(19),
        iocardVoltage(20),
        iocardPerf(21),
        iocardPower(22),
        computeThermal(23),
        computeInoperable(24),
        computeVoltage(25),
        computePerf(26),
        computePower(27),
        iocardInaccessible(28),
        fabricConnProblem(29),
        fabricUnsupportedConn(30),
        chassisLimitExceeded(31),
        chassisVifCapacityReduced(32),
        chassisPortChannelEnabled(33),
        chassisUnsupported(34)
    }

CfprApEquipmentChassisPowerOperState ::= TEXTUAL-CONVENTION
    STATUS        current
    DESCRIPTION
        ""
    SYNTAX        INTEGER
    {
        unknown(0),
        ok(1),
        failed(2),
        inputFailed(3),
        inputDegraded(4),
        outputFailed(5),
        outputDegraded(6),
        redundancyFailed(7),
        redundancyDegraded(8)
    }

CfprApEquipmentChassisStatsThresholded ::= TEXTUAL-CONVENTION
    STATUS        current
    DESCRIPTION
        ""
    SYNTAX        BITS
    {
        inletTemp1(0),
        inputPower(8),
        inputPowerAvg(9),
        inputPowerMax(10),
        inputPowerMin(11),
        outletTemp1(12),
        outletTemp1Avg(13),
        outletTemp1Max(14),
        outletTemp1Min(15),
        outletTemp2(16),
        outletTemp2Avg(17),
        outletTemp2Max(18),
        outletTemp2Min(19),
        outputPower(20),
        outputPowerAvg(21),
        outputPowerMax(22),
        outputPowerMin(23)
    }

CfprApEquipmentChassisStatsHistThresholded ::= TEXTUAL-CONVENTION
    STATUS        current
    DESCRIPTION
        ""
    SYNTAX        BITS
    {
        inletTemp1(0),
        inputPower(8),
        inputPowerAvg(9),
        inputPowerMax(10),
        inputPowerMin(11),
        outletTemp1(12),
        outletTemp1Avg(13),
        outletTemp1Max(14),
        outletTemp1Min(15),
        outletTemp2(16),
        outletTemp2Avg(17),
        outletTemp2Max(18),
        outletTemp2Min(19),
        outputPower(20),
        outputPowerAvg(21),
        outputPowerMax(22),
        outputPowerMin(23)
    }

CfprApEquipmentCommStatus ::= TEXTUAL-CONVENTION
    STATUS        current
    DESCRIPTION
        ""
    SYNTAX        INTEGER
    {
        unknown(0),
        connected(1),
        disconnected(2)
    }

CfprApEquipmentConnectionStatus ::= TEXTUAL-CONVENTION
    STATUS        current
    DESCRIPTION
        ""
    SYNTAX        BITS
    {
        a(0),
        b(1)
    }

CfprApEquipmentCpuType ::= TEXTUAL-CONVENTION
    STATUS        current
    DESCRIPTION
        ""
    SYNTAX        INTEGER
    {
        other(0),
        ivyBridge(1),
        sandyBridge(2)
    }

CfprApEquipmentDiscoveryCapOperPowerRequirement ::= TEXTUAL-CONVENTION
    STATUS        current
    DESCRIPTION
        ""
    SYNTAX        INTEGER
    {
        none(0),
        standby(1),
        full(2)
    }

CfprApEquipmentDiscoveryState ::= TEXTUAL-CONVENTION
    STATUS        current
    DESCRIPTION
        ""
    SYNTAX        INTEGER
    {
        unknown(0),
        online(1),
        offline(2),
        discovered(3),
        unsupportedConnectivity(4),
        autoUpgrading(5)
    }

CfprApEquipmentEnabledStatus ::= TEXTUAL-CONVENTION
    STATUS        current
    DESCRIPTION
        ""
    SYNTAX        INTEGER
    {
        unknown(0),
        enabled(1),
        disabled(2)
    }

CfprApEquipmentEthPortSpeedCap ::= TEXTUAL-CONVENTION
    STATUS        current
    DESCRIPTION
        ""
    SYNTAX        BITS
    {
        auto(0)
    }

CfprApEquipmentFanId ::= TEXTUAL-CONVENTION
    STATUS        current
    DESCRIPTION
        ""
    SYNTAX        Gauge32 (1..8)

CfprApEquipmentFanModule ::= TEXTUAL-CONVENTION
    STATUS        current
    DESCRIPTION
        ""
    SYNTAX        Gauge32 (1..8)

CfprApEquipmentFanTray ::= TEXTUAL-CONVENTION
    STATUS        current
    DESCRIPTION
        ""
    SYNTAX        Gauge32 (1..8)

CfprApEquipmentFanModuleId ::= TEXTUAL-CONVENTION
    STATUS        current
    DESCRIPTION
        ""
    SYNTAX        Gauge32 (1..8)

CfprApEquipmentFanModuleTray ::= TEXTUAL-CONVENTION
    STATUS        current
    DESCRIPTION
        ""
    SYNTAX        Gauge32 (1..1)

CfprApEquipmentFanModuleStatsThresholded ::= TEXTUAL-CONVENTION
    STATUS        current
    DESCRIPTION
        ""
    SYNTAX        BITS
    {
        ambientTemp(0),
        ambientTempAvg(1),
        ambientTempMax(2),
        ambientTempMin(3)
    }

CfprApEquipmentFanModuleStatsHistThresholded ::= TEXTUAL-CONVENTION
    STATUS        current
    DESCRIPTION
        ""
    SYNTAX        BITS
    {
        ambientTemp(0),
        ambientTempAvg(1),
        ambientTempMax(2),
        ambientTempMin(3)
    }

CfprApEquipmentFanStatsThresholded ::= TEXTUAL-CONVENTION
    STATUS        current
    DESCRIPTION
        ""
    SYNTAX        BITS
    {
        speed(0),
        speedAvg(1),
        speedMax(2),
        speedMin(3)
    }

CfprApEquipmentFanStatsHistThresholded ::= TEXTUAL-CONVENTION
    STATUS        current
    DESCRIPTION
        ""
    SYNTAX        BITS
    {
        speed(0),
        speedAvg(1),
        speedMax(2),
        speedMin(3)
    }

CfprApEquipmentFexId ::= TEXTUAL-CONVENTION
    STATUS        current
    DESCRIPTION
        ""
    SYNTAX        Gauge32 (1..255)

CfprApEquipmentFexCapProviderRole ::= TEXTUAL-CONVENTION
    STATUS        current
    DESCRIPTION
        ""
    SYNTAX        INTEGER
    {
        mgmt(1),
        data(2),
        full(3)
    }

CfprApEquipmentFexEnvStatsThresholded ::= TEXTUAL-CONVENTION
    STATUS        current
    DESCRIPTION
        ""
    SYNTAX        BITS
    {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CfprApEquipmentFexEnvStatsHistThresholded ::= TEXTUAL-CONVENTION
    STATUS        current
    DESCRIPTION
        ""
    SYNTAX        BITS
    {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CfprApEquipmentFexPowerSummaryThresholded ::= TEXTUAL-CONVENTION
    STATUS        current
    DESCRIPTION
        ""
    SYNTAX        BITS
    {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CfprApEquipmentFexPowerSummaryHistThresholded ::= TEXTUAL-CONVENTION
    STATUS        current
    DESCRIPTION
        ""
    SYNTAX        BITS
    {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CfprApEquipmentFexPsuInputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprApEquipmentFexPsuInputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprApEquipmentHealthLedState ::= TEXTUAL-CONVENTION
    STATUS        current
    DESCRIPTION
        ""
    SYNTAX        INTEGER
    {
        normal(0),
        minor(1),
        critical(2)
    }

CfprApEquipmentIOCardId ::= TEXTUAL-CONVENTION
    STATUS        current
    DESCRIPTION
        ""
    SYNTAX        Gauge32 (1..2)

CfprApEquipmentIOCardBaseFsmCurrentFsm ::= TEXTUAL-CONVENTION
    STATUS        current
    DESCRIPTION
        ""
    SYNTAX        INTEGER
    {
        nop(0),
        fePresence(219),
        feConn(222)
    }

CfprApEquipmentIOCardBaseFsmStageName ::= TEXTUAL-CONVENTION
    STATUS        current
    DESCRIPTION
        ""
    SYNTAX        INTEGER
    {
        nop(0),
        fePresenceBegin(219),
        fePresenceCheckLicense(220),
        fePresenceIdentify(221),
        feConnBegin(222),
        feConnConfigureSwMgmtEndPoint(223),
        feConnConfigureVifNs(224),
        feConnFail(580),
        feConnSuccess(581),
        fePresenceFail(582),
        fePresenceSuccess(583)
    }

CfprApEquipmentIOCardBaseFsmTaskFlags ::= TEXTUAL-CONVENTION
    STATUS        current
    DESCRIPTION
        ""
    SYNTAX        BITS
    {
        samDmeEquipmentIOCardBaseFePresenceUcsConfig(20),
        samDmeEquipmentIOCardBaseFePresenceMiniUcsConfig(21)
    }

CfprApEquipmentIOCardBaseFsmTaskItem ::= TEXTUAL-CONVENTION
    STATUS        current
    DESCRIPTION
        ""
    SYNTAX        INTEGER
    {
        nop(0),
        fePresence(219),
        feConn(222)
    }

CfprApEquipmentIOCardFsmCurrentFsm ::= TEXTUAL-CONVENTION
    STATUS        current
    DESCRIPTION
        ""
    SYNTAX        INTEGER
    {
        nop(0),
        resetIom(211),
        fePresence(219),
        feConn(222)
    }

CfprApEquipmentIOCardFsmStageName ::= TEXTUAL-CONVENTION
    STATUS        current
    DESCRIPTION
        ""
    SYNTAX        INTEGER
    {
        nop(0),
        resetIomBegin(211),
        resetIomExecute(212),
        fePresenceBegin(219),
        fePresenceCheckLicense(220),
        fePresenceIdentify(221),
        feConnBegin(222),
        feConnConfigureSwMgmtEndPoint(223),
        feConnConfigureVifNs(224),
        feConnFail(580),
        feConnSuccess(581),
        fePresenceFail(582),
        fePresenceSuccess(583),
        resetIomFail(584),
        resetIomSuccess(585)
    }

CfprApEquipmentIOCardFsmTaskItem ::= TEXTUAL-CONVENTION
    STATUS        current
    DESCRIPTION
        ""
    SYNTAX        INTEGER
    {
        nop(0),
        resetIom(211)
    }

CfprApEquipmentIOCardIssues ::= TEXTUAL-CONVENTION
    STATUS        current
    DESCRIPTION
        ""
    SYNTAX        BITS
    {
        thermal(0),
        inoperable(1),
        voltage(2),
        perf(3),
        power(4),
        removed(5),
        fabricPortProblem(6),
        postFailure(7),
        serverPortProblem(8),
        fabricpcLinkAutoAckBlocked(9)
    }

CfprApEquipmentIOCardStatsThresholded ::= TEXTUAL-CONVENTION
    STATUS        current
    DESCRIPTION
        ""
    SYNTAX        BITS
    {
        ambientTemp(0),
        ambientTempAvg(1),
        ambientTempMax(2),
        ambientTempMin(3),
        dimmTemp(4),
        dimmTempAvg(5),
        dimmTempMax(6),
        dimmTempMin(7),
        procTemp(8),
        procTempAvg(9),
        procTempMax(10),
        procTempMin(11),
        temp(12),
        tempAvg(13),
        tempMax(14),
        tempMin(15)
    }

CfprApEquipmentIOCardStatsHistThresholded ::= TEXTUAL-CONVENTION
    STATUS        current
    DESCRIPTION
        ""
    SYNTAX        BITS
    {
        ambientTemp(0),
        ambientTempAvg(1),
        ambientTempMax(2),
        ambientTempMin(3),
        dimmTemp(4),
        dimmTempAvg(5),
        dimmTempMax(6),
        dimmTempMin(7),
        procTemp(8),
        procTempAvg(9),
        procTempMax(10),
        procTempMin(11),
        temp(12),
        tempAvg(13),
        tempMax(14),
        tempMin(15)
    }

CfprApEquipmentInternalFanType ::= TEXTUAL-CONVENTION
    STATUS        current
    DESCRIPTION
        ""
    SYNTAX        INTEGER
    {
        chassis(0),
        switch(1),
        fex(2)
    }

CfprApEquipmentIsSupported ::= TEXTUAL-CONVENTION
    STATUS        current
    DESCRIPTION
        ""
    SYNTAX        INTEGER
    {
        no(0),
        yes(1)
    }

CfprApEquipmentLedColor ::= TEXTUAL-CONVENTION
    STATUS        current
    DESCRIPTION
        ""
    SYNTAX        INTEGER
    {
        unknown(0),
        green(1),
        amber(2),
        red(3),
        blue(4)
    }

CfprApEquipmentLedLocatorState ::= TEXTUAL-CONVENTION
    STATUS        current
    DESCRIPTION
        ""
    SYNTAX        INTEGER
    {
        inactive(0),
        off(1),
        on(2)
    }

CfprApEquipmentLedOperState ::= TEXTUAL-CONVENTION
    STATUS        current
    DESCRIPTION
        ""
    SYNTAX        INTEGER
    {
        unknown(0),
        on(1),
        off(2),
        blinking(3),
        eth(4),
        fc(5)
    }

CfprApEquipmentLocatorLedFsmCurrentFsm ::= TEXTUAL-CONVENTION
    STATUS        current
    DESCRIPTION
        ""
    SYNTAX        INTEGER
    {
        nop(0),
        setFeLocatorLed(231),
        setFiLocatorLed(233)
    }

CfprApEquipmentLocatorLedFsmStageName ::= TEXTUAL-CONVENTION
    STATUS        current
    DESCRIPTION
        ""
    SYNTAX        INTEGER
    {
        nop(0),
        setFeLocatorLedBegin(231),
        setFeLocatorLedExecute(232),
        setFiLocatorLedBegin(233),
        setFiLocatorLedExecute(234),
        setFeLocatorLedFail(586),
        setFeLocatorLedSuccess(587),
        setFiLocatorLedFail(588),
        setFiLocatorLedSuccess(589)
    }

CfprApEquipmentLocatorLedFsmTaskItem ::= TEXTUAL-CONVENTION
    STATUS        current
    DESCRIPTION
        ""
    SYNTAX        INTEGER
    {
        nop(0),
        setFeLocatorLed(231),
        setFiLocatorLed(233)
    }

CfprApEquipmentMemoryUnitDiscoveryModifierAction ::= TEXTUAL-CONVENTION
    STATUS        current
    DESCRIPTION
        ""
    SYNTAX        INTEGER
    {
        unknown(0),
        setRevToOne(1),
        setRev(2),
        setRevStrict(3)
    }

CfprApEquipmentMethod ::= TEXTUAL-CONVENTION
    STATUS        current
    DESCRIPTION
        ""
    SYNTAX        BITS
    {
        post(0),
        configCheck(1),
        diagCheck(2),
        selCheck(3)
    }

CfprApEquipmentNetworkElementFanStatsThresholded ::= TEXTUAL-CONVENTION
    STATUS        current
    DESCRIPTION
        ""
    SYNTAX        BITS
    {
        drivePercentage(0),
        drivePercentageAvg(1),
        drivePercentageMax(2),
        drivePercentageMin(3),
        speed(4),
        speedAvg(5),
        speedMax(6),
        speedMin(7)
    }

CfprApEquipmentNetworkElementFanStatsHistThresholded ::= TEXTUAL-CONVENTION
    STATUS        current
    DESCRIPTION
        ""
    SYNTAX        BITS
    {
        drivePercentage(0),
        drivePercentageAvg(1),
        drivePercentageMax(2),
        drivePercentageMin(3),
        speed(4),
        speedAvg(5),
        speedMax(6),
        speedMin(7)
    }

CfprApEquipmentOperability ::= TEXTUAL-CONVENTION
    STATUS        current
    DESCRIPTION
        ""
    SYNTAX        INTEGER
    {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        malformedFru(14),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107),
        linkActivateBlocked(108)
    }

CfprApEquipmentOwnership ::= TEXTUAL-CONVENTION
    STATUS        current
    DESCRIPTION
        ""
    SYNTAX        INTEGER
    {
        unknown(0),
        owned(1),
        unowned(2)
    }

CfprApEquipmentPOSTRecoverability ::= TEXTUAL-CONVENTION
    STATUS        current
    DESCRIPTION
        ""
    SYNTAX        INTEGER
    {
        unknown(0),
        recoverable(1),
        nonRecoverable(2)
    }

CfprApEquipmentPasswordState ::= TEXTUAL-CONVENTION
    STATUS        current
    DESCRIPTION
        ""
    SYNTAX        INTEGER
    {
        unknown(0),
        set(1),
        notSet(2)
    }

CfprApEquipmentPictureType ::= TEXTUAL-CONVENTION
    STATUS        current
    DESCRIPTION
        ""
    SYNTAX        INTEGER
    {
        unknown(0),
        front(1),
        back(2),
        top(3),
        bottom(4),
        left(5),
        right(6)
    }

CfprApEquipmentPortAttribute ::= TEXTUAL-CONVENTION
    STATUS        current
    DESCRIPTION
        ""
    SYNTAX        INTEGER
    {
        none(0),
        scalability(1)
    }

CfprApEquipmentPowerCapDefProfileMethod ::= TEXTUAL-CONVENTION
    STATUS        current
    DESCRIPTION
        ""
    SYNTAX        INTEGER
    {
        unknown(0),
        default(1),
        static(2),
        pnuos(3),
        nodemgr(4)
    }

CfprApEquipmentPowerState ::= TEXTUAL-CONVENTION
    STATUS        current
    DESCRIPTION
        ""
    SYNTAX        INTEGER
    {
        unknown(0),
        on(1),
        test(2),
        off(3),
        online(4),
        offline(5),
        offduty(6),
        degraded(7),
        powerSave(8),
        error(9),
        ok(10),
        failed(11),
        notSupported(100)
    }

CfprApEquipmentPresence ::= TEXTUAL-CONVENTION
    STATUS        current
    DESCRIPTION
        ""
    SYNTAX        INTEGER
    {
        unknown(0),
        empty(1),
        equipped(10),
        missing(11),
        mismatch(12),
        equippedNotPrimary(13),
        equippedSlave(14),
        mismatchSlave(15),
        missingSlave(16),
        equippedIdentityUnestablishable(20),
        mismatchIdentityUnestablishable(21),
        equippedWithMalformedFru(22),
        inaccessible(30),
        unauthorized(40),
        notSupported(100)
    }

CfprApEquipmentPsuType ::= TEXTUAL-CONVENTION
    STATUS        current
    DESCRIPTION
        ""
    SYNTAX        INTEGER
    {
        ac(1),
        dc(2)
    }

CfprApEquipmentPsuId ::= TEXTUAL-CONVENTION
    STATUS        current
    DESCRIPTION
        ""
    SYNTAX        Gauge32 (1..4)

CfprApEquipmentPsuFanStatus ::= TEXTUAL-CONVENTION
    STATUS        current
    DESCRIPTION
        ""
    SYNTAX        INTEGER
    {
        unknown(0),
        ok(1),
        failed(2)
    }

CfprApEquipmentPsuInputSrc ::= TEXTUAL-CONVENTION
    STATUS        current
    DESCRIPTION
        ""
    SYNTAX        INTEGER
    {
        unknown(0),
        n210AC50380DC(1),
        n110AC(2),
        undetermined(3),
        n115AC230AC(4)
    }

CfprApEquipmentPsuInputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprApEquipmentPsuInputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprApEquipmentPsuOutputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprApEquipmentPsuOutputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprApEquipmentPsuStateQualifier ::= TEXTUAL-CONVENTION
    STATUS        current
    DESCRIPTION
        ""
    SYNTAX        INTEGER
    {
        unknown(0),
        failure(1),
        overCurrent(2),
        overTemperature(3),
        inputLoss(4),
        fanFailure(5),
        inputCurrentWarning(6),
        inputVoltageWarning(7),
        ambientTemperatureWarning(8),
        outputCurrentWarning(9)
    }

CfprApEquipmentPsuStatsThresholded ::= TEXTUAL-CONVENTION
    STATUS        current
    DESCRIPTION
        ""
    SYNTAX        BITS
    {
        ambientTemp(0),
        ambientTempAvg(1),
        ambientTempMax(2),
        ambientTempMin(3),
        fanSpeed(4),
        fanSpeedAvg(5),
        fanSpeedMax(6),
        fanSpeedMin(7),
        input210v(8),
        input210vAvg(9),
        input210vMax(10),
        input210vMin(11),
        inputCurrent(12),
        inputCurrentAvg(13),
        inputCurrentMax(14),
        inputCurrentMin(15),
        inputPower(16),
        inputPowerAvg(17),
        inputPowerMax(18),
        inputPowerMin(19),
        output12v(20),
        output12vAvg(21),
        output12vMax(22),
        output12vMin(23),
        output3v3(24),
        output3v3Avg(25),
        output3v3Max(26),
        output3v3Min(27),
        outputCurrent(28),
        outputCurrentAvg(29),
        outputCurrentMax(30),
        outputCurrentMin(31),
        outputPower(32),
        outputPowerAvg(33),
        outputPowerMax(34),
        outputPowerMin(35)
    }

CfprApEquipmentPsuStatsHistThresholded ::= TEXTUAL-CONVENTION
    STATUS        current
    DESCRIPTION
        ""
    SYNTAX        BITS
    {
        ambientTemp(0),
        ambientTempAvg(1),
        ambientTempMax(2),
        ambientTempMin(3),
        fanSpeed(4),
        fanSpeedAvg(5),
        fanSpeedMax(6),
        fanSpeedMin(7),
        input210v(8),
        input210vAvg(9),
        input210vMax(10),
        input210vMin(11),
        inputCurrent(12),
        inputCurrentAvg(13),
        inputCurrentMax(14),
        inputCurrentMin(15),
        inputPower(16),
        inputPowerAvg(17),
        inputPowerMax(18),
        inputPowerMin(19),
        output12v(20),
        output12vAvg(21),
        output12vMax(22),
        output12vMin(23),
        output3v3(24),
        output3v3Avg(25),
        output3v3Max(26),
        output3v3Min(27),
        outputCurrent(28),
        outputCurrentAvg(29),
        outputCurrentMax(30),
        outputCurrentMin(31),
        outputPower(32),
        outputPowerAvg(33),
        outputPowerMax(34),
        outputPowerMin(35)
    }

CfprApEquipmentPsuVoltageType ::= TEXTUAL-CONVENTION
    STATUS        current
    DESCRIPTION
        ""
    SYNTAX        INTEGER
    {
        unknown(0),
        ac(1),
        dc(2),
        dv(3),
        hvdc(4)
    }

CfprApEquipmentRackUnitFanStatsThresholded ::= TEXTUAL-CONVENTION
    STATUS        current
    DESCRIPTION
        ""
    SYNTAX        BITS
    {
        speed(0),
        speedAvg(1),
        speedMax(2),
        speedMin(3)
    }

CfprApEquipmentRackUnitFanStatsHistThresholded ::= TEXTUAL-CONVENTION
    STATUS        current
    DESCRIPTION
        ""
    SYNTAX        BITS
    {
        speed(0),
        speedAvg(1),
        speedMax(2),
        speedMin(3)
    }

CfprApEquipmentRackUnitPsuStatsThresholded ::= TEXTUAL-CONVENTION
    STATUS        current
    DESCRIPTION
        ""
    SYNTAX        BITS
    {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CfprApEquipmentRackUnitPsuStatsHistThresholded ::= TEXTUAL-CONVENTION
    STATUS        current
    DESCRIPTION
        ""
    SYNTAX        BITS
    {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CfprApEquipmentRemovalConditions ::= TEXTUAL-CONVENTION
    STATUS        current
    DESCRIPTION
        ""
    SYNTAX        INTEGER
    {
        unknown(0),
        notApplicable(2),
        removableWhenOff(3),
        removableWhenOnOrOff(4)
    }

CfprApEquipmentResetOn ::= TEXTUAL-CONVENTION
    STATUS        current
    DESCRIPTION
        ""
    SYNTAX        INTEGER
    {
        unknown(0),
        update(1),
        activate(2)
    }

CfprApEquipmentSecureBios ::= TEXTUAL-CONVENTION
    STATUS        current
    DESCRIPTION
        ""
    SYNTAX        INTEGER
    {
        unknown(0),
        notSupported(1),
        supported(2)
    }

CfprApEquipmentSensorThresholdStatus ::= TEXTUAL-CONVENTION
    STATUS        current
    DESCRIPTION
        ""
    SYNTAX        INTEGER
    {
        unknown(0),
        ok(1),
        upperNonRecoverable(2),
        upperCritical(3),
        upperNonCritical(4),
        lowerNonCritical(5),
        lowerCritical(6),
        lowerNonRecoverable(7),
        notSupported(100)
    }

CfprApEquipmentSlotArrayLocation ::= TEXTUAL-CONVENTION
    STATUS        current
    DESCRIPTION
        ""
    SYNTAX        INTEGER
    {
        unknown(0),
        front(1),
        back(2),
        top(3),
        bottom(4),
        left(5),
        right(6)
    }

CfprApEquipmentSlotArrayOrientation ::= TEXTUAL-CONVENTION
    STATUS        current
    DESCRIPTION
        ""
    SYNTAX        INTEGER
    {
        unknown(0),
        vertical(1),
        horizontal(2)
    }

CfprApEquipmentSlotArraySelector ::= TEXTUAL-CONVENTION
    STATUS        current
    DESCRIPTION
        ""
    SYNTAX        INTEGER
    {
        unknown(0),
        psu(1),
        fan(2),
        iocard(3),
        diskSlot(5),
        driveSlot(6),
        usbPort(7),
        ethernetPort(8),
        comPort(9),
        parPort(10),
        vgaPort(11),
        dviPort(12),
        keyboardPort(13),
        mousePort(14),
        gem(15),
        blade(16)
    }

CfprApEquipmentSlotSpanOrientation ::= TEXTUAL-CONVENTION
    STATUS        current
    DESCRIPTION
        ""
    SYNTAX        INTEGER
    {
        unknown(0),
        inline(1),
        transverse(2)
    }

CfprApEquipmentSlotStatus ::= TEXTUAL-CONVENTION
    STATUS        current
    DESCRIPTION
        ""
    SYNTAX        INTEGER
    {
        unknown(0),
        empty(1),
        equipped(10),
        missing(11),
        mismatch(12),
        equippedNotPrimary(13),
        equippedSlave(14),
        mismatchSlave(15),
        missingSlave(16),
        equippedIdentityUnestablishable(20),
        mismatchIdentityUnestablishable(21),
        equippedWithMalformedFru(22),
        inaccessible(30),
        unauthorized(40)
    }

CfprApEquipmentStorageMethod ::= TEXTUAL-CONVENTION
    STATUS        current
    DESCRIPTION
        ""
    SYNTAX        INTEGER
    {
        unknown(0),
        singleFlash(1),
        dualFlash(2)
    }

CfprApEquipmentSwitchIOCardId ::= TEXTUAL-CONVENTION
    STATUS        current
    DESCRIPTION
        ""
    SYNTAX        Gauge32 (1..2)

CfprApEquipmentSwitchIOCardFsmCurrentFsm ::= TEXTUAL-CONVENTION
    STATUS        current
    DESCRIPTION
        ""
    SYNTAX        INTEGER
    {
        nop(0),
        fePresence(219),
        feConn(222)
    }

CfprApEquipmentSwitchIOCardFsmStageName ::= TEXTUAL-CONVENTION
    STATUS        current
    DESCRIPTION
        ""
    SYNTAX        INTEGER
    {
        nop(0),
        fePresenceBegin(219),
        fePresenceCheckLicense(220),
        fePresenceIdentify(221),
        feConnBegin(222),
        feConnConfigureSwMgmtEndPoint(223),
        feConnConfigureVifNs(224),
        feConnFail(580),
        feConnSuccess(581),
        fePresenceFail(582),
        fePresenceSuccess(583)
    }

CfprApEquipmentTpmType ::= TEXTUAL-CONVENTION
    STATUS        current
    DESCRIPTION
        ""
    SYNTAX        INTEGER
    {
        unknown(0),
        physical(1),
        virtual(2)
    }

CfprApEquipmentUnifiedPortAlgorithm ::= TEXTUAL-CONVENTION
    STATUS        current
    DESCRIPTION
        ""
    SYNTAX        INTEGER
    {
        none(0),
        slideRuleEthFirstDoubleRow(1),
        unrestricted(2),
        slideRuleEthFirstSingleRow(3),
        slideRuleFcFirstDoubleRow(4),
        slideRuleFcFirstSingleRow(5)
    }

CfprApEquipmentUuidFeatureCapUuidSupportMode ::= TEXTUAL-CONVENTION
    STATUS        current
    DESCRIPTION
        ""
    SYNTAX        INTEGER
    {
        none(0),
        loose(1),
        strict(2)
    }

CfprApEquipmentXcvrId ::= TEXTUAL-CONVENTION
    STATUS        current
    DESCRIPTION
        ""
    SYNTAX        Gauge32 (1..128)

CfprApEquipmentXcvrType ::= TEXTUAL-CONVENTION
    STATUS        current
    DESCRIPTION
        ""
    SYNTAX        INTEGER
    {
        none(0),
        n1gcx(1),
        n1gsx(2),
        n1glx(3),
        n1gex(4),
        n1gzx(5),
        n1gns(6),
        n1gt(7),
        n100mbase(10),
        n10gsr(11),
        n10ger(12),
        n10glr(13),
        n10glrm(14),
        n10glrmSm(15),
        n10gzr(16),
        n10gpasCx11(20),
        n10gpasCx12(21),
        n10gpasCx13(22),
        n10gpasCx14(23),
        n10gpasCx15(24),
        n10gpasCx16(25),
        n10gpasCx17(26),
        n10gpasCx11s(27),
        n10gpasCx1(28),
        n10gactCx11(30),
        n10gactCx13(31),
        n10gactCx15(32),
        n10gactCx17(33),
        n10gactCx11s(34),
        n10gactCx1(35),
        n10gactLimitCx1(36),
        h10gcu1m(40),
        h10gcu3m(41),
        h10gcu5m(42),
        h10gcu7m(43),
        n10gcx11s(50),
        n10glbx1(51),
        n10gusr(52),
        n10gelpbk(55),
        n10gelpbkCr(56),
        n10gelpbkBer(57),
        fet(253),
        sfp(254),
        unknown(255)
    }

CfprApEquipmentCType ::= TEXTUAL-CONVENTION
    STATUS        current
    DESCRIPTION
        ""
    SYNTAX        INTEGER
    {
        sas(0),
        flash(1)
    }

CfprApEquipmentFabricEpType ::= TEXTUAL-CONVENTION
    STATUS        current
    DESCRIPTION
        ""
    SYNTAX        INTEGER
    {
        unknown(0),
        chassis(1),
        fex(2),
        blade(3),
        rackUnit(4)
    }

CfprApEtherCIoEpIfType ::= TEXTUAL-CONVENTION
    STATUS        current
    DESCRIPTION
        ""
    SYNTAX        INTEGER
    {
        unknown(0),
        physical(1),
        aggregation(2),
        virtual(3),
        fabric(4)
    }

CfprApEtherCloudType ::= TEXTUAL-CONVENTION
    STATUS        current
    DESCRIPTION
        ""
    SYNTAX        INTEGER
    {
        unclassified(1),
        lan(2),
        san(3)
    }

CfprApEtherErrStatsThresholded ::= TEXTUAL-CONVENTION
    STATUS        current
    DESCRIPTION
        ""
    SYNTAX        BITS
    {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CfprApEtherErrStatsHistThresholded ::= TEXTUAL-CONVENTION
    STATUS        current
    DESCRIPTION
        ""
    SYNTAX        BITS
    {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CfprApEtherExternalEpAdminState ::= TEXTUAL-CONVENTION
    STATUS        current
    DESCRIPTION
        ""
    SYNTAX        INTEGER
    {
        enabled(1),
        disabled(2)
    }

CfprApEtherExternalEpLocale ::= TEXTUAL-CONVENTION
    STATUS        current
    DESCRIPTION
        ""
    SYNTAX        BITS
    {
        server(0),
        chassis(1),
        internal(2),
        external(3)
    }

CfprApEtherExternalPcAdminState ::= TEXTUAL-CONVENTION
    STATUS        current
    DESCRIPTION
        ""
    SYNTAX        INTEGER
    {
        enabled(1),
        disabled(2)
    }

CfprApEtherExternalPcLocale ::= TEXTUAL-CONVENTION
    STATUS        current
    DESCRIPTION
        ""
    SYNTAX        BITS
    {
        server(0),
        chassis(1),
        internal(2),
        external(3)
    }

CfprApEtherFcoeInterfaceStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprApEtherFcoeInterfaceStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprApEtherFtwOperMode ::= TEXTUAL-CONVENTION
    STATUS        current
    DESCRIPTION
        ""
    SYNTAX        INTEGER
    {
        noBypass(0),
        bypassL2(1),
        bypassReq(2),
        bypassWdt(3),
        bypassPwr(4)
    }

CfprApEtherFtwPortPairMode ::= TEXTUAL-CONVENTION
    STATUS        current
    DESCRIPTION
        ""
    SYNTAX        INTEGER
    {
        disabled(0),
        standby(1),
        bypass(2)
    }

CfprApEtherFtwPortPairWdtState ::= TEXTUAL-CONVENTION
    STATUS        current
    DESCRIPTION
        ""
    SYNTAX        INTEGER
    {
        enabled(1),
        disabled(2)
    }

CfprApEtherFtwPortPairFsmCurrentFsm ::= TEXTUAL-CONVENTION
    STATUS        current
    DESCRIPTION
        ""
    SYNTAX        INTEGER
    {
        nop(0),
        configFtw(315)
    }

CfprApEtherFtwPortPairFsmStageName ::= TEXTUAL-CONVENTION
    STATUS        current
    DESCRIPTION
        ""
    SYNTAX        INTEGER
    {
        nop(0),
        configFtwBegin(315),
        configFtwConfigure(316),
        configFtwFail(590),
        configFtwSuccess(591)
    }

CfprApEtherFtwPortPairFsmTaskItem ::= TEXTUAL-CONVENTION
    STATUS        current
    DESCRIPTION
        ""
    SYNTAX        INTEGER
    {
        nop(0),
        configFtw(315)
    }

CfprApEtherIntFIoEpType ::= TEXTUAL-CONVENTION
    STATUS        current
    DESCRIPTION
        ""
    SYNTAX        BITS
    {
        lan(0),
        san(1),
        ipc(2)
    }

CfprApEtherInternalPcLocale ::= TEXTUAL-CONVENTION
    STATUS        current
    DESCRIPTION
        ""
    SYNTAX        BITS
    {
        server(0),
        chassis(1),
        internal(2),
        external(3)
    }

CfprApEtherLossStatsThresholded ::= TEXTUAL-CONVENTION
    STATUS        current
    DESCRIPTION
        ""
    SYNTAX        BITS
    {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CfprApEtherLossStatsHistThresholded ::= TEXTUAL-CONVENTION
    STATUS        current
    DESCRIPTION
        ""
    SYNTAX        BITS
    {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CfprApEtherNiErrStatsThresholded ::= TEXTUAL-CONVENTION
    STATUS        current
    DESCRIPTION
        ""
    SYNTAX        BITS
    {
        crcDelta(0),
        crcDeltaAvg(1),
        crcDeltaMax(2),
        crcDeltaMin(3),
        frameTxDelta(4),
        frameTxDeltaAvg(5),
        frameTxDeltaMax(6),
        frameTxDeltaMin(7),
        inRangeDelta(8),
        inRangeDeltaAvg(9),
        inRangeDeltaMax(10),
        inRangeDeltaMin(11),
        tooLongDelta(12),
        tooLongDeltaAvg(13),
        tooLongDeltaMax(14),
        tooLongDeltaMin(15),
        tooShortDelta(16),
        tooShortDeltaAvg(17),
        tooShortDeltaMax(18),
        tooShortDeltaMin(19)
    }

CfprApEtherNiErrStatsHistThresholded ::= TEXTUAL-CONVENTION
    STATUS        current
    DESCRIPTION
        ""
    SYNTAX        BITS
    {
        crcDelta(0),
        crcDeltaAvg(1),
        crcDeltaMax(2),
        crcDeltaMin(3),
        frameTxDelta(4),
        frameTxDeltaAvg(5),
        frameTxDeltaMax(6),
        frameTxDeltaMin(7),
        inRangeDelta(8),
        inRangeDeltaAvg(9),
        inRangeDeltaMax(10),
        inRangeDeltaMin(11),
        tooLongDelta(12),
        tooLongDeltaAvg(13),
        tooLongDeltaMax(14),
        tooLongDeltaMin(15),
        tooShortDelta(16),
        tooShortDeltaAvg(17),
        tooShortDeltaMax(18),
        tooShortDeltaMin(19)
    }

CfprApEtherPIoEpIfType ::= TEXTUAL-CONVENTION
    STATUS        current
    DESCRIPTION
        ""
    SYNTAX        INTEGER
    {
        unknown(0),
        physical(1),
        aggregation(2),
        virtual(3),
        fabric(4)
    }

CfprApEtherPIoFsmCurrentFsm ::= TEXTUAL-CONVENTION
    STATUS        current
    DESCRIPTION
        ""
    SYNTAX        INTEGER
    {
        nop(0),
        inCompatSfpPresence(235),
        inCompatSfpReplaced(237)
    }

CfprApEtherPIoFsmStageName ::= TEXTUAL-CONVENTION
    STATUS        current
    DESCRIPTION
        ""
    SYNTAX        INTEGER
    {
        nop(0),
        inCompatSfpPresenceBegin(235),
        inCompatSfpPresenceShutdown(236),
        inCompatSfpReplacedBegin(237),
        inCompatSfpReplacedEnablePort(238),
        inCompatSfpPresenceFail(732),
        inCompatSfpPresenceSuccess(733),
        inCompatSfpReplacedFail(734),
        inCompatSfpReplacedSuccess(735)
    }

CfprApEtherPauseStatsThresholded ::= TEXTUAL-CONVENTION
    STATUS        current
    DESCRIPTION
        ""
    SYNTAX        BITS
    {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CfprApEtherPauseStatsHistThresholded ::= TEXTUAL-CONVENTION
    STATUS        current
    DESCRIPTION
        ""
    SYNTAX        BITS
    {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CfprApEtherRxStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprApEtherRxStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprApEtherSatelliteConnectionDisc ::= TEXTUAL-CONVENTION
    STATUS        current
    DESCRIPTION
        ""
    SYNTAX        INTEGER
    {
        absent(0),
        present(1),
        misConnect(2),
        missing(3),
        new(4)
    }

CfprApEtherServerIntFIoAdminState ::= TEXTUAL-CONVENTION
    STATUS        current
    DESCRIPTION
        ""
    SYNTAX        INTEGER
    {
        enabled(1),
        disabled(2)
    }

CfprApEtherServerIntFIoIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApEtherServerIntFIoLocale ::= TEXTUAL-CONVENTION
    STATUS        current
    DESCRIPTION
        ""
    SYNTAX        BITS
    {
        server(0),
        chassis(1),
        internal(2),
        external(3)
    }

CfprApEtherServerIntFIoTransport ::= TEXTUAL-CONVENTION
    STATUS        current
    DESCRIPTION
        ""
    SYNTAX        BITS
    {
        ether(0),
        dce(1),
        fc(2)
    }

CfprApEtherServerIntFIoType ::= TEXTUAL-CONVENTION
    STATUS        current
    DESCRIPTION
        ""
    SYNTAX        BITS
    {
        lan(0),
        san(1),
        ipc(2)
    }

CfprApEtherServerIntFIoFsmCurrentFsm ::= TEXTUAL-CONVENTION
    STATUS        current
    DESCRIPTION
        ""
    SYNTAX        INTEGER
    {
        nop(0),
        configSpeed(313)
    }

CfprApEtherServerIntFIoFsmStageName ::= TEXTUAL-CONVENTION
    STATUS        current
    DESCRIPTION
        ""
    SYNTAX        INTEGER
    {
        nop(0),
        configSpeedBegin(313),
        configSpeedConfigure(314),
        configSpeedFail(592),
        configSpeedSuccess(593)
    }

CfprApEtherServerIntFIoFsmTaskItem ::= TEXTUAL-CONVENTION
    STATUS        current
    DESCRIPTION
        ""
    SYNTAX        INTEGER
    {
        nop(0),
        configSpeed(313)
    }

CfprApEtherServerIntFIoPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApEtherServerIntFIoPcPortId ::= TEXTUAL-CONVENTION
    STATUS        current
    DESCRIPTION
        ""
    SYNTAX        Gauge32 (1024..4096)

CfprApEtherServerIntFIoPcTransport ::= TEXTUAL-CONVENTION
    STATUS        current
    DESCRIPTION
        ""
    SYNTAX        BITS
    {
        ether(0),
        dce(1),
        fc(2)
    }

CfprApEtherServerIntFIoPcType ::= TEXTUAL-CONVENTION
    STATUS        current
    DESCRIPTION
        ""
    SYNTAX        BITS
    {
        lan(0),
        san(1),
        ipc(2)
    }

CfprApEtherServerIntFIoPcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApEtherServerIntFIoPcEpPortId ::= TEXTUAL-CONVENTION
    STATUS        current
    DESCRIPTION
        ""
    SYNTAX        Gauge32 (1..33)

CfprApEtherSwitchIntFIoAck ::= TEXTUAL-CONVENTION
    STATUS        current
    DESCRIPTION
        ""
    SYNTAX        INTEGER
    {
        unInitialized(0),
        unAcknowledged(1),
        unsupportedConnectivity(2),
        ok(3),
        removing(4),
        ackInProgress(6),
        evaluation(7),
        acknowledged(8),
        autoAck(9)
    }

CfprApEtherSwitchIntFIoIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApEtherSwitchIntFIoLocale ::= TEXTUAL-CONVENTION
    STATUS        current
    DESCRIPTION
        ""
    SYNTAX        BITS
    {
        server(0),
        chassis(1),
        internal(2),
        external(3)
    }

CfprApEtherSwitchIntFIoTransport ::= TEXTUAL-CONVENTION
    STATUS        current
    DESCRIPTION
        ""
    SYNTAX        BITS
    {
        ether(0),
        dce(1),
        fc(2)
    }

CfprApEtherSwitchIntFIoType ::= TEXTUAL-CONVENTION
    STATUS        current
    DESCRIPTION
        ""
    SYNTAX        BITS
    {
        lan(0),
        san(1),
        ipc(2)
    }

CfprApEtherSwitchIntFIoPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApEtherSwitchIntFIoPcPortId ::= TEXTUAL-CONVENTION
    STATUS        current
    DESCRIPTION
        ""
    SYNTAX        Gauge32 (1024..4096)

CfprApEtherSwitchIntFIoPcTransport ::= TEXTUAL-CONVENTION
    STATUS        current
    DESCRIPTION
        ""
    SYNTAX        BITS
    {
        ether(0),
        dce(1),
        fc(2)
    }

CfprApEtherSwitchIntFIoPcType ::= TEXTUAL-CONVENTION
    STATUS        current
    DESCRIPTION
        ""
    SYNTAX        BITS
    {
        lan(0),
        san(1),
        ipc(2)
    }

CfprApEtherSwitchIntFIoPcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApEtherSwitchIntFIoPcEpPortId ::= TEXTUAL-CONVENTION
    STATUS        current
    DESCRIPTION
        ""
    SYNTAX        Gauge32 (1..8)

CfprApEtherTxStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprApEtherTxStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprApEventEpCtrlLevel ::= TEXTUAL-CONVENTION
    STATUS        current
    DESCRIPTION
        ""
    SYNTAX        INTEGER
    {
        cleared(0),
        info(1),
        condition(2),
        warning(3),
        minor(4),
        major(5),
        critical(6)
    }

CfprApExtmgmtArpTargetsMaxDeadlineTimeout ::= TEXTUAL-CONVENTION
    STATUS        current
    DESCRIPTION
        ""
    SYNTAX        Gauge32 (5..15)

CfprApExtmgmtArpTargetsNumberOfArpRequests ::= TEXTUAL-CONVENTION
    STATUS        current
    DESCRIPTION
        ""
    SYNTAX        Gauge32 (1..5)

CfprApExtmgmtGatewayPingMaxDeadlineTimeout ::= TEXTUAL-CONVENTION
    STATUS        current
    DESCRIPTION
        ""
    SYNTAX        Gauge32 (5..15)

CfprApExtmgmtGatewayPingNumberOfPingRequests ::= TEXTUAL-CONVENTION
    STATUS        current
    DESCRIPTION
        ""
    SYNTAX        Gauge32 (1..5)

CfprApExtmgmtIfType ::= TEXTUAL-CONVENTION
    STATUS        current
    DESCRIPTION
        ""
    SYNTAX        BITS
    {
        lan(0),
        san(1),
        ipc(2)
    }

CfprApExtmgmtIfMonPolicyAdminState ::= TEXTUAL-CONVENTION
    STATUS        current
    DESCRIPTION
        ""
    SYNTAX        INTEGER
    {
        enabled(1),
        disabled(2)
    }

CfprApExtmgmtIfMonPolicyMonitorMechanism ::= TEXTUAL-CONVENTION
    STATUS        current
    DESCRIPTION
        ""
    SYNTAX        INTEGER
    {
        miiStatus(0),
        arpTargetPing(1),
        gatewayPing(2)
    }

CfprApExtmgmtMiiStatusMaxRetryCount ::= TEXTUAL-CONVENTION
    STATUS        current
    DESCRIPTION
        ""
    SYNTAX        Gauge32 (1..3)

CfprApExtmgmtMiiStatusRetryInterval ::= TEXTUAL-CONVENTION
    STATUS        current
    DESCRIPTION
        ""
    SYNTAX        Gauge32 (3..10)

CfprApExtmgmtNdiscTargetsMaxDeadlineTimeout ::= TEXTUAL-CONVENTION
    STATUS        current
    DESCRIPTION
        ""
    SYNTAX        Gauge32 (5..15)

CfprApExtmgmtNdiscTargetsNumberOfNdiscRequests ::= TEXTUAL-CONVENTION
    STATUS        current
    DESCRIPTION
        ""
    SYNTAX        Gauge32 (1..5)

CfprApExtpolAppCapability ::= TEXTUAL-CONVENTION
    STATUS        current
    DESCRIPTION
        ""
    SYNTAX        BITS
    {
        serviceReg(0),
        identifierMgr(1),
        operationMgr(2),
        resourceMgr(3),
        virtualSwitchingMgr(4),
        policyMgr(5),
        bootMgr(6),
        vmMgr(7),
        vmAdmin(8),
        infraCryptoOffloa(9),
        vmm(10),
        vmVasw(11),
        vmFw(12),
        vmSlb(13),
        infraFw(14),
        infraSlb(15),
        ipam(16),
        pcm(17),
        infraAggr(18),
        infraWas(19),
        infraWaf(20),
        infraPasw(21),
        infraPdsw(22),
        storageBroker(23),
        orgMgr(24),
        statsMgr(25),
        centralMgr(26)
    }

CfprApExtpolConnProtocol ::= TEXTUAL-CONVENTION
    STATUS        current
    DESCRIPTION
        ""
    SYNTAX        INTEGER
    {
        ipv4(0),
        ipv6(1),
        unknown(2)
    }

CfprApExtpolConnType ::= TEXTUAL-CONVENTION
    STATUS        current
    DESCRIPTION
        ""
    SYNTAX        INTEGER
    {
        serviceReg(2),
        identifierMgr(3),
        operationMgr(4),
        resourceMgr(5),
        statsMgr(6),
        centralMgr(7),
        virtualSwitchingMgr(8),
        policyMgr(9),
        bootMgr(10),
        vmMgr(11),
        managedEndpoint(12),
        mgmtController(13),
        storageBroker(14),
        resourceAggr(15),
        ape(18)
    }

CfprApExtpolConnectorOperState ::= TEXTUAL-CONVENTION
    STATUS        current
    DESCRIPTION
        ""
    SYNTAX        INTEGER
    {
        unregistered(0),
        lostVisibility(1),
        registering(2),
        synchronizing(3),
        registered(4),
        versionMismatch(5),
        registryNotReachable(6)
    }

CfprApExtpolEpFsmCurrentFsm ::= TEXTUAL-CONVENTION
    STATUS        current
    DESCRIPTION
        ""
    SYNTAX        INTEGER
    {
        nop(0),
        registerFsm(317),
        repairCert(496)
    }

CfprApExtpolEpFsmStageName ::= TEXTUAL-CONVENTION
    STATUS        current
    DESCRIPTION
        ""
    SYNTAX        INTEGER
    {
        nop(0),
        registerFsmBegin(317),
        registerFsmExecute(318),
        repairCertBegin(496),
        repairCertVerifyGuid(497),
        repairCertUnregister(498),
        repairCertCleanOldData(499),
        repairCertRequest(500),
        repairCertVerify(501),
        registerFsmFail(594),
        registerFsmSuccess(595),
        repairCertFail(596),
        repairCertSuccess(597)
    }

CfprApExtpolEpFsmTaskItem ::= TEXTUAL-CONVENTION
    STATUS        current
    DESCRIPTION
        ""
    SYNTAX        INTEGER
    {
        nop(0),
        registerFsm(317),
        repairCert(496)
    }

CfprApExtpolProviderFsmCurrentFsm ::= TEXTUAL-CONVENTION
    STATUS        current
    DESCRIPTION
        ""
    SYNTAX        INTEGER
    {
        nop(0),
        reportConfigImport(462)
    }

CfprApExtpolProviderFsmStageName ::= TEXTUAL-CONVENTION
    STATUS        current
    DESCRIPTION
        ""
    SYNTAX        INTEGER
    {
        nop(0),
        reportConfigImportBegin(462),
        reportConfigImportReport(463),
        reportConfigImportFail(598),
        reportConfigImportSuccess(599)
    }

CfprApExtpolProviderFsmTaskItem ::= TEXTUAL-CONVENTION
    STATUS        current
    DESCRIPTION
        ""
    SYNTAX        INTEGER
    {
        nop(0),
        reportConfigImport(462)
    }

CfprApExtpolRegistryFsmCurrentFsm ::= TEXTUAL-CONVENTION
    STATUS        current
    DESCRIPTION
        ""
    SYNTAX        INTEGER
    {
        nop(0),
        crossDomainConfig(319),
        crossDomainDelete(322)
    }

CfprApExtpolRegistryFsmStageName ::= TEXTUAL-CONVENTION
    STATUS        current
    DESCRIPTION
        ""
    SYNTAX        INTEGER
    {
        nop(0),
        crossDomainConfigBegin(319),
        crossDomainConfigSetLocal(320),
        crossDomainConfigSetPeer(321),
        crossDomainDeleteBegin(322),
        crossDomainDeleteSetLocal(323),
        crossDomainDeleteSetPeer(324),
        crossDomainConfigFail(600),
        crossDomainConfigSuccess(601),
        crossDomainDeleteFail(602),
        crossDomainDeleteSuccess(603)
    }

CfprApExtpolRegistryFsmTaskItem ::= TEXTUAL-CONVENTION
    STATUS        current
    DESCRIPTION
        ""
    SYNTAX        INTEGER
    {
        nop(0),
        crossDomainConfig(319),
        crossDomainDelete(322)
    }

CfprApExtpolState ::= TEXTUAL-CONVENTION
    STATUS        current
    DESCRIPTION
        ""
    SYNTAX        INTEGER
    {
        unknown(0),
        licenseOk(1),
        licenseInsufficient(2),
        licenseGraceperiod(3),
        licenseExpired(4),
        notApplicable(5)
    }

CfprApExtpolSuspendState ::= TEXTUAL-CONVENTION
    STATUS        current
    DESCRIPTION
        ""
    SYNTAX        INTEGER
    {
        off(0),
        on(1)
    }

CfprApExtvmmFabricNetworkType ::= TEXTUAL-CONVENTION
    STATUS        current
    DESCRIPTION
        ""
    SYNTAX        INTEGER
    {
        notConnected(0),
        notConnectedPvlans(1),
        connected(2)
    }

CfprApExtvmmNetworkSetConfigQualifier ::= TEXTUAL-CONVENTION
    STATUS        current
    DESCRIPTION
        ""
    SYNTAX        INTEGER
    {
        normal(0),
        duplicateVmndReference(1)
    }

CfprApExtvmmOwnership ::= TEXTUAL-CONVENTION
    STATUS        current
    DESCRIPTION
        ""
    SYNTAX        INTEGER
    {
        discovered(1),
        managed(2)
    }

CfprApExtvmmRefOperState ::= TEXTUAL-CONVENTION
    STATUS        current
    DESCRIPTION
        ""
    SYNTAX        INTEGER
    {
        up(0),
        invalidReference(1)
    }

CfprApExtvmmVcVersion ::= TEXTUAL-CONVENTION
    STATUS        current
    DESCRIPTION
        ""
    SYNTAX        INTEGER
    {
        unknown(0),
        kl(1),
        klU1(2)
    }

CfprApExtvmmVnicType ::= TEXTUAL-CONVENTION
    STATUS        current
    DESCRIPTION
        ""
    SYNTAX        INTEGER
    {
        unknown(0),
        ether(1),
        fc(4),
        scsi(8),
        ipc(16)
    }

CfprApExtvmmProviderVendorType ::= TEXTUAL-CONVENTION
    STATUS        current
    DESCRIPTION
        ""
    SYNTAX        INTEGER
    {
        unknown(0),
        vmware(1),
        microsoft(2)
    }

CfprApFabricADceSwSrvEpTransport ::= TEXTUAL-CONVENTION
    STATUS        current
    DESCRIPTION
        ""
    SYNTAX        BITS
    {
        ether(0),
        dce(1),
        fc(2)
    }

CfprApFabricAEthEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricAEthEstcEpTransport ::= TEXTUAL-CONVENTION
    STATUS        current
    DESCRIPTION
        ""
    SYNTAX        BITS
    {
        ether(0),
        dce(1),
        fc(2)
    }

CfprApFabricAEthEstcEpType ::= TEXTUAL-CONVENTION
    STATUS        current
    DESCRIPTION
        ""
    SYNTAX        BITS
    {
        lan(0),
        san(1),
        ipc(2)
    }

CfprApFabricAEthLanEpTransport ::= TEXTUAL-CONVENTION
    STATUS        current
    DESCRIPTION
        ""
    SYNTAX        BITS
    {
        ether(0),
        dce(1),
        fc(2)
    }

CfprApFabricAFcEstcEpTransport ::= TEXTUAL-CONVENTION
    STATUS        current
    DESCRIPTION
        ""
    SYNTAX        BITS
    {
        ether(0),
        dce(1),
        fc(2)
    }

CfprApFabricAFcEstcEpType ::= TEXTUAL-CONVENTION
    STATUS        current
    DESCRIPTION
        ""
    SYNTAX        BITS
    {
        lan(0),
        san(1),
        ipc(2)
    }

CfprApFabricAFcSanEpTransport ::= TEXTUAL-CONVENTION
    STATUS        current
    DESCRIPTION
        ""
    SYNTAX        BITS
    {
        ether(0),
        dce(1),
        fc(2)
    }

CfprApFabricAFcoeEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricAFcoeEstcEpTransport ::= TEXTUAL-CONVENTION
    STATUS        current
    DESCRIPTION
        ""
    SYNTAX        BITS
    {
        ether(0),
        dce(1),
        fc(2)
    }

CfprApFabricAFcoeEstcEpType ::= TEXTUAL-CONVENTION
    STATUS        current
    DESCRIPTION
        ""
    SYNTAX        BITS
    {
        lan(0),
        san(1),
        ipc(2)
    }

CfprApFabricAFcoeSanEpTransport ::= TEXTUAL-CONVENTION
    STATUS        current
    DESCRIPTION
        ""
    SYNTAX        BITS
    {
        ether(0),
        dce(1),
        fc(2)
    }

CfprApFabricAVlanAssocPrimaryVlanSwitchId ::= TEXTUAL-CONVENTION
    STATUS        current
    DESCRIPTION
        ""
    SYNTAX        INTEGER
    {
        none(0),
        a(1),
        b(2)
    }

CfprApFabricAVlanSharing ::= TEXTUAL-CONVENTION
    STATUS        current
    DESCRIPTION
        ""
    SYNTAX        INTEGER
    {
        none(0),
        primary(1),
        isolated(2),
        community(3)
    }

CfprApFabricAVlanTransport ::= TEXTUAL-CONVENTION
    STATUS        current
    DESCRIPTION
        ""
    SYNTAX        BITS
    {
        ether(0),
        dce(1),
        fc(2)
    }

CfprApFabricAVlanType ::= TEXTUAL-CONVENTION
    STATUS        current
    DESCRIPTION
        ""
    SYNTAX        BITS
    {
        lan(0),
        san(1),
        ipc(2)
    }

CfprApFabricAVsanTransport ::= TEXTUAL-CONVENTION
    STATUS        current
    DESCRIPTION
        ""
    SYNTAX        BITS
    {
        ether(0),
        dce(1),
        fc(2)
    }

CfprApFabricAVsanType ::= TEXTUAL-CONVENTION
    STATUS        current
    DESCRIPTION
        ""
    SYNTAX        BITS
    {
        lan(0),
        san(1),
        ipc(2)
    }

CfprApFabricAccessType ::= TEXTUAL-CONVENTION
    STATUS        current
    DESCRIPTION
        ""
    SYNTAX        INTEGER
    {
        lan(0),
        san(1)
    }

CfprApFabricAdminState ::= TEXTUAL-CONVENTION
    STATUS        current
    DESCRIPTION
        ""
    SYNTAX        INTEGER
    {
        enabled(1),
        disabled(2)
    }

CfprApFabricBHVlanSwitchId ::= TEXTUAL-CONVENTION
    STATUS        current
    DESCRIPTION
        ""
    SYNTAX        INTEGER
    {
        none(0),
        a(1),
        b(2),
        dual(3)
    }

CfprApFabricBladeLifeCycle ::= TEXTUAL-CONVENTION
    STATUS        current
    DESCRIPTION
        ""
    SYNTAX        INTEGER
    {
        inService(1),
        outOfService(2),
        outOfServiceSlave(3)
    }

CfprApFabricBreakoutPortId ::= TEXTUAL-CONVENTION
    STATUS        current
    DESCRIPTION
        ""
    SYNTAX        Gauge32 (1..4)

CfprApFabricBreakoutSlotId ::= TEXTUAL-CONVENTION
    STATUS        current
    DESCRIPTION
        ""
    SYNTAX        Gauge32 (2..3)

CfprApFabricBreakoutType ::= TEXTUAL-CONVENTION
    STATUS        current
    DESCRIPTION
        ""
    SYNTAX        INTEGER
    {
        unknown(0),
        n10g4x(1)
    }

CfprApFabricCIoEpAdminState ::= TEXTUAL-CONVENTION
    STATUS        current
    DESCRIPTION
        ""
    SYNTAX        INTEGER
    {
        enabled(1),
        disabled(2)
    }

CfprApFabricCIoEpIfType ::= TEXTUAL-CONVENTION
    STATUS        current
    DESCRIPTION
        ""
    SYNTAX        INTEGER
    {
        unknown(0),
        physical(1),
        aggregation(2),
        virtual(3),
        fabric(4)
    }

CfprApFabricCdpLinkPolicyAdminState ::= TEXTUAL-CONVENTION
    STATUS        current
    DESCRIPTION
        ""
    SYNTAX        INTEGER
    {
        enabled(1),
        disabled(2)
    }

CfprApFabricCloudType ::= TEXTUAL-CONVENTION
    STATUS        current
    DESCRIPTION
        ""
    SYNTAX        BITS
    {
        ethlan(0),
        ethestclan(1),
        ethlanmon(2),
        fcsan(3),
        fcsanmon(4),
        fcestc(5)
    }

CfprApFabricComputeEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricComputeEpType ::= TEXTUAL-CONVENTION
    STATUS        current
    DESCRIPTION
        ""
    SYNTAX        BITS
    {
        lan(0),
        san(1),
        ipc(2)
    }

CfprApFabricComputePhEpAdminState ::= TEXTUAL-CONVENTION
    STATUS        current
    DESCRIPTION
        ""
    SYNTAX        INTEGER
    {
        enabled(1),
        disabled(2),
        remove(3)
    }

CfprApFabricComputeSlotEpSlotId ::= TEXTUAL-CONVENTION
    STATUS        current
    DESCRIPTION
        ""
    SYNTAX        Gauge32 (1..8)

CfprApFabricConfMode ::= TEXTUAL-CONVENTION
    STATUS        current
    DESCRIPTION
        ""
    SYNTAX        INTEGER
    {
        none(0),
        logicalConfigInvalid(1),
        validatingConf(2),
        applyPhysTrans(3),
        confSwitch(4)
    }

CfprApFabricConfState ::= TEXTUAL-CONVENTION
    STATUS        current
    DESCRIPTION
        ""
    SYNTAX        INTEGER
    {
        ok(0),
        logicalConfigInvalid(1)
    }

CfprApFabricConfigState ::= TEXTUAL-CONVENTION
    STATUS        current
    DESCRIPTION
        ""
    SYNTAX        INTEGER
    {
        applied(1),
        inconsistent(2)
    }

CfprApFabricDceSwSrvEpPortId ::= TEXTUAL-CONVENTION
    STATUS        current
    DESCRIPTION
        ""
    SYNTAX        Gauge32 (1..48)

CfprApFabricDceSwSrvEpSlotId ::= TEXTUAL-CONVENTION
    STATUS        current
    DESCRIPTION
        ""
    SYNTAX        Gauge32 (1..4)

CfprApFabricDceSwSrvPcAdminState ::= TEXTUAL-CONVENTION
    STATUS        current
    DESCRIPTION
        ""
    SYNTAX        INTEGER
    {
        enabled(1),
        disabled(2)
    }

CfprApFabricDceSwSrvPcPortId ::= TEXTUAL-CONVENTION
    STATUS        current
    DESCRIPTION
        ""
    SYNTAX        Gauge32 (1024..4096)

CfprApFabricDceSwSrvPcTransport ::= TEXTUAL-CONVENTION
    STATUS        current
    DESCRIPTION
        ""
    SYNTAX        BITS
    {
        ether(0),
        dce(1),
        fc(2)
    }

CfprApFabricDceSwSrvPcEpPortId ::= TEXTUAL-CONVENTION
    STATUS        current
    DESCRIPTION
        ""
    SYNTAX        Gauge32 (1..48)

CfprApFabricDceSwSrvPcEpSlotId ::= TEXTUAL-CONVENTION
    STATUS        current
    DESCRIPTION
        ""
    SYNTAX        Gauge32 (1..4)

CfprApFabricDefaultZoningState ::= TEXTUAL-CONVENTION
    STATUS        current
    DESCRIPTION
        ""
    SYNTAX        INTEGER
    {
        disabled(0),
        enabled(1)
    }

CfprApFabricDirection ::= TEXTUAL-CONVENTION
    STATUS        current
    DESCRIPTION
        ""
    SYNTAX        INTEGER
    {
        receive(1),
        transmit(2)
    }

CfprApFabricEpMgrFsmCurrentFsm ::= TEXTUAL-CONVENTION
    STATUS        current
    DESCRIPTION
        ""
    SYNTAX        INTEGER
    {
        nop(0),
        configure(455)
    }

CfprApFabricEpMgrFsmStageName ::= TEXTUAL-CONVENTION
    STATUS        current
    DESCRIPTION
        ""
    SYNTAX        INTEGER
    {
        nop(0),
        configureBegin(455),
        configureValidateConfiguration(456),
        configureApplyPhysical(457),
        configureWaitOnPhys(458),
        configureApplyConfig(459),
        configureFail(604),
        configureSuccess(605)
    }

CfprApFabricEpMgrFsmTaskFlags ::= TEXTUAL-CONVENTION
    STATUS        current
    DESCRIPTION
        ""
    SYNTAX        BITS
    {
        samDmeFabricEpMgrConfigurePhysChange(26),
        samDmeFabricEpMgrConfigureModification(27),
        samDmeFabricEpMgrConfigureEthServerConfig(28),
        samDmeFabricEpMgrConfigureEthUplinkConfig(29),
        samDmeFabricEpMgrConfigureFcUplinkConfig(30),
        samDmeFabricEpMgrConfigureEthStorageConfig(31),
        samDmeFabricEpMgrConfigureFcStorageConfig(32)
    }

CfprApFabricEpMgrFsmTaskItem ::= TEXTUAL-CONVENTION
    STATUS        current
    DESCRIPTION
        ""
    SYNTAX        INTEGER
    {
        nop(0),
        configure(455)
    }

CfprApFabricEpVlanVlanType ::= TEXTUAL-CONVENTION
    STATUS        current
    DESCRIPTION
        ""
    SYNTAX        INTEGER
    {
        regular(0),
        default(1),
        native(2),
        fcoeuplinknative(3)
    }

CfprApFabricEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricEstcPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricEstcPcType ::= TEXTUAL-CONVENTION
    STATUS        current
    DESCRIPTION
        ""
    SYNTAX        BITS
    {
        lan(0),
        san(1),
        ipc(2)
    }

CfprApFabricEthCdpPolicyProtocol ::= TEXTUAL-CONVENTION
    STATUS        current
    DESCRIPTION
        ""
    SYNTAX        INTEGER
    {
        unknown(0),
        udld(1),
        cdp(2)
    }

CfprApFabricEthEstcTransport ::= TEXTUAL-CONVENTION
    STATUS        current
    DESCRIPTION
        ""
    SYNTAX        BITS
    {
        ether(0),
        dce(1),
        fc(2)
    }

CfprApFabricEthEstcType ::= TEXTUAL-CONVENTION
    STATUS        current
    DESCRIPTION
        ""
    SYNTAX        BITS
    {
        lan(0),
        san(1),
        ipc(2)
    }

CfprApFabricEthEstcEpPortId ::= TEXTUAL-CONVENTION
    STATUS        current
    DESCRIPTION
        ""
    SYNTAX        Gauge32 (1..48)

CfprApFabricEthEstcEpPrio ::= TEXTUAL-CONVENTION
    STATUS        current
    DESCRIPTION
        ""
    SYNTAX        INTEGER
    {
        fc(1),
        platinum(2),
        gold(3),
        silver(4),
        bronze(5),
        bestEffort(6)
    }

CfprApFabricEthEstcEpSlotId ::= TEXTUAL-CONVENTION
    STATUS        current
    DESCRIPTION
        ""
    SYNTAX        Gauge32 (1..4)

CfprApFabricEthEstcEpTransport ::= TEXTUAL-CONVENTION
    STATUS        current
    DESCRIPTION
        ""
    SYNTAX        BITS
    {
        ether(0),
        dce(1),
        fc(2)
    }

CfprApFabricEthEstcEpType ::= TEXTUAL-CONVENTION
    STATUS        current
    DESCRIPTION
        ""
    SYNTAX        BITS
    {
        lan(0),
        san(1),
        ipc(2)
    }

CfprApFabricEthEstcOperPortMode ::= TEXTUAL-CONVENTION
    STATUS        current
    DESCRIPTION
        ""
    SYNTAX        INTEGER
    {
        regularTrunk(1),
        regularAccess(2),
        promiscuousTrunk(3),
        promiscuousAccess(4)
    }

CfprApFabricEthEstcPcTransport ::= TEXTUAL-CONVENTION
    STATUS        current
    DESCRIPTION
        ""
    SYNTAX        BITS
    {
        ether(0),
        dce(1),
        fc(2)
    }

CfprApFabricEthEstcPcEpPortId ::= TEXTUAL-CONVENTION
    STATUS        current
    DESCRIPTION
        ""
    SYNTAX        Gauge32 (1..48)

CfprApFabricEthEstcPcEpSlotId ::= TEXTUAL-CONVENTION
    STATUS        current
    DESCRIPTION
        ""
    SYNTAX        Gauge32 (1..4)

CfprApFabricEthEstcPortMode ::= TEXTUAL-CONVENTION
    STATUS        current
    DESCRIPTION
        ""
    SYNTAX        INTEGER
    {
        trunk(1),
        access(2)
    }

CfprApFabricEthFlowMonLanTransport ::= TEXTUAL-CONVENTION
    STATUS        current
    DESCRIPTION
        ""
    SYNTAX        BITS
    {
        ether(0),
        dce(1),
        fc(2)
    }

CfprApFabricEthFlowMonLanType ::= TEXTUAL-CONVENTION
    STATUS        current
    DESCRIPTION
        ""
    SYNTAX        BITS
    {
        lan(0),
        san(1),
        ipc(2)
    }

CfprApFabricEthFlowMonSourceType ::= TEXTUAL-CONVENTION
    STATUS        current
    DESCRIPTION
        ""
    SYNTAX        INTEGER
    {
        vnic(1),
        portProfile(2)
    }

CfprApFabricEthFlowMonSrcRefType ::= TEXTUAL-CONVENTION
    STATUS        current
    DESCRIPTION
        ""
    SYNTAX        BITS
    {
        lan(0),
        san(1),
        ipc(2)
    }

CfprApFabricEthLanTransport ::= TEXTUAL-CONVENTION
    STATUS        current
    DESCRIPTION
        ""
    SYNTAX        BITS
    {
        ether(0),
        dce(1),
        fc(2)
    }

CfprApFabricEthLanEpAdminState ::= TEXTUAL-CONVENTION
    STATUS        current
    DESCRIPTION
        ""
    SYNTAX        INTEGER
    {
        enabled(1),
        disabled(2)
    }

CfprApFabricEthLanEpSpeedCap ::= TEXTUAL-CONVENTION
    STATUS        current
    DESCRIPTION
        ""
    SYNTAX        BITS
    {
        auto(0)
    }

CfprApFabricEthLanEpVlanStatus ::= TEXTUAL-CONVENTION
    STATUS        current
    DESCRIPTION
        ""
    SYNTAX        INTEGER
    {
        ok(0),
        missingPrimary(1)
    }

CfprApFabricEthLanFlowMonTransport ::= TEXTUAL-CONVENTION
    STATUS        current
    DESCRIPTION
        ""
    SYNTAX        BITS
    {
        ether(0),
        dce(1),
        fc(2)
    }

CfprApFabricEthLanFlowMonCollectorTransport ::= TEXTUAL-CONVENTION
    STATUS        current
    DESCRIPTION
        ""
    SYNTAX        BITS
    {
        ether(0),
        dce(1),
        fc(2)
    }

CfprApFabricEthLanFlowMonExporterTransport ::= TEXTUAL-CONVENTION
    STATUS        current
    DESCRIPTION
        ""
    SYNTAX        BITS
    {
        ether(0),
        dce(1),
        fc(2)
    }

CfprApFabricEthLanFlowMonSrcEpTransport ::= TEXTUAL-CONVENTION
    STATUS        current
    DESCRIPTION
        ""
    SYNTAX        BITS
    {
        ether(0),
        dce(1),
        fc(2)
    }

CfprApFabricEthLanFlowMonitorTransport ::= TEXTUAL-CONVENTION
    STATUS        current
    DESCRIPTION
        ""
    SYNTAX        BITS
    {
        ether(0),
        dce(1),
        fc(2)
    }

CfprApFabricEthLanFlowMonitoringType ::= TEXTUAL-CONVENTION
    STATUS        current
    DESCRIPTION
        ""
    SYNTAX        INTEGER
    {
        unknown(0),
        ethFlowMonitoring(1),
        span(2)
    }

CfprApFabricEthLanPcAdminState ::= TEXTUAL-CONVENTION
    STATUS        current
    DESCRIPTION
        ""
    SYNTAX        INTEGER
    {
        enabled(1),
        disabled(2)
    }

CfprApFabricEthLanPcLacpDetach ::= TEXTUAL-CONVENTION
    STATUS        current
    DESCRIPTION
        ""
    SYNTAX        INTEGER
    {
        enabled(1),
        disabled(2)
    }

CfprApFabricEthLanPcSpeedCap ::= TEXTUAL-CONVENTION
    STATUS        current
    DESCRIPTION
        ""
    SYNTAX        BITS
    {
        auto(0)
    }

CfprApFabricEthLanPcTransport ::= TEXTUAL-CONVENTION
    STATUS        current
    DESCRIPTION
        ""
    SYNTAX        BITS
    {
        ether(0),
        dce(1),
        fc(2)
    }

CfprApFabricEthLanPcVlanStatus ::= TEXTUAL-CONVENTION
    STATUS        current
    DESCRIPTION
        ""
    SYNTAX        INTEGER
    {
        ok(0),
        missingPrimary(1)
    }

CfprApFabricEthLinkPolicyType ::= TEXTUAL-CONVENTION
    STATUS        current
    DESCRIPTION
        ""
    SYNTAX        BITS
    {
        lan(0),
        san(1),
        ipc(2)
    }

CfprApFabricEthMonTransport ::= TEXTUAL-CONVENTION
    STATUS        current
    DESCRIPTION
        ""
    SYNTAX        BITS
    {
        ether(0),
        dce(1),
        fc(2)
    }

CfprApFabricEthMonType ::= TEXTUAL-CONVENTION
    STATUS        current
    DESCRIPTION
        ""
    SYNTAX        BITS
    {
        lan(0),
        san(1),
        ipc(2)
    }

CfprApFabricEthMonDestEpAdminSpeed ::= TEXTUAL-CONVENTION
    STATUS        current
    DESCRIPTION
        ""
    SYNTAX        INTEGER
    {
        indeterminate(0),
        n1gbps(1),
        n10gbps(2),
        n20gbps(3),
        n40gbps(4)
    }

CfprApFabricEthMonDestEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricEthMonDestEpPortId ::= TEXTUAL-CONVENTION
    STATUS        current
    DESCRIPTION
        ""
    SYNTAX        Gauge32 (1..48)

CfprApFabricEthMonDestEpSlotId ::= TEXTUAL-CONVENTION
    STATUS        current
    DESCRIPTION
        ""
    SYNTAX        Gauge32 (1..4)

CfprApFabricEthMonDestEpType ::= TEXTUAL-CONVENTION
    STATUS        current
    DESCRIPTION
        ""
    SYNTAX        BITS
    {
        lan(0),
        san(1),
        ipc(2)
    }

CfprApFabricEthMonFiltEpType ::= TEXTUAL-CONVENTION
    STATUS        current
    DESCRIPTION
        ""
    SYNTAX        BITS
    {
        lan(0),
        san(1),
        ipc(2)
    }

CfprApFabricEthMonFiltRefType ::= TEXTUAL-CONVENTION
    STATUS        current
    DESCRIPTION
        ""
    SYNTAX        BITS
    {
        lan(0),
        san(1),
        ipc(2)
    }

CfprApFabricEthMonLanTransport ::= TEXTUAL-CONVENTION
    STATUS        current
    DESCRIPTION
        ""
    SYNTAX        BITS
    {
        ether(0),
        dce(1),
        fc(2)
    }

CfprApFabricEthMonLanType ::= TEXTUAL-CONVENTION
    STATUS        current
    DESCRIPTION
        ""
    SYNTAX        BITS
    {
        lan(0),
        san(1),
        ipc(2)
    }

CfprApFabricEthMonSrcEpType ::= TEXTUAL-CONVENTION
    STATUS        current
    DESCRIPTION
        ""
    SYNTAX        BITS
    {
        lan(0),
        san(1),
        ipc(2)
    }

CfprApFabricEthMonSrcRefType ::= TEXTUAL-CONVENTION
    STATUS        current
    DESCRIPTION
        ""
    SYNTAX        BITS
    {
        lan(0),
        san(1),
        ipc(2)
    }

CfprApFabricEthPcProtocol ::= TEXTUAL-CONVENTION
    STATUS        current
    DESCRIPTION
        ""
    SYNTAX        INTEGER
    {
        static(1),
        lacp(2)
    }

CfprApFabricEthSourceType ::= TEXTUAL-CONVENTION
    STATUS        current
    DESCRIPTION
        ""
    SYNTAX        INTEGER
    {
        vnic(1),
        uplinkPort(2),
        vlan(3),
        serverPort(4),
        portChannel(5),
        hostPort(6),
        storage(7),
        nasPort(8),
        nasPortChannel(9),
        fcoeuplinkPort(10),
        fcoeuplinkPortchannel(11),
        vmNic(12),
        vhba(20)
    }

CfprApFabricEthTargetEpTransport ::= TEXTUAL-CONVENTION
    STATUS        current
    DESCRIPTION
        ""
    SYNTAX        BITS
    {
        ether(0),
        dce(1),
        fc(2)
    }

CfprApFabricEthUdldPolicyProtocol ::= TEXTUAL-CONVENTION
    STATUS        current
    DESCRIPTION
        ""
    SYNTAX        INTEGER
    {
        unknown(0),
        udld(1),
        cdp(2)
    }

CfprApFabricEthVlanPcTransport ::= TEXTUAL-CONVENTION
    STATUS        current
    DESCRIPTION
        ""
    SYNTAX        BITS
    {
        ether(0),
        dce(1),
        fc(2)
    }

CfprApFabricExternalLocale ::= TEXTUAL-CONVENTION
    STATUS        current
    DESCRIPTION
        ""
    SYNTAX        BITS
    {
        server(0),
        chassis(1),
        internal(2),
        external(3)
    }

CfprApFabricExternalEpAdminState ::= TEXTUAL-CONVENTION
    STATUS        current
    DESCRIPTION
        ""
    SYNTAX        INTEGER
    {
        enabled(1),
        disabled(2)
    }

CfprApFabricExternalEpLocale ::= TEXTUAL-CONVENTION
    STATUS        current
    DESCRIPTION
        ""
    SYNTAX        BITS
    {
        server(0),
        chassis(1),
        internal(2),
        external(3)
    }

CfprApFabricExternalPcLocale ::= TEXTUAL-CONVENTION
    STATUS        current
    DESCRIPTION
        ""
    SYNTAX        BITS
    {
        server(0),
        chassis(1),
        internal(2),
        external(3)
    }

CfprApFabricFcEstcTransport ::= TEXTUAL-CONVENTION
    STATUS        current
    DESCRIPTION
        ""
    SYNTAX        BITS
    {
        ether(0),
        dce(1),
        fc(2)
    }

CfprApFabricFcEstcType ::= TEXTUAL-CONVENTION
    STATUS        current
    DESCRIPTION
        ""
    SYNTAX        BITS
    {
        lan(0),
        san(1),
        ipc(2)
    }

CfprApFabricFcEstcEpPortId ::= TEXTUAL-CONVENTION
    STATUS        current
    DESCRIPTION
        ""
    SYNTAX        Gauge32 (1..48)

CfprApFabricFcEstcEpSlotId ::= TEXTUAL-CONVENTION
    STATUS        current
    DESCRIPTION
        ""
    SYNTAX        Gauge32 (1..5)

CfprApFabricFcMonTransport ::= TEXTUAL-CONVENTION
    STATUS        current
    DESCRIPTION
        ""
    SYNTAX        BITS
    {
        ether(0),
        dce(1),
        fc(2)
    }

CfprApFabricFcMonType ::= TEXTUAL-CONVENTION
    STATUS        current
    DESCRIPTION
        ""
    SYNTAX        BITS
    {
        lan(0),
        san(1),
        ipc(2)
    }

CfprApFabricFcMonDestEpAdminSpeed ::= TEXTUAL-CONVENTION
    STATUS        current
    DESCRIPTION
        ""
    SYNTAX        INTEGER
    {
        indeterminate(0),
        n1gbps(1),
        n2gbps(2),
        n4gbps(3),
        n8gbps(4),
        auto(5)
    }

CfprApFabricFcMonDestEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricFcMonDestEpPortId ::= TEXTUAL-CONVENTION
    STATUS        current
    DESCRIPTION
        ""
    SYNTAX        Gauge32 (1..48)

CfprApFabricFcMonDestEpSlotId ::= TEXTUAL-CONVENTION
    STATUS        current
    DESCRIPTION
        ""
    SYNTAX        Gauge32 (1..5)

CfprApFabricFcMonDestEpType ::= TEXTUAL-CONVENTION
    STATUS        current
    DESCRIPTION
        ""
    SYNTAX        BITS
    {
        lan(0),
        san(1),
        ipc(2)
    }

CfprApFabricFcMonFiltEpType ::= TEXTUAL-CONVENTION
    STATUS        current
    DESCRIPTION
        ""
    SYNTAX        BITS
    {
        lan(0),
        san(1),
        ipc(2)
    }

CfprApFabricFcMonFiltRefType ::= TEXTUAL-CONVENTION
    STATUS        current
    DESCRIPTION
        ""
    SYNTAX        BITS
    {
        lan(0),
        san(1),
        ipc(2)
    }

CfprApFabricFcMonSanTransport ::= TEXTUAL-CONVENTION
    STATUS        current
    DESCRIPTION
        ""
    SYNTAX        BITS
    {
        ether(0),
        dce(1),
        fc(2)
    }

CfprApFabricFcMonSanType ::= TEXTUAL-CONVENTION
    STATUS        current
    DESCRIPTION
        ""
    SYNTAX        BITS
    {
        lan(0),
        san(1),
        ipc(2)
    }

CfprApFabricFcMonSrcEpType ::= TEXTUAL-CONVENTION
    STATUS        current
    DESCRIPTION
        ""
    SYNTAX        BITS
    {
        lan(0),
        san(1),
        ipc(2)
    }

CfprApFabricFcMonSrcRefType ::= TEXTUAL-CONVENTION
    STATUS        current
    DESCRIPTION
        ""
    SYNTAX        BITS
    {
        lan(0),
        san(1),
        ipc(2)
    }

CfprApFabricFcSanTransport ::= TEXTUAL-CONVENTION
    STATUS        current
    DESCRIPTION
        ""
    SYNTAX        BITS
    {
        ether(0),
        dce(1),
        fc(2)
    }

CfprApFabricFcSanUplinkTrunking ::= TEXTUAL-CONVENTION
    STATUS        current
    DESCRIPTION
        ""
    SYNTAX        INTEGER
    {
        disabled(0),
        enabled(1)
    }

CfprApFabricFcSanEpPortId ::= TEXTUAL-CONVENTION
    STATUS        current
    DESCRIPTION
        ""
    SYNTAX        Gauge32 (1..48)

CfprApFabricFcSanEpSlotId ::= TEXTUAL-CONVENTION
    STATUS        current
    DESCRIPTION
        ""
    SYNTAX        Gauge32 (1..5)

CfprApFabricFcSanPcTransport ::= TEXTUAL-CONVENTION
    STATUS        current
    DESCRIPTION
        ""
    SYNTAX        BITS
    {
        ether(0),
        dce(1),
        fc(2)
    }

CfprApFabricFcSanPcEpPortId ::= TEXTUAL-CONVENTION
    STATUS        current
    DESCRIPTION
        ""
    SYNTAX        Gauge32 (1..48)

CfprApFabricFcSanPcEpSlotId ::= TEXTUAL-CONVENTION
    STATUS        current
    DESCRIPTION
        ""
    SYNTAX        Gauge32 (1..5)

CfprApFabricFcSourceType ::= TEXTUAL-CONVENTION
    STATUS        current
    DESCRIPTION
        ""
    SYNTAX        INTEGER
    {
        uplinkPort(2),
        vsan(3),
        storage(4),
        portChannel(5),
        vhba(20)
    }

CfprApFabricFcVsanPcTransport ::= TEXTUAL-CONVENTION
    STATUS        current
    DESCRIPTION
        ""
    SYNTAX        BITS
    {
        ether(0),
        dce(1),
        fc(2)
    }

CfprApFabricFcVsanPortEpPortId ::= TEXTUAL-CONVENTION
    STATUS        current
    DESCRIPTION
        ""
    SYNTAX        Gauge32 (1..256)

CfprApFabricFcVsanPortEpSlotId ::= TEXTUAL-CONVENTION
    STATUS        current
    DESCRIPTION
        ""
    SYNTAX        Gauge32 (1..5)

CfprApFabricFcZoneSharingMode ::= TEXTUAL-CONVENTION
    STATUS        current
    DESCRIPTION
        ""
    SYNTAX        INTEGER
    {
        coalesce(0),
        clearUnmanagedZoneAll(1)
    }

CfprApFabricFcoeEstcEpPortId ::= TEXTUAL-CONVENTION
    STATUS        current
    DESCRIPTION
        ""
    SYNTAX        Gauge32 (1..48)

CfprApFabricFcoeEstcEpSlotId ::= TEXTUAL-CONVENTION
    STATUS        current
    DESCRIPTION
        ""
    SYNTAX        Gauge32 (1..4)

CfprApFabricFcoeSanEpPortId ::= TEXTUAL-CONVENTION
    STATUS        current
    DESCRIPTION
        ""
    SYNTAX        Gauge32 (1..48)

CfprApFabricFcoeSanEpSlotId ::= TEXTUAL-CONVENTION
    STATUS        current
    DESCRIPTION
        ""
    SYNTAX        Gauge32 (1..5)

CfprApFabricFcoeSanPcTransport ::= TEXTUAL-CONVENTION
    STATUS        current
    DESCRIPTION
        ""
    SYNTAX        BITS
    {
        ether(0),
        dce(1),
        fc(2)
    }

CfprApFabricFcoeSanPcEpPortId ::= TEXTUAL-CONVENTION
    STATUS        current
    DESCRIPTION
        ""
    SYNTAX        Gauge32 (1..48)

CfprApFabricFcoeSanPcEpSlotId ::= TEXTUAL-CONVENTION
    STATUS        current
    DESCRIPTION
        ""
    SYNTAX        Gauge32 (1..5)

CfprApFabricFcoeVsanPcTransport ::= TEXTUAL-CONVENTION
    STATUS        current
    DESCRIPTION
        ""
    SYNTAX        BITS
    {
        ether(0),
        dce(1),
        fc(2)
    }

CfprApFabricFcoeVsanPortEpPortId ::= TEXTUAL-CONVENTION
    STATUS        current
    DESCRIPTION
        ""
    SYNTAX        Gauge32 (1..256)

CfprApFabricFcoeVsanPortEpSlotId ::= TEXTUAL-CONVENTION
    STATUS        current
    DESCRIPTION
        ""
    SYNTAX        Gauge32 (1..5)

CfprApFabricFillPattern ::= TEXTUAL-CONVENTION
    STATUS        current
    DESCRIPTION
        ""
    SYNTAX        INTEGER
    {
        idle(0),
        arbff(1)
    }

CfprApFabricFlowMonCollectorLocale ::= TEXTUAL-CONVENTION
    STATUS        current
    DESCRIPTION
        ""
    SYNTAX        BITS
    {
        server(0),
        chassis(1),
        internal(2),
        external(3)
    }

CfprApFabricFlowMonDefType ::= TEXTUAL-CONVENTION
    STATUS        current
    DESCRIPTION
        ""
    SYNTAX        INTEGER
    {
        systemDefined(1),
        userDefined(2)
    }

CfprApFabricFlowMonIpv4Keys ::= TEXTUAL-CONVENTION
    STATUS        current
    DESCRIPTION
        ""
    SYNTAX        BITS
    {
        ipv4SrcAddress(0),
        ipv4DestAddress(1),
        ipProtocol(2),
        ipTos(3),
        srcPort(4),
        destPort(5)
    }

CfprApFabricFlowMonIpv6Keys ::= TEXTUAL-CONVENTION
    STATUS        current
    DESCRIPTION
        ""
    SYNTAX        BITS
    {
        ipv6SrcAddress(0),
        ipv6DestAddress(1),
        ipProtocol(2),
        reserved(3),
        srcPort(4),
        destPort(5)
    }

CfprApFabricFlowMonKeyType ::= TEXTUAL-CONVENTION
    STATUS        current
    DESCRIPTION
        ""
    SYNTAX        INTEGER
    {
        l2keys(0),
        ipv4keys(1),
        ipv6keys(2)
    }

CfprApFabricFlowMonL2Keys ::= TEXTUAL-CONVENTION
    STATUS        current
    DESCRIPTION
        ""
    SYNTAX        BITS
    {
        ethertype(0),
        destMacAddress(1),
        srcMacAddress(2)
    }

CfprApFabricFlowMonNonKeys ::= TEXTUAL-CONVENTION
    STATUS        current
    DESCRIPTION
        ""
    SYNTAX        BITS
    {
        counterPacketsLong(0),
        counterBytesLong(1),
        sysUptimeFirst(2),
        sysUptimeLast(3)
    }

CfprApFabricFlowMonitoringCategoryAdminState ::= TEXTUAL-CONVENTION
    STATUS        current
    DESCRIPTION
        ""
    SYNTAX        INTEGER
    {
        enabled(1),
        disabled(2)
    }

CfprApFabricHostPortId ::= TEXTUAL-CONVENTION
    STATUS        current
    DESCRIPTION
        ""
    SYNTAX        INTEGER
    {
        any(0),
        n1(1),
        n2(2),
        none(10)
    }

CfprApFabricInternalLocale ::= TEXTUAL-CONVENTION
    STATUS        current
    DESCRIPTION
        ""
    SYNTAX        BITS
    {
        server(0),
        chassis(1),
        internal(2),
        external(3)
    }

CfprApFabricInternalDceSrvTransport ::= TEXTUAL-CONVENTION
    STATUS        current
    DESCRIPTION
        ""
    SYNTAX        BITS
    {
        ether(0),
        dce(1),
        fc(2)
    }

CfprApFabricInternalDceSrvType ::= TEXTUAL-CONVENTION
    STATUS        current
    DESCRIPTION
        ""
    SYNTAX        BITS
    {
        lan(0),
        san(1),
        ipc(2)
    }

CfprApFabricInternalEpAdminState ::= TEXTUAL-CONVENTION
    STATUS        current
    DESCRIPTION
        ""
    SYNTAX        INTEGER
    {
        enabled(1),
        disabled(2)
    }

CfprApFabricInternalEpLocale ::= TEXTUAL-CONVENTION
    STATUS        current
    DESCRIPTION
        ""
    SYNTAX        BITS
    {
        server(0),
        chassis(1),
        internal(2),
        external(3)
    }

CfprApFabricInternalPcLocale ::= TEXTUAL-CONVENTION
    STATUS        current
    DESCRIPTION
        ""
    SYNTAX        BITS
    {
        server(0),
        chassis(1),
        internal(2),
        external(3)
    }

CfprApFabricLacpMode ::= TEXTUAL-CONVENTION
    STATUS        current
    DESCRIPTION
        ""
    SYNTAX        INTEGER
    {
        none(0),
        active(1),
        on(2),
        passive(3)
    }

CfprApFabricLacpRate ::= TEXTUAL-CONVENTION
    STATUS        current
    DESCRIPTION
        ""
    SYNTAX        INTEGER
    {
        normal(0),
        fast(1)
    }

CfprApFabricLacpSuspend ::= TEXTUAL-CONVENTION
    STATUS        current
    DESCRIPTION
        ""
    SYNTAX        INTEGER
    {
        false(0),
        true(1)
    }

CfprApFabricLanType ::= TEXTUAL-CONVENTION
    STATUS        current
    DESCRIPTION
        ""
    SYNTAX        BITS
    {
        lan(0),
        san(1),
        ipc(2)
    }

CfprApFabricLanCloudVlanCompression ::= TEXTUAL-CONVENTION
    STATUS        current
    DESCRIPTION
        ""
    SYNTAX        INTEGER
    {
        enabled(1),
        disabled(2)
    }

CfprApFabricLanCloudFsmCurrentFsm ::= TEXTUAL-CONVENTION
    STATUS        current
    DESCRIPTION
        ""
    SYNTAX        INTEGER
    {
        nop(0),
        switchMode(449)
    }

CfprApFabricLanCloudFsmStageName ::= TEXTUAL-CONVENTION
    STATUS        current
    DESCRIPTION
        ""
    SYNTAX        INTEGER
    {
        nop(0),
        switchModeBegin(449),
        switchModeSwConfigPeer(450),
        switchModeSwConfigLocal(451),
        switchModeFail(606),
        switchModeSuccess(607)
    }

CfprApFabricLanCloudFsmTaskItem ::= TEXTUAL-CONVENTION
    STATUS        current
    DESCRIPTION
        ""
    SYNTAX        INTEGER
    {
        nop(0),
        switchMode(449)
    }

CfprApFabricLanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricLanEpType ::= TEXTUAL-CONVENTION
    STATUS        current
    DESCRIPTION
        ""
    SYNTAX        BITS
    {
        lan(0),
        san(1),
        ipc(2)
    }

CfprApFabricLanFlowMonType ::= TEXTUAL-CONVENTION
    STATUS        current
    DESCRIPTION
        ""
    SYNTAX        BITS
    {
        lan(0),
        san(1),
        ipc(2)
    }

CfprApFabricLanFlowMonCollectorType ::= TEXTUAL-CONVENTION
    STATUS        current
    DESCRIPTION
        ""
    SYNTAX        BITS
    {
        lan(0),
        san(1),
        ipc(2)
    }

CfprApFabricLanFlowMonExporterType ::= TEXTUAL-CONVENTION
    STATUS        current
    DESCRIPTION
        ""
    SYNTAX        BITS
    {
        lan(0),
        san(1),
        ipc(2)
    }

CfprApFabricLanFlowMonSrcEpType ::= TEXTUAL-CONVENTION
    STATUS        current
    DESCRIPTION
        ""
    SYNTAX        BITS
    {
        lan(0),
        san(1),
        ipc(2)
    }

CfprApFabricLanFlowMonitorType ::= TEXTUAL-CONVENTION
    STATUS        current
    DESCRIPTION
        ""
    SYNTAX        BITS
    {
        lan(0),
        san(1),
        ipc(2)
    }

CfprApFabricLanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricLanPcType ::= TEXTUAL-CONVENTION
    STATUS        current
    DESCRIPTION
        ""
    SYNTAX        BITS
    {
        lan(0),
        san(1),
        ipc(2)
    }

CfprApFabricLifeCycle ::= TEXTUAL-CONVENTION
    STATUS        current
    DESCRIPTION
        ""
    SYNTAX        INTEGER
    {
        inService(1),
        outOfService(2),
        outOfServiceSlave(3)
    }

CfprApFabricMemberStatus ::= TEXTUAL-CONVENTION
    STATUS        current
    DESCRIPTION
        ""
    SYNTAX        INTEGER
    {
        up(0),
        down(1)
    }

CfprApFabricMembershipStatus ::= TEXTUAL-CONVENTION
    STATUS        current
    DESCRIPTION
        ""
    SYNTAX        INTEGER
    {
        down(1),
        up(2),
        hotStandby(3),
        suspended(4),
        individual(5),
        moduleRemoved(6),
        incompatibleSpeed(7),
        unknown(8)
    }

CfprApFabricMonAdminState ::= TEXTUAL-CONVENTION
    STATUS        current
    DESCRIPTION
        ""
    SYNTAX        INTEGER
    {
        enabled(1),
        disabled(2)
    }

CfprApFabricMonOperState ::= TEXTUAL-CONVENTION
    STATUS        current
    DESCRIPTION
        ""
    SYNTAX        INTEGER
    {
        unknown(0),
        up(1),
        down(2),
        error(3)
    }

CfprApFabricMonOperStateReason ::= TEXTUAL-CONVENTION
    STATUS        current
    DESCRIPTION
        ""
    SYNTAX        INTEGER
    {
        active(0),
        noHardwareResource(1),
        noOperationalSrcDst(2),
        genericError(3),
        noSourcesConfigured(4),
        noDestinationConfigured(5),
        noSourceDestinationConfigured(6),
        sessionAdminShut(7),
        wrongDestinationMode(8),
        wrongSourceMode(9),
        tunnelMisconfDown(10),
        noFlowIdSpecified(11),
        unknown(12)
    }

CfprApFabricNFExporterVersion ::= TEXTUAL-CONVENTION
    STATUS        current
    DESCRIPTION
        ""
    SYNTAX        INTEGER
    {
        v9(1),
        ipfix(2)
    }

CfprApFabricNFTransport ::= TEXTUAL-CONVENTION
    STATUS        current
    DESCRIPTION
        ""
    SYNTAX        INTEGER
    {
        udp(1),
        sctp(2)
    }

CfprApFabricNetGroupSwitchId ::= TEXTUAL-CONVENTION
    STATUS        current
    DESCRIPTION
        ""
    SYNTAX        INTEGER
    {
        none(0),
        a(1),
        b(2),
        dual(3)
    }

CfprApFabricNetGroupType ::= TEXTUAL-CONVENTION
    STATUS        current
    DESCRIPTION
        ""
    SYNTAX        BITS
    {
        mgmt(0),
        vlanCompression(1),
        vlanUncompressed(2)
    }

CfprApFabricNetflowCollectorFlowProtocol ::= TEXTUAL-CONVENTION
    STATUS        current
    DESCRIPTION
        ""
    SYNTAX        INTEGER
    {
        netflow(1)
    }

CfprApFabricNetflowConfigIssues ::= TEXTUAL-CONVENTION
    STATUS        current
    DESCRIPTION
        ""
    SYNTAX        BITS
    {
        monitorUnresolved(0),
        exporterUnresolved(1),
        exporterProfileUnresolved(2),
        collectorUnresolved(3),
        sourceVlanUnresolved(4)
    }

CfprApFabricNetflowMonExporterProtocol ::= TEXTUAL-CONVENTION
    STATUS        current
    DESCRIPTION
        ""
    SYNTAX        INTEGER
    {
        netflow(1)
    }

CfprApFabricNetflowMonSessionAdminState ::= TEXTUAL-CONVENTION
    STATUS        current
    DESCRIPTION
        ""
    SYNTAX        INTEGER
    {
        enabled(1),
        disabled(2)
    }

CfprApFabricNetflowMonSessionProtocol ::= TEXTUAL-CONVENTION
    STATUS        current
    DESCRIPTION
        ""
    SYNTAX        INTEGER
    {
        netflow(1)
    }

CfprApFabricNetflowMonSrcEpProtocol ::= TEXTUAL-CONVENTION
    STATUS        current
    DESCRIPTION
        ""
    SYNTAX        INTEGER
    {
        netflow(1)
    }

CfprApFabricNetflowMonSrcRefProtocol ::= TEXTUAL-CONVENTION
    STATUS        current
    DESCRIPTION
        ""
    SYNTAX        INTEGER
    {
        netflow(1)
    }

CfprApFabricNetflowMonitorFlowMonProtocol ::= TEXTUAL-CONVENTION
    STATUS        current
    DESCRIPTION
        ""
    SYNTAX        INTEGER
    {
        netflow(1)
    }

CfprApFabricOperState ::= TEXTUAL-CONVENTION
    STATUS        current
    DESCRIPTION
        ""
    SYNTAX        INTEGER
    {
        unknown(0),
        up(1),
        down(2),
        errorMisconfigured(3)
    }

CfprApFabricOwner ::= TEXTUAL-CONVENTION
    STATUS        current
    DESCRIPTION
        ""
    SYNTAX        INTEGER
    {
        policy(1),
        management(2)
    }

CfprApFabricPIoEpIfType ::= TEXTUAL-CONVENTION
    STATUS        current
    DESCRIPTION
        ""
    SYNTAX        INTEGER
    {
        unknown(0),
        physical(1),
        aggregation(2),
        virtual(3),
        fabric(4)
    }

CfprApFabricPIoEpOperState ::= TEXTUAL-CONVENTION
    STATUS        current
    DESCRIPTION
        ""
    SYNTAX        INTEGER
    {
        unknown(0),
        up(1),
        down(2),
        errorMisconfigured(3)
    }

CfprApFabricPIoEpPortId ::= TEXTUAL-CONVENTION
    STATUS        current
    DESCRIPTION
        ""
    SYNTAX        Gauge32 (1..48)

CfprApFabricPIoEpSlotId ::= TEXTUAL-CONVENTION
    STATUS        current
    DESCRIPTION
        ""
    SYNTAX        Gauge32 (1..4)

CfprApFabricPathEpIfType ::= TEXTUAL-CONVENTION
    STATUS        current
    DESCRIPTION
        ""
    SYNTAX        INTEGER
    {
        unknown(0),
        physical(1),
        aggregation(2),
        virtual(3),
        fabric(4)
    }

CfprApFabricPathEpLocale ::= TEXTUAL-CONVENTION
    STATUS        current
    DESCRIPTION
        ""
    SYNTAX        BITS
    {
        server(0),
        chassis(1),
        internal(2),
        external(3)
    }

CfprApFabricPcConfigStatus ::= TEXTUAL-CONVENTION
    STATUS        current
    DESCRIPTION
        ""
    SYNTAX        INTEGER
    {
        applied(1),
        incompatibleSpeed(2)
    }

CfprApFabricPktCaptureAppSlotId ::= TEXTUAL-CONVENTION
    STATUS        current
    DESCRIPTION
        ""
    SYNTAX        Gauge32 (1..3)

CfprApFabricPktCaptureAppendFlag ::= TEXTUAL-CONVENTION
    STATUS        current
    DESCRIPTION
        ""
    SYNTAX        INTEGER
    {
        append(1),
        overwrite(2)
    }

CfprApFabricPoolMemberConfigIssues ::= TEXTUAL-CONVENTION
    STATUS        current
    DESCRIPTION
        ""
    SYNTAX        BITS
    {
        namedVlanUnresolved(0)
    }

CfprApFabricPort ::= TEXTUAL-CONVENTION
    STATUS        current
    DESCRIPTION
        ""
    SYNTAX        Gauge32 (0..65535)

CfprApFabricQosPrio ::= TEXTUAL-CONVENTION
    STATUS        current
    DESCRIPTION
        ""
    SYNTAX        INTEGER
    {
        low(0),
        high(1)
    }

CfprApFabricQuerierType ::= TEXTUAL-CONVENTION
    STATUS        current
    DESCRIPTION
        ""
    SYNTAX        INTEGER
    {
        enabled(0),
        disabled(1)
    }

CfprApFabricReqIssues ::= TEXTUAL-CONVENTION
    STATUS        current
    DESCRIPTION
        ""
    SYNTAX        BITS
    {
        permitUnresolved(0)
    }

CfprApFabricSSAPortType ::= TEXTUAL-CONVENTION
    STATUS        current
    DESCRIPTION
        ""
    SYNTAX        INTEGER
    {
        data(0),
        mgmt(1),
        cluster(2),
        firepowerEventing(3)
    }

CfprApFabricSanType ::= TEXTUAL-CONVENTION
    STATUS        current
    DESCRIPTION
        ""
    SYNTAX        BITS
    {
        lan(0),
        san(1),
        ipc(2)
    }

CfprApFabricSanCloudFsmCurrentFsm ::= TEXTUAL-CONVENTION
    STATUS        current
    DESCRIPTION
        ""
    SYNTAX        INTEGER
    {
        nop(0),
        switchMode(452)
    }

CfprApFabricSanCloudFsmStageName ::= TEXTUAL-CONVENTION
    STATUS        current
    DESCRIPTION
        ""
    SYNTAX        INTEGER
    {
        nop(0),
        switchModeBegin(452),
        switchModeSwConfigPeer(453),
        switchModeSwConfigLocal(454),
        switchModeFail(608),
        switchModeSuccess(609)
    }

CfprApFabricSanCloudFsmTaskItem ::= TEXTUAL-CONVENTION
    STATUS        current
    DESCRIPTION
        ""
    SYNTAX        INTEGER
    {
        nop(0),
        switchMode(452)
    }

CfprApFabricSanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricSanEpType ::= TEXTUAL-CONVENTION
    STATUS        current
    DESCRIPTION
        ""
    SYNTAX        BITS
    {
        lan(0),
        san(1),
        ipc(2)
    }

CfprApFabricSanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricSanPcType ::= TEXTUAL-CONVENTION
    STATUS        current
    DESCRIPTION
        ""
    SYNTAX        BITS
    {
        lan(0),
        san(1),
        ipc(2)
    }

CfprApFabricSlotAdminState ::= TEXTUAL-CONVENTION
    STATUS        current
    DESCRIPTION
        ""
    SYNTAX        INTEGER
    {
        acknowledged(1),
        reacknowledge(3)
    }

CfprApFabricSnoopingType ::= TEXTUAL-CONVENTION
    STATUS        current
    DESCRIPTION
        ""
    SYNTAX        INTEGER
    {
        enabled(0),
        disabled(1)
    }

CfprApFabricSpannedCluster ::= TEXTUAL-CONVENTION
    STATUS        current
    DESCRIPTION
        ""
    SYNTAX        INTEGER
    {
        enabled(1),
        disabled(2)
    }

CfprApFabricSspEthMonAppendFlag ::= TEXTUAL-CONVENTION
    STATUS        current
    DESCRIPTION
        ""
    SYNTAX        INTEGER
    {
        append(1),
        overwrite(2)
    }

CfprApFabricSspMonAdminState ::= TEXTUAL-CONVENTION
    STATUS        current
    DESCRIPTION
        ""
    SYNTAX        INTEGER
    {
        enabled(1),
        disabled(2)
    }

CfprApFabricSspMonDelPcap ::= TEXTUAL-CONVENTION
    STATUS        current
    DESCRIPTION
        ""
    SYNTAX        INTEGER
    {
        enabled(1),
        disabled(2)
    }

CfprApFabricSspMonOperState ::= TEXTUAL-CONVENTION
    STATUS        current
    DESCRIPTION
        ""
    SYNTAX        INTEGER
    {
        unknown(0),
        up(1),
        down(2),
        error(3)
    }

CfprApFabricSspMonOperStateReason ::= TEXTUAL-CONVENTION
    STATUS        current
    DESCRIPTION
        ""
    SYNTAX        INTEGER
    {
        active(0),
        noHardwareResource(1),
        noOperationalSrcDst(2),
        genericError(3),
        noSourcesConfigured(4),
        sessionAdminShut(5),
        directoryError(8),
        unknown(12),
        fileError(16),
        memoryOvershoot(32),
        pipeError(64),
        linkError(128)
    }

CfprApFabricStatus ::= TEXTUAL-CONVENTION
    STATUS        current
    DESCRIPTION
        ""
    SYNTAX        INTEGER
    {
        modified(0),
        created(1),
        deleted(2),
        intentDeletion(3)
    }

CfprApFabricSubGroupAggrPortId ::= TEXTUAL-CONVENTION
    STATUS        current
    DESCRIPTION
        ""
    SYNTAX        Gauge32 (1..48)

CfprApFabricSubGroupConfigState ::= TEXTUAL-CONVENTION
    STATUS        current
    DESCRIPTION
        ""
    SYNTAX        INTEGER
    {
        enabled(1),
        disabled(2)
    }

CfprApFabricSubGroupSlotId ::= TEXTUAL-CONVENTION
    STATUS        current
    DESCRIPTION
        ""
    SYNTAX        Gauge32 (1..4)

CfprApFabricSwChEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricSwChEpType ::= TEXTUAL-CONVENTION
    STATUS        current
    DESCRIPTION
        ""
    SYNTAX        BITS
    {
        lan(0),
        san(1),
        ipc(2)
    }

CfprApFabricSwChPhEpAdminState ::= TEXTUAL-CONVENTION
    STATUS        current
    DESCRIPTION
        ""
    SYNTAX        INTEGER
    {
        enabled(1),
        disabled(2),
        remove(3)
    }

CfprApFabricSwSrvEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricSwSrvEpType ::= TEXTUAL-CONVENTION
    STATUS        current
    DESCRIPTION
        ""
    SYNTAX        BITS
    {
        lan(0),
        san(1),
        ipc(2)
    }

CfprApFabricSwSrvPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricSwSrvPcType ::= TEXTUAL-CONVENTION
    STATUS        current
    DESCRIPTION
        ""
    SYNTAX        BITS
    {
        lan(0),
        san(1),
        ipc(2)
    }

CfprApFabricSwSubGroupAggrPortId ::= TEXTUAL-CONVENTION
    STATUS        current
    DESCRIPTION
        ""
    SYNTAX        Gauge32 (1..48)

CfprApFabricSwSubGroupConfigState ::= TEXTUAL-CONVENTION
    STATUS        current
    DESCRIPTION
        ""
    SYNTAX        INTEGER
    {
        enabled(1),
        disabled(2)
    }

CfprApFabricSwSubGroupSlotId ::= TEXTUAL-CONVENTION
    STATUS        current
    DESCRIPTION
        ""
    SYNTAX        Gauge32 (1..4)

CfprApFabricSwitchingMode ::= TEXTUAL-CONVENTION
    STATUS        current
    DESCRIPTION
        ""
    SYNTAX        INTEGER
    {
        endHost(0),
        switch(1),
        securityNode(2)
    }

CfprApFabricTargetEpType ::= TEXTUAL-CONVENTION
    STATUS        current
    DESCRIPTION
        ""
    SYNTAX        BITS
    {
        lan(0),
        san(1),
        ipc(2)
    }

CfprApFabricTargetStatus ::= TEXTUAL-CONVENTION
    STATUS        current
    DESCRIPTION
        ""
    SYNTAX        INTEGER
    {
        valid(0),
        invalid(1)
    }

CfprApFabricTrafficDirection ::= TEXTUAL-CONVENTION
    STATUS        current
    DESCRIPTION
        ""
    SYNTAX        INTEGER
    {
        rx(1),
        tx(2),
        both(3)
    }

CfprApFabricUdldLinkPolicyAdminState ::= TEXTUAL-CONVENTION
    STATUS        current
    DESCRIPTION
        ""
    SYNTAX        INTEGER
    {
        enabled(1),
        disabled(2)
    }

CfprApFabricUdldLinkPolicyMode ::= TEXTUAL-CONVENTION
    STATUS        current
    DESCRIPTION
        ""
    SYNTAX        INTEGER
    {
        normal(0),
        aggressive(1)
    }

CfprApFabricUdldOperState ::= TEXTUAL-CONVENTION
    STATUS        current
    DESCRIPTION
        ""
    SYNTAX        INTEGER
    {
        unknown(0),
        unidirectional(1),
        bidirectional(2),
        txRxLoop(3),
        mismatch(4),
        echoEmpty(5),
        adminDisabled(6)
    }

CfprApFabricVConInstType ::= TEXTUAL-CONVENTION
    STATUS        current
    DESCRIPTION
        ""
    SYNTAX        INTEGER
    {
        auto(1),
        manual(2),
        policy(3)
    }

CfprApFabricVConMappingScheme ::= TEXTUAL-CONVENTION
    STATUS        current
    DESCRIPTION
        ""
    SYNTAX        INTEGER
    {
        roundRobin(2),
        linearOrdered(3),
        roundRobinToLinearOrdered(4),
        linearOrderedToRoundRobin(5)
    }

CfprApFabricVConPlacementPref ::= TEXTUAL-CONVENTION
    STATUS        current
    DESCRIPTION
        ""
    SYNTAX        INTEGER
    {
        physical(1),
        auto(2)
    }

CfprApFabricVConSelectPref ::= TEXTUAL-CONVENTION
    STATUS        current
    DESCRIPTION
        ""
    SYNTAX        INTEGER
    {
        assignedOnly(1),
        unassignedOnly(2),
        dynamicOnly(4),
        excludeUsnic(7),
        usnicOnly(8),
        excludeDynamic(11),
        excludeUnassigned(13),
        all(15)
    }

CfprApFabricVConSharePref ::= TEXTUAL-CONVENTION
    STATUS        current
    DESCRIPTION
        ""
    SYNTAX        INTEGER
    {
        exclusiveOnly(1),
        exclusivePreferred(2),
        sameTransport(3),
        differentTransport(4),
        shared(5)
    }

CfprApFabricVConTransportPref ::= TEXTUAL-CONVENTION
    STATUS        current
    DESCRIPTION
        ""
    SYNTAX        BITS
    {
        fc(0),
        ethernet(1)
    }

CfprApFabricVlanSwitchId ::= TEXTUAL-CONVENTION
    STATUS        current
    DESCRIPTION
        ""
    SYNTAX        INTEGER
    {
        none(0),
        a(1),
        b(2),
        dual(3)
    }

CfprApFabricVlanAssocPrimaryVlanState ::= TEXTUAL-CONVENTION
    STATUS        current
    DESCRIPTION
        ""
    SYNTAX        INTEGER
    {
        ok(1),
        isEmpty(2),
        doesNotExists(3),
        isNotPrimaryType(4),
        isInErrorState(5)
    }

CfprApFabricVlanCompType ::= TEXTUAL-CONVENTION
    STATUS        current
    DESCRIPTION
        ""
    SYNTAX        INTEGER
    {
        included(1),
        excluded(2)
    }

CfprApFabricVlanConfigIssues ::= TEXTUAL-CONVENTION
    STATUS        current
    DESCRIPTION
        ""
    SYNTAX        BITS
    {
        conflictingVlanAccess(0),
        unsupportedMulticastPolicy(1)
    }

CfprApFabricVlanOperState ::= TEXTUAL-CONVENTION
    STATUS        current
    DESCRIPTION
        ""
    SYNTAX        INTEGER
    {
        ok(1),
        errorMisconfigured(2)
    }

CfprApFabricVlanOverlapState ::= TEXTUAL-CONVENTION
    STATUS        current
    DESCRIPTION
        ""
    SYNTAX        INTEGER
    {
        notActive(0),
        ok(1),
        sharingTypeMismatch(2),
        primaryIdMismatch(3)
    }

CfprApFabricVlanSharingType ::= TEXTUAL-CONVENTION
    STATUS        current
    DESCRIPTION
        ""
    SYNTAX        INTEGER
    {
        none(0),
        primary(1),
        isolated(2),
        community(3)
    }

CfprApFabricVnetEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApFabricVnetEpLocale ::= TEXTUAL-CONVENTION
    STATUS        current
    DESCRIPTION
        ""
    SYNTAX        BITS
    {
        server(0),
        chassis(1),
        internal(2),
        external(3)
    }

CfprApFabricVnetEpPolicyOwner ::= TEXTUAL-CONVENTION
    STATUS        current
    DESCRIPTION
        ""
    SYNTAX        INTEGER
    {
        local(0),
        policy(1),
        pendingPolicy(2)
    }

CfprApFabricVnetEpSyncEpFsmCurrentFsm ::= TEXTUAL-CONVENTION
    STATUS        current
    DESCRIPTION
        ""
    SYNTAX        INTEGER
    {
        nop(0),
        pushVnetEpDeletion(447)
    }

CfprApFabricVnetEpSyncEpFsmStageName ::= TEXTUAL-CONVENTION
    STATUS        current
    DESCRIPTION
        ""
    SYNTAX        INTEGER
    {
        nop(0),
        pushVnetEpDeletionBegin(447),
        pushVnetEpDeletionSync(448),
        pushVnetEpDeletionFail(610),
        pushVnetEpDeletionSuccess(611)
    }

CfprApFabricVnetEpSyncEpFsmTaskItem ::= TEXTUAL-CONVENTION
    STATUS        current
    DESCRIPTION
        ""
    SYNTAX        INTEGER
    {
        nop(0),
        pushVnetEpDeletion(447)
    }

CfprApFabricVsanSwitchId ::= TEXTUAL-CONVENTION
    STATUS        current
    DESCRIPTION
        ""
    SYNTAX        INTEGER
    {
        none(0),
        a(1),
        b(2),
        dual(3)
    }

CfprApFabricVsanOperState ::= TEXTUAL-CONVENTION
    STATUS        current
    DESCRIPTION
        ""
    SYNTAX        INTEGER
    {
        ok(1),
        errorMisconfigured(2),
        errorReserved(3)
    }

CfprApFabricWarnings ::= TEXTUAL-CONVENTION
    STATUS        current
    DESCRIPTION
        ""
    SYNTAX        BITS
    {
        fcZoningEnabled(0),
        configurationError(1)
    }

CfprApFabricZoningState ::= TEXTUAL-CONVENTION
    STATUS        current
    DESCRIPTION
        ""
    SYNTAX        INTEGER
    {
        disabled(0),
        enabled(1)
    }

CfprApFabricRecoveryAction ::= TEXTUAL-CONVENTION
    STATUS        current
    DESCRIPTION
        ""
    SYNTAX        INTEGER
    {
        none(0),
        reset(1)
    }

CfprApFaultBasePolicyClearAction ::= TEXTUAL-CONVENTION
    STATUS        current
    DESCRIPTION
        ""
    SYNTAX        INTEGER
    {
        retain(0),
        delete(1)
    }

CfprApFaultBasePolicySoakingSeverity ::= TEXTUAL-CONVENTION
    STATUS        current
    DESCRIPTION
        ""
    SYNTAX        INTEGER
    {
        info(1),
        condition(2),
        warning(3)
    }

CfprApFcErrStatsThresholded ::= TEXTUAL-CONVENTION
    STATUS        current
    DESCRIPTION
        ""
    SYNTAX        BITS
    {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CfprApFcErrStatsHistThresholded ::= TEXTUAL-CONVENTION
    STATUS        current
    DESCRIPTION
        ""
    SYNTAX        BITS
    {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CfprApFcPIoFsmCurrentFsm ::= TEXTUAL-CONVENTION
    STATUS        current
    DESCRIPTION
        ""
    SYNTAX        INTEGER
    {
        nop(0),
        inCompatSfpPresence(235),
        inCompatSfpReplaced(237)
    }

CfprApFcPIoFsmStageName ::= TEXTUAL-CONVENTION
    STATUS        current
    DESCRIPTION
        ""
    SYNTAX        INTEGER
    {
        nop(0),
        inCompatSfpPresenceBegin(235),
        inCompatSfpPresenceShutdown(236),
        inCompatSfpReplacedBegin(237),
        inCompatSfpReplacedEnablePort(238),
        inCompatSfpPresenceFail(732),
        inCompatSfpPresenceSuccess(733),
        inCompatSfpReplacedFail(734),
        inCompatSfpReplacedSuccess(735)
    }

CfprApFcStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CfprApFcStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CfprApFcpoolBootTargetType ::= TEXTUAL-CONVENTION
    STATUS        current
    DESCRIPTION
        ""
    SYNTAX        INTEGER
    {
        primary(0),
        secondary(1)
    }

CfprApFcpoolInitiatorPurpose ::= TEXTUAL-CONVENTION
    STATUS        current
    DESCRIPTION
        ""
    SYNTAX        INTEGER
    {
        portWwn(0),
        nodeWwn(1),
        derived(2)
    }

CfprApFcpoolInitiatorEpPurpose ::= TEXTUAL-CONVENTION
    STATUS        current
    DESCRIPTION
        ""
    SYNTAX        INTEGER
    {
        portWwn(0),
        nodeWwn(1)
    }

CfprApFcpoolInitiatorsAssignmentOrder ::= TEXTUAL-CONVENTION
    STATUS        current
    DESCRIPTION
        ""
    SYNTAX        INTEGER
    {
        default(0),
        sequential(1)
    }

CfprApFcpoolInitiatorsMaxPortsPerNode ::= TEXTUAL-CONVENTION
    STATUS        current
    DESCRIPTION
        ""
    SYNTAX        INTEGER
    {
        upto3(3),
        upto7(7),
        upto15(15),
        upto31(31),
        upto63(63)
    }

CfprApFcpoolInitiatorsPurpose ::= TEXTUAL-CONVENTION
    STATUS        current
    DESCRIPTION
        ""
    SYNTAX        INTEGER
    {
        nodeAndPortWwnAssignment(0),
        portWwnAssignment(1),
        nodeWwnAssignment(2)
    }

CfprApFeatureSupportabilityType ::= TEXTUAL-CONVENTION
    STATUS        current
    DESCRIPTION
        ""
    SYNTAX        INTEGER
    {
        supported(0),
        notSupported(1),
        deprecated(2)
    }

CfprApFirmwareAdminState ::= TEXTUAL-CONVENTION
    STATUS        current
    DESCRIPTION
        ""
    SYNTAX        INTEGER
    {
        active(0),
        deleted(1)
    }

CfprApFirmwareAutoSyncConfigIssue ::= TEXTUAL-CONVENTION
    STATUS        current
    DESCRIPTION
        ""
    SYNTAX        INTEGER
    {
        noIssues(0),
        defaultPackageMissing(1),
        versionsEmptyInDefaultPackage(2)
    }

CfprApFirmwareAutoSyncState ::= TEXTUAL-CONVENTION
    STATUS        current
    DESCRIPTION
        ""
    SYNTAX        INTEGER
    {
        autoAcknowledge(0),
        userAcknowledge(1),
        noActions(2)
    }

CfprApFirmwareBootUnitImage ::= TEXTUAL-CONVENTION
    STATUS        current
    DESCRIPTION
        ""
    SYNTAX        INTEGER
    {
        running(0),
        backup(1)
    }

CfprApFirmwareBootUnitMode ::= TEXTUAL-CONVENTION
    STATUS        current
    DESCRIPTION
        ""
    SYNTAX        INTEGER
    {
        install(0),
        upgrade(1)
    }

CfprApFirmwareCatalogPackConfigState ::= TEXTUAL-CONVENTION
    STATUS        current
    DESCRIPTION
        ""
    SYNTAX        INTEGER
    {
        ok(0),
        notApplied(1),
        failed(2)
    }

CfprApFirmwareCompleteness ::= TEXTUAL-CONVENTION
    STATUS        current
    DESCRIPTION
        ""
    SYNTAX        INTEGER
    {
        partial(0),
        complete(1)
    }

CfprApFirmwareComponentType ::= TEXTUAL-CONVENTION
    STATUS        current
    DESCRIPTION
        ""
    SYNTAX        BITS
    {
        kernel(0),
        system(1),
        combined(2),
        bootLoader(3)
    }

CfprApFirmwareDependencyRelationship ::= TEXTUAL-CONVENTION
    STATUS        current
    DESCRIPTION
        ""
    SYNTAX        INTEGER
    {
        special(0),
        ancestor(1),
        descendent(2)
    }

CfprApFirmwareDependencyScope ::= TEXTUAL-CONVENTION
    STATUS        current
    DESCRIPTION
        ""
    SYNTAX        INTEGER
    {
        unknown(0),
        blade(1),
        chassis(2),
        system(4),
        switch(8),
        global(16)
    }

CfprApFirmwareDependencySensitivity ::= TEXTUAL-CONVENTION
    STATUS        current
    DESCRIPTION
        ""
    SYNTAX        INTEGER
    {
        global(0),
        fabric(1),
        path(2)
    }

CfprApFirmwareDistributableFsmCurrentFsm ::= TEXTUAL-CONVENTION
    STATUS        current
    DESCRIPTION
        ""
    SYNTAX        INTEGER
    {
        nop(0),
        delete(14)
    }

CfprApFirmwareDistributableFsmStageName ::= TEXTUAL-CONVENTION
    STATUS        current
    DESCRIPTION
        ""
    SYNTAX        INTEGER
    {
        nop(0),
        deleteBegin(14),
        deleteLocal(15),
        deleteRemote(16),
        deleteFail(612),
        deleteSuccess(613)
    }

CfprApFirmwareDistributableFsmTaskItem ::= TEXTUAL-CONVENTION
    STATUS        current
    DESCRIPTION
        ""
    SYNTAX        INTEGER
    {
        nop(0),
        delete(14)
    }

CfprApFirmwareDistributableType ::= TEXTUAL-CONVENTION
    STATUS        current
    DESCRIPTION
        ""
    SYNTAX        INTEGER
    {
        unknown(0),
        image(1),
        fullBundle(2),
        infrastructureBundle(3),
        bSeriesBundle(4),
        cSeriesBundle(5),
        catalog(6),
        platformBundle(7),
        firmwareFpr9kBundle(8),
        firmwareFpr4kBundle(9),
        appBundle(10)
    }

CfprApFirmwareDownloadActivity ::= TEXTUAL-CONVENTION
    STATUS        current
    DESCRIPTION
        ""
    SYNTAX        INTEGER
    {
        restart(0),
        idle(1)
    }

CfprApFirmwareDownloaderFsmCurrentFsm ::= TEXTUAL-CONVENTION
    STATUS        current
    DESCRIPTION
        ""
    SYNTAX        INTEGER
    {
        nop(0),
        download(6)
    }

CfprApFirmwareDownloaderFsmStageName ::= TEXTUAL-CONVENTION
    STATUS        current
    DESCRIPTION
        ""
    SYNTAX        INTEGER
    {
        nop(0),
        downloadBegin(6),
        downloadLocal(7),
        downloadUnpackLocal(8),
        downloadDeleteLocal(9),
        downloadCopyRemote(10),
        downloadFail(614),
        downloadSuccess(615)
    }

CfprApFirmwareDownloaderFsmTaskItem ::= TEXTUAL-CONVENTION
    STATUS        current
    DESCRIPTION
        ""
    SYNTAX        INTEGER
    {
        nop(0),
        download(6)
    }

CfprApFirmwareEquipmentType ::= TEXTUAL-CONVENTION
    STATUS        current
    DESCRIPTION
        ""
    SYNTAX        INTEGER
    {
        unknown(0),
        system(1),
        switch(2),
        iocard(3),
        server(4),
        cimc(5),
        adaptor(6),
        storageController(7),
        boardController(8),
        bios(9),
        serviceProfile(10),
        graphicsCard(11)
    }

CfprApFirmwareFirmwareState ::= TEXTUAL-CONVENTION
    STATUS        current
    DESCRIPTION
        ""
    SYNTAX        BITS
    {
        cimcFirmwareMismatch(0),
        pldFirmwareMismatch(1)
    }

CfprApFirmwareFwState ::= TEXTUAL-CONVENTION
    STATUS        current
    DESCRIPTION
        ""
    SYNTAX        INTEGER
    {
        unknown(0),
        sameRelease(1),
        compatible(2),
        incompatible(3),
        multipleReleases(4)
    }

CfprApFirmwareFwUpgradeState ::= TEXTUAL-CONVENTION
    STATUS        current
    DESCRIPTION
        ""
    SYNTAX        INTEGER
    {
        ready(0),
        inProgress(1),
        upgrading(2),
        updatingImageVersion(3),
        updatingPackageVersion(4),
        failed(5),
        failedUpgrade(6)
    }

CfprApFirmwareHostPackConfigQualifier ::= TEXTUAL-CONVENTION
    STATUS        current
    DESCRIPTION
        ""
    SYNTAX        BITS
    {
        biosImageNotSelected(0)
    }

CfprApFirmwareImageDeleted ::= TEXTUAL-CONVENTION
    STATUS        current
    DESCRIPTION
        ""
    SYNTAX        BITS
    {
        a(0),
        b(1)
    }

CfprApFirmwareImageError ::= TEXTUAL-CONVENTION
    STATUS        current
    DESCRIPTION
        ""
    SYNTAX        INTEGER
    {
        none(0),
        checksumFailure(1),
        filesystemError(2),
        mgmtConnectError(3),
        bootConfMissing(4),
        crcFailure(5),
        unknownError(6),
        rebuilding(7)
    }

CfprApFirmwareImageFsmCurrentFsm ::= TEXTUAL-CONVENTION
    STATUS        current
    DESCRIPTION
        ""
    SYNTAX        INTEGER
    {
        nop(0),
        delete(11)
    }

CfprApFirmwareImageFsmStageName ::= TEXTUAL-CONVENTION
    STATUS        current
    DESCRIPTION
        ""
    SYNTAX        INTEGER
    {
        nop(0),
        deleteBegin(11),
        deleteLocal(12),
        deleteRemote(13),
        deleteFail(616),
        deleteSuccess(617)
    }

CfprApFirmwareImageFsmTaskItem ::= TEXTUAL-CONVENTION
    STATUS        current
    DESCRIPTION
        ""
    SYNTAX        INTEGER
    {
        nop(0),
        delete(11)
    }

CfprApFirmwareImagePresence ::= TEXTUAL-CONVENTION
    STATUS        current
    DESCRIPTION
        ""
    SYNTAX        BITS
    {
        a(0),
        b(1)
    }

CfprApFirmwareImageState ::= TEXTUAL-CONVENTION
    STATUS        current
    DESCRIPTION
        ""
    SYNTAX        INTEGER
    {
        ready(0),
        scheduled(1),
        updating(2),
        activating(3),
        failed(4),
        setStartup(5),
        rebooting(6),
        pendingNextBoot(7),
        throttled(8),
        upgrading(9),
        autoUpdating(10),
        autoActivating(11),
        pendingPowerCycle(12),
        badImage(13),
        rebuilding(14)
    }

CfprApFirmwareImpactType ::= TEXTUAL-CONVENTION
    STATUS        current
    DESCRIPTION
        ""
    SYNTAX        INTEGER
    {
        activate(0),
        noimpact(1),
        reset(2),
        update(3)
    }

CfprApFirmwareInfraPackFsmCurrentFsm ::= TEXTUAL-CONVENTION
    STATUS        current
    DESCRIPTION
        ""
    SYNTAX        INTEGER
    {
        nop(0),
        infraVersion(828)
    }

CfprApFirmwareInfraPackFsmStageName ::= TEXTUAL-CONVENTION
    STATUS        current
    DESCRIPTION
        ""
    SYNTAX        INTEGER
    {
        nop(0),
        infraVersionBegin(828),
        infraVersionWaitForReady(829),
        infraVersionRestore(830),
        infraVersionFail(831),
        infraVersionSuccess(832)
    }

CfprApFirmwareInfraPackFsmTaskFlags ::= TEXTUAL-CONVENTION
    STATUS        current
    DESCRIPTION
        ""
    SYNTAX        BITS
    {
        samDmeFirmwareInfraPackInfraVersionInitRestore(33)
    }

CfprApFirmwareInfraPackFsmTaskItem ::= TEXTUAL-CONVENTION
    STATUS        current
    DESCRIPTION
        ""
    SYNTAX        INTEGER
    {
        nop(0),
        infraVersion(828)
    }

CfprApFirmwareInstallState ::= TEXTUAL-CONVENTION
    STATUS        current
    DESCRIPTION
        ""
    SYNTAX        INTEGER
    {
        ready(0),
        scheduled(1),
        inProgress(2),
        failed(3),
        pendingUserAck(4),
        startPendingExtPermission(5)
    }

CfprApFirmwareItemType ::= TEXTUAL-CONVENTION
    STATUS        current
    DESCRIPTION
        ""
    SYNTAX        INTEGER
    {
        unspecified(0),
        switchKernel(1),
        switchSoftware(2),
        system(3),
        bladeController(4),
        iocard(5),
        bladeBios(6),
        adaptor(7),
        storageController(8),
        hostNic(9),
        hostHba(10),
        hostHbaOptionrom(11),
        hostNicOptionrom(12),
        boardController(13),
        localDisk(14),
        flexflashController(20),
        bladeSspOsController(22),
        graphicsCard(25)
    }

CfprApFirmwarePackMode ::= TEXTUAL-CONVENTION
    STATUS        current
    DESCRIPTION
        ""
    SYNTAX        INTEGER
    {
        staged(0),
        oneShot(1)
    }

CfprApFirmwarePackItemPresence ::= TEXTUAL-CONVENTION
    STATUS        current
    DESCRIPTION
        ""
    SYNTAX        INTEGER
    {
        unknown(0),
        missing(1),
        present(2)
    }

CfprApFirmwarePlatformPackFsmCurrentFsm ::= TEXTUAL-CONVENTION
    STATUS        current
    DESCRIPTION
        ""
    SYNTAX        INTEGER
    {
        nop(0),
        platformVersion(34)
    }

CfprApFirmwarePlatformPackFsmStageName ::= TEXTUAL-CONVENTION
    STATUS        current
    DESCRIPTION
        ""
    SYNTAX        INTEGER
    {
        nop(0),
        platformVersionBegin(34),
        platformVersionWaitForReady(35),
        platformVersionRestore(36),
        platformVersionFail(618),
        platformVersionSuccess(619)
    }

CfprApFirmwarePlatformPackFsmTaskFlags ::= TEXTUAL-CONVENTION
    STATUS        current
    DESCRIPTION
        ""
    SYNTAX        BITS
    {
        samDmeFirmwarePlatformPackPlatformVersionInitRestore(3)
    }

CfprApFirmwarePlatformPackFsmTaskItem ::= TEXTUAL-CONVENTION
    STATUS        current
    DESCRIPTION
        ""
    SYNTAX        INTEGER
    {
        nop(0),
        platformVersion(34)
    }

CfprApFirmwarePlatformType ::= TEXTUAL-CONVENTION
    STATUS        current
    DESCRIPTION
        ""
    SYNTAX        INTEGER
    {
        ucs(0),
        ucsMini(1),
        sspBakerstreet(2),
        fpr2100(3)
    }

CfprApFirmwareRunningDeployment ::= TEXTUAL-CONVENTION
    STATUS        current
    DESCRIPTION
        ""
    SYNTAX        INTEGER
    {
        unspecified(0),
        kernel(1),
        bootLoader(2),
        system(3)
    }

CfprApFirmwareSupFirmwareFsmCurrentFsm ::= TEXTUAL-CONVENTION
    STATUS        current
    DESCRIPTION
        ""
    SYNTAX        INTEGER
    {
        nop(0),
        deploy(56)
    }

CfprApFirmwareSupFirmwareFsmStageName ::= TEXTUAL-CONVENTION
    STATUS        current
    DESCRIPTION
        ""
    SYNTAX        INTEGER
    {
        nop(0),
        deployBegin(56),
        deployWaitForDeploy(57),
        deployValidateFirmwarePack(58),
        deployDebundlePort(59),
        deployPollDebundlePort(60),
        deployActivateFirmwarePack(61),
        deployPollActivateOfFirmwarePack(62),
        deployUpdateImageVersion(63),
        deployWaitForFirmwareVersionUpdate(64),
        deployUpdatePackageVersion(65),
        deployCompleteFirmwareUpgrade(66),
        deployFail(620),
        deploySuccess(621)
    }

CfprApFirmwareSupFirmwareFsmTaskFlags ::= TEXTUAL-CONVENTION
    STATUS        current
    DESCRIPTION
        ""
    SYNTAX        BITS
    {
        samDmeFirmwareSupFirmwareDeployApplySupfw(10)
    }

CfprApFirmwareSupFirmwareFsmTaskItem ::= TEXTUAL-CONVENTION
    STATUS        current
    DESCRIPTION
        ""
    SYNTAX        INTEGER
    {
        nop(0),
        deploy(56)
    }

CfprApFirmwareSystemFsmCurrentFsm ::= TEXTUAL-CONVENTION
    STATUS        current
    DESCRIPTION
        ""
    SYNTAX        INTEGER
    {
        nop(0),
        deploy(37),
        applyCatalogPack(67)
    }

CfprApFirmwareSystemFsmStageName ::= TEXTUAL-CONVENTION
    STATUS        current
    DESCRIPTION
        ""
    SYNTAX        INTEGER
    {
        nop(0),
        deployBegin(37),
        deployWaitForDeploy(38),
        deployValidateApplicationPack(39),
        deployDeleteCurrentApplication(40),
        deployPollDeleteCurrentApplicationStatus(41),
        deploySetStartupServiceManagerVersion(42),
        deployPollStartupServiceManagerStatus(43),
        deployActivateNpuImage(44),
        deployPollNpuActivationStatus(45),
        deployActivateSystemImage(46),
        deployActivateFirmwareImage(47),
        deployRebootSystemForImageUpgrade(48),
        deployWaitForSystemReady(49),
        deployPollSystemActivationStatus(50),
        deployActivateManagerImage(51),
        deployPollManagerActivationStatus(52),
        deployActivateApplicationImage(53),
        deployPollApplicationActivationStatus(54),
        deployCompleteFirmwareUpgrade(55),
        applyCatalogPackBegin(67),
        applyCatalogPackResolveDistributableNames(68),
        applyCatalogPackResolveDistributable(69),
        applyCatalogPackResolveImages(70),
        applyCatalogPackActivateCatalog(71),
        applyCatalogPackFail(622),
        applyCatalogPackSuccess(623),
        deployFail(624),
        deploySuccess(625),
        deployCheckFirmwareUpgradeStatus(834)
    }

CfprApFirmwareSystemFsmTaskFlags ::= TEXTUAL-CONVENTION
    STATUS        current
    DESCRIPTION
        ""
    SYNTAX        BITS
    {
        samDmeFirmwareSystemDeployApplyInfra(4),
        samDmeFirmwareSystemDeployApplyApp(5),
        samDmeFirmwareSystemDeployApplyMgr(6),
        samDmeFirmwareSystemDeployApplyNpu(7),
        samDmeFirmwareSystemDeployApplySys(8),
        samDmeFirmwareSystemDeployApplyFw(9)
    }

CfprApFirmwareSystemFsmTaskItem ::= TEXTUAL-CONVENTION
    STATUS        current
    DESCRIPTION
        ""
    SYNTAX        INTEGER
    {
        nop(0),
        deploy(37),
        applyCatalogPack(67)
    }

CfprApFirmwareTransferState ::= TEXTUAL-CONVENTION
    STATUS        current
    DESCRIPTION
        ""
    SYNTAX        INTEGER
    {
        init(0),
        downloading(1),
        downloaded(2),
        failed(3)
    }

CfprApFirmwareTransport ::= TEXTUAL-CONVENTION
    STATUS        current
    DESCRIPTION
        ""
    SYNTAX        INTEGER
    {
        ftp(0),
        tftp(1),
        scp(2),
        sftp(3),
        local(4),
        usbA(5),
        usbB(6)
    }

CfprApFirmwareTriggerState ::= TEXTUAL-CONVENTION
    STATUS        current
    DESCRIPTION
        ""
    SYNTAX        INTEGER
    {
        triggered(0),
        trigger(1)
    }

CfprApFirmwareType ::= TEXTUAL-CONVENTION
    STATUS        current
    DESCRIPTION
        ""
    SYNTAX        INTEGER
    {
        unspecified(0),
        switchKernel(1),
        switchSoftware(2),
        system(3),
        bladeController(4),
        iocard(5),
        fex(6),
        adaptor(7),
        storageController(8),
        hostNic(9),
        hostHba(10),
        hostHbaOptionrom(11),
        hostNicOptionrom(12),
        boardController(13),
        localDisk(14),
        diag(15),
        catalog(16),
        mgmtExt(17),
        debugPlugIn(18),
        switch(19),
        flexflashController(20),
        bladeSspOsController(22),
        fxosCspCompatibility(23),
        fprRommon(24),
        graphicsCard(25),
        fprFirmware(26),
        fprCspapp(27)
    }

CfprApFirmwareUpdatableDeployment ::= TEXTUAL-CONVENTION
    STATUS        current
    DESCRIPTION
        ""
    SYNTAX        INTEGER
    {
        unspecified(0),
        backup(4)
    }

CfprApFirmwareUpgradeCategory ::= TEXTUAL-CONVENTION
    STATUS        current
    DESCRIPTION
        ""
    SYNTAX        INTEGER
    {
        other(0),
        dataLoad(1),
        catalog(2),
        config(3),
        serverReboot(4),
        faults(5)
    }

CfprApFirmwareUpgradeSeverity ::= TEXTUAL-CONVENTION
    STATUS        current
    DESCRIPTION
        ""
    SYNTAX        INTEGER
    {
        unknown(0),
        fatal(1),
        error(2),
        warn(3),
        info(4)
    }

CfprApFirmwareUpgradeState ::= TEXTUAL-CONVENTION
    STATUS        current
    DESCRIPTION
        ""
    SYNTAX        INTEGER
    {
        ready(0),
        validatingImages(1),
        removingApplication(2),
        updatingManagerStartup(3),
        upgradingNpu(4),
        upgradingSystem(5),
        upgradingFirmware(6),
        rebootingSystem(7),
        waitingSystemReady(8),
        checkingServiceManager(9),
        upgradingServiceManager(10),
        updatingSoftwarePackVersion(11),
        updateSoftwarePackCompleted(12),
        installingApplication(13),
        failedImageValidation(14),
        failedToRemoveApplication(15),
        failedToUpgradeNpuImage(16),
        failedToSetServiceMgrVersion(17),
        failedToUpgradeSystemImage(18),
        failedToRebootSystem(19),
        failedToUpgradeFirmware(20),
        failedToUpdatePackageVersion(21),
        failedToUpgradeServiceManager(22),
        failedToInstallApplication(23)
    }

CfprApFirmwareUpgradeStatus ::= TEXTUAL-CONVENTION
    STATUS        current
    DESCRIPTION
        ""
    SYNTAX        INTEGER
    {
        unknown(0),
        inProgress(1),
        failed(2),
        success(3),
        warnings(4),
        skipped(5)
    }

CfprApFlowctrlFlowControl ::= TEXTUAL-CONVENTION
    STATUS        current
    DESCRIPTION
        ""
    SYNTAX        INTEGER
    {
        off(0),
        on(1)
    }

CfprApFlowctrlPriorityPause ::= TEXTUAL-CONVENTION
    STATUS        current
    DESCRIPTION
        ""
    SYNTAX        INTEGER
    {
        auto(0),
        on(1)
    }

CfprApFsmCompletion ::= TEXTUAL-CONVENTION
    STATUS        current
    DESCRIPTION
        ""
    SYNTAX        INTEGER
    {
        scheduled(0),
        processing(1),
        completed(2),
        cancelled(3)
    }

CfprApFsmFlags ::= TEXTUAL-CONVENTION
    STATUS        current
    DESCRIPTION
        ""
    SYNTAX        BITS
    {
        unused(1)
    }

CfprApFsmFsmStageStatus ::= TEXTUAL-CONVENTION
    STATUS        current
    DESCRIPTION
        ""
    SYNTAX        INTEGER
    {
        fail(0),
        success(1),
        skip(2),
        pending(3),
        inProgress(4),
        throttled(5),
        nop(255)
    }

CfprApFsmLifecycle ::= TEXTUAL-CONVENTION
    STATUS        current
    DESCRIPTION
        ""
    SYNTAX        INTEGER
    {
        available(0),
        allocated(1),
        deallocated(2),
        repurposed(3)
    }

CfprApGmetaCategory ::= TEXTUAL-CONVENTION
    STATUS        current
    DESCRIPTION
        ""
    SYNTAX        INTEGER
    {
        unknown(0),
        inventory(1)
    }

CfprApGmetaHolderFsmCurrentFsm ::= TEXTUAL-CONVENTION
    STATUS        current
    DESCRIPTION
        ""
    SYNTAX        INTEGER
    {
        nop(0),
        inventory(3)
    }

CfprApGmetaHolderFsmStageName ::= TEXTUAL-CONVENTION
    STATUS        current
    DESCRIPTION
        ""
    SYNTAX        INTEGER
    {
        nop(0),
        inventoryBegin(3),
        inventoryCheckInventoryStatus(4),
        inventoryReportFullInventory(5),
        inventoryFail(626),
        inventorySuccess(627)
    }

CfprApGmetaHolderFsmTaskFlags ::= TEXTUAL-CONVENTION
    STATUS        current
    DESCRIPTION
        ""
    SYNTAX        BITS
    {
        samDmeGmetaHolderInventoryRegister(0)
    }

CfprApGmetaHolderFsmTaskItem ::= TEXTUAL-CONVENTION
    STATUS        current
    DESCRIPTION
        ""
    SYNTAX        INTEGER
    {
        nop(0),
        inventory(3)
    }

CfprApGmetaInventoryStatus ::= TEXTUAL-CONVENTION
    STATUS        current
    DESCRIPTION
        ""
    SYNTAX        INTEGER
    {
        invDisable(0),
        invEnable(1),
        invStop(2),
        invThrottled(3)
    }

CfprApGmetaPollInterval ::= TEXTUAL-CONVENTION
    STATUS        current
    DESCRIPTION
        ""
    SYNTAX        INTEGER
    {
        never(0),
        n1min(1),
        n2min(2),
        n5min(5),
        n10min(10),
        n15min(15),
        n30min(30)
    }

CfprApHostagAction ::= TEXTUAL-CONVENTION
    STATUS        current
    DESCRIPTION
        ""
    SYNTAX        INTEGER
    {
        none(0)
    }

CfprApHostagAgentType ::= TEXTUAL-CONVENTION
    STATUS        current
    DESCRIPTION
        ""
    SYNTAX        INTEGER
    {
        indeterminate(0),
        pnuosAgent(1),
        hostAgent(2)
    }

CfprApHostagEvent ::= TEXTUAL-CONVENTION
    STATUS        current
    DESCRIPTION
        ""
    SYNTAX        INTEGER
    {
        none(0)
    }

CfprApHostimgComposition ::= TEXTUAL-CONVENTION
    STATUS        current
    DESCRIPTION
        ""
    SYNTAX        INTEGER
    {
        complete(0),
        componentized(1)
    }

CfprApHostimgDistribution ::= TEXTUAL-CONVENTION
    STATUS        current
    DESCRIPTION
        ""
    SYNTAX        INTEGER
    {
        unknown(0),
        fedora(1)
    }

CfprApHostimgImgType ::= TEXTUAL-CONVENTION
    STATUS        current
    DESCRIPTION
        ""
    SYNTAX        INTEGER
    {
        unknown(0),
        esxi(1),
        kvm(2),
        xen(3),
        linux(4),
        windows(5),
        gpxeScript(6)
    }

CfprApHostimgType ::= TEXTUAL-CONVENTION
    STATUS        current
    DESCRIPTION
        ""
    SYNTAX        INTEGER
    {
        complete(0),
        kernel(1),
        fileSystem(2),
        module(3),
        gpxeScript(4)
    }

CfprApIdentConsType ::= TEXTUAL-CONVENTION
    STATUS        current
    DESCRIPTION
        ""
    SYNTAX        INTEGER
    {
        vnic(1),
        vhba(2),
        server(3),
        chassis(4),
        vm(5),
        vmnic(6)
    }

CfprApIdentIdDefinedInIdm ::= TEXTUAL-CONVENTION
    STATUS        current
    DESCRIPTION
        ""
    SYNTAX        INTEGER
    {
        no(0),
        yes(1)
    }

CfprApIdentIdentReqIntent ::= TEXTUAL-CONVENTION
    STATUS        current
    DESCRIPTION
        ""
    SYNTAX        INTEGER
    {
        requisition(1),
        assign(2),
        unassign(3),
        addPooled(4),
        deletePooled(5),
        checkDuplicateId(6)
    }

CfprApIdentIdentRequestFsmCurrentFsm ::= TEXTUAL-CONVENTION
    STATUS        current
    DESCRIPTION
        ""
    SYNTAX        INTEGER
    {
        nop(0),
        updateIdent(72)
    }

CfprApIdentIdentRequestFsmStageName ::= TEXTUAL-CONVENTION
    STATUS        current
    DESCRIPTION
        ""
    SYNTAX        INTEGER
    {
        nop(0),
        updateIdentBegin(72),
        updateIdentExecute(73),
        updateIdentFail(628),
        updateIdentSuccess(629)
    }

CfprApIdentIdentRequestFsmTaskItem ::= TEXTUAL-CONVENTION
    STATUS        current
    DESCRIPTION
        ""
    SYNTAX        INTEGER
    {
        nop(0),
        updateIdent(72)
    }

CfprApIdentIdentType ::= TEXTUAL-CONVENTION
    STATUS        current
    DESCRIPTION
        ""
    SYNTAX        INTEGER
    {
        mac(1),
        wwnn(2),
        wwpn(3),
        uuid(4),
        vlan(5),
        ipV4(6),
        ipV6(7),
        iqn(8)
    }

CfprApIdentMetaSystemFsmCurrentFsm ::= TEXTUAL-CONVENTION
    STATUS        current
    DESCRIPTION
        ""
    SYNTAX        INTEGER
    {
        nop(0),
        sync(74),
        ucscUnivSync(77)
    }

CfprApIdentMetaSystemFsmStageName ::= TEXTUAL-CONVENTION
    STATUS        current
    DESCRIPTION
        ""
    SYNTAX        INTEGER
    {
        nop(0),
        syncBegin(74),
        syncPing(75),
        syncExecute(76),
        ucscUnivSyncBegin(77),
        ucscUnivSyncExecute(78),
        syncFail(630),
        syncSuccess(631),
        ucscUnivSyncFail(632),
        ucscUnivSyncSuccess(633)
    }

CfprApIdentMetaSystemFsmTaskItem ::= TEXTUAL-CONVENTION
    STATUS        current
    DESCRIPTION
        ""
    SYNTAX        INTEGER
    {
        nop(0),
        sync(74),
        ucscUnivSync(77)
    }

CfprApIdentRetStatus ::= TEXTUAL-CONVENTION
    STATUS        current
    DESCRIPTION
        ""
    SYNTAX        INTEGER
    {
        succeeded(1),
        assignedByOther(2),
        outOfSync(3),
        failed(4),
        synced(5)
    }

CfprApImgsecKeyType ::= TEXTUAL-CONVENTION
    STATUS        current
    DESCRIPTION
        ""
    SYNTAX        INTEGER
    {
        public(0),
        private(1),
        shared(2)
    }

CfprApInitiatorFcInitiatorEpProt ::= TEXTUAL-CONVENTION
    STATUS        current
    DESCRIPTION
        ""
    SYNTAX        INTEGER
    {
        derived(0),
        fc(1),
        iscsi(2)
    }

CfprApInitiatorGroupType ::= TEXTUAL-CONVENTION
    STATUS        current
    DESCRIPTION
        ""
    SYNTAX        INTEGER
    {
        dedicated(1),
        shared(2),
        policy(3)
    }

CfprApInitiatorIScsiInitiatorEpProt ::= TEXTUAL-CONVENTION
    STATUS        current
    DESCRIPTION
        ""
    SYNTAX        INTEGER
    {
        derived(0),
        fc(1),
        iscsi(2)
    }

CfprApInitiatorInitiatorEpPref ::= TEXTUAL-CONVENTION
    STATUS        current
    DESCRIPTION
        ""
    SYNTAX        INTEGER
    {
        preferred(0),
        alternate(1)
    }

CfprApIpIPv4DnsPref ::= TEXTUAL-CONVENTION
    STATUS        current
    DESCRIPTION
        ""
    SYNTAX        INTEGER
    {
        preferred(0),
        alternate(1)
    }

CfprApIpIpV4StaticAddrPref ::= TEXTUAL-CONVENTION
    STATUS        current
    DESCRIPTION
        ""
    SYNTAX        INTEGER
    {
        preferred(0),
        alternate(1)
    }

CfprApIpProtocol ::= TEXTUAL-CONVENTION
    STATUS        current
    DESCRIPTION
        ""
    SYNTAX        INTEGER
    {
        tcp(1),
        udp(2)
    }

CfprApIpServiceIfPref ::= TEXTUAL-CONVENTION
    STATUS        current
    DESCRIPTION
        ""
    SYNTAX        INTEGER
    {
        preferred(0),
        alternate(1)
    }

CfprApIppoolDHCPMode ::= TEXTUAL-CONVENTION
    STATUS        current
    DESCRIPTION
        ""
    SYNTAX        INTEGER
    {
        disabled(0),
        enabled(1)
    }

CfprApIppoolManagementMode ::= TEXTUAL-CONVENTION
    STATUS        current
    DESCRIPTION
        ""
    SYNTAX        INTEGER
    {
        internal(0),
        external(1)
    }

CfprApIppoolNetBIOSMode ::= TEXTUAL-CONVENTION
    STATUS        current
    DESCRIPTION
        ""
    SYNTAX        INTEGER
    {
        disabled(0),
        enabled(1)
    }

CfprApIppoolPoolAssignmentOrder ::= TEXTUAL-CONVENTION
    STATUS        current
    DESCRIPTION
        ""
    SYNTAX        INTEGER
    {
        default(0),
        sequential(1)
    }

CfprApIqnpoolBlockFrom ::= TEXTUAL-CONVENTION
    STATUS        current
    DESCRIPTION
        ""
    SYNTAX        Gauge32 (0..65535)

CfprApIqnpoolBlockTo ::= TEXTUAL-CONVENTION
    STATUS        current
    DESCRIPTION
        ""
    SYNTAX        Gauge32 (0..65535)

CfprApIqnpoolPoolAssignmentOrder ::= TEXTUAL-CONVENTION
    STATUS        current
    DESCRIPTION
        ""
    SYNTAX        INTEGER
    {
        default(0),
        sequential(1)
    }

CfprApIqnpoolTransportBlockFrom ::= TEXTUAL-CONVENTION
    STATUS        current
    DESCRIPTION
        ""
    SYNTAX        Gauge32 (0..65535)

CfprApIqnpoolTransportBlockTo ::= TEXTUAL-CONVENTION
    STATUS        current
    DESCRIPTION
        ""
    SYNTAX        Gauge32 (0..65535)

CfprApLicenseConfigOperation ::= TEXTUAL-CONVENTION
    STATUS        current
    DESCRIPTION
        ""
    SYNTAX        INTEGER
    {
        register(0),
        unregister(1),
        setdebug(2),
        cleardebug(3),
        renew(4),
        expireauth(5),
        expireeval(6),
        cadev(7),
        caprod(8)
    }

CfprApLicenseDebugFlag ::= TEXTUAL-CONVENTION
    STATUS        current
    DESCRIPTION
        ""
    SYNTAX        INTEGER
    {
        error(0),
        debug(1),
        trace(2),
        all(3)
    }

CfprApLicenseDownloadActivity ::= TEXTUAL-CONVENTION
    STATUS        current
    DESCRIPTION
        ""
    SYNTAX        INTEGER
    {
        restart(0),
        idle(1)
    }

CfprApLicenseDownloaderFsmCurrentFsm ::= TEXTUAL-CONVENTION
    STATUS        current
    DESCRIPTION
        ""
    SYNTAX        INTEGER
    {
        nop(0),
        download(140)
    }

CfprApLicenseDownloaderFsmStageName ::= TEXTUAL-CONVENTION
    STATUS        current
    DESCRIPTION
        ""
    SYNTAX        INTEGER
    {
        nop(0),
        downloadBegin(140),
        downloadLocal(141),
        downloadValidateLocal(142),
        downloadCopyRemote(143),
        downloadDeleteLocal(144),
        downloadValidateRemote(145),
        downloadDeleteRemote(146),
        downloadFail(634),
        downloadSuccess(635)
    }

CfprApLicenseDownloaderFsmTaskItem ::= TEXTUAL-CONVENTION
    STATUS        current
    DESCRIPTION
        ""
    SYNTAX        INTEGER
    {
        nop(0),
        download(140)
    }

CfprApLicenseFeatureType ::= TEXTUAL-CONVENTION
    STATUS        current
    DESCRIPTION
        ""
    SYNTAX        INTEGER
    {
        counted(0),
        boolean(1)
    }

CfprApLicenseFileFsmCurrentFsm ::= TEXTUAL-CONVENTION
    STATUS        current
    DESCRIPTION
        ""
    SYNTAX        INTEGER
    {
        nop(0),
        install(147),
        clear(150)
    }

CfprApLicenseFileFsmStageName ::= TEXTUAL-CONVENTION
    STATUS        current
    DESCRIPTION
        ""
    SYNTAX        INTEGER
    {
        nop(0),
        installBegin(147),
        installLocal(148),
        installRemote(149),
        clearBegin(150),
        clearLocal(151),
        clearRemote(152),
        clearFail(636),
        clearSuccess(637),
        installFail(638),
        installSuccess(639)
    }

CfprApLicenseFileFsmTaskItem ::= TEXTUAL-CONVENTION
    STATUS        current
    DESCRIPTION
        ""
    SYNTAX        INTEGER
    {
        nop(0),
        install(147),
        clear(150)
    }

CfprApLicenseFileState ::= TEXTUAL-CONVENTION
    STATUS        current
    DESCRIPTION
        ""
    SYNTAX        INTEGER
    {
        unknown(0),
        installPending(1),
        installing(2),
        stale(3),
        installed(4),
        installFailed(5),
        deletePending(6),
        deleting(7),
        deleted(8),
        deleteFailed(9),
        validated(10)
    }

CfprApLicenseInstanceFsmCurrentFsm ::= TEXTUAL-CONVENTION
    STATUS        current
    DESCRIPTION
        ""
    SYNTAX        INTEGER
    {
        nop(0),
        updateFlexlm(153)
    }

CfprApLicenseInstanceFsmStageName ::= TEXTUAL-CONVENTION
    STATUS        current
    DESCRIPTION
        ""
    SYNTAX        INTEGER
    {
        nop(0),
        updateFlexlmBegin(153),
        updateFlexlmLocal(154),
        updateFlexlmRemote(155),
        updateFlexlmFail(640),
        updateFlexlmSuccess(641)
    }

CfprApLicenseInstanceFsmTaskItem ::= TEXTUAL-CONVENTION
    STATUS        current
    DESCRIPTION
        ""
    SYNTAX        INTEGER
    {
        nop(0),
        updateFlexlm(153)
    }

CfprApLicensePeerStatus ::= TEXTUAL-CONVENTION
    STATUS        current
    DESCRIPTION
        ""
    SYNTAX        INTEGER
    {
        noPeer(0),
        unknown(1),
        lacks(2),
        exceeds(3),
        matching(4)
    }

CfprApLicenseScope ::= TEXTUAL-CONVENTION
    STATUS        current
    DESCRIPTION
        ""
    SYNTAX        INTEGER
    {
        a(1),
        b(2),
        server(3),
        unknown(4)
    }

CfprApLicenseSmartConfigFsmCurrentFsm ::= TEXTUAL-CONVENTION
    STATUS        current
    DESCRIPTION
        ""
    SYNTAX        INTEGER
    {
        nop(0),
        setConfig(156)
    }

CfprApLicenseSmartConfigFsmStageName ::= TEXTUAL-CONVENTION
    STATUS        current
    DESCRIPTION
        ""
    SYNTAX        INTEGER
    {
        nop(0),
        setConfigBegin(156),
        setConfigLocal(157),
        setConfigFail(642),
        setConfigSuccess(643)
    }

CfprApLicenseSmartConfigFsmTaskItem ::= TEXTUAL-CONVENTION
    STATUS        current
    DESCRIPTION
        ""
    SYNTAX        INTEGER
    {
        nop(0),
        setConfig(156)
    }

CfprApLicenseState ::= TEXTUAL-CONVENTION
    STATUS        current
    DESCRIPTION
        ""
    SYNTAX        INTEGER
    {
        unknown(0),
        licenseOk(1),
        licenseInsufficient(2),
        licenseGraceperiod(3),
        licenseExpired(4),
        notApplicable(5)
    }

CfprApLicenseTransferState ::= TEXTUAL-CONVENTION
    STATUS        current
    DESCRIPTION
        ""
    SYNTAX        INTEGER
    {
        init(0),
        downloading(1),
        downloaded(2),
        failed(3)
    }

CfprApLicenseTransport ::= TEXTUAL-CONVENTION
    STATUS        current
    DESCRIPTION
        ""
    SYNTAX        INTEGER
    {
        ftp(0),
        tftp(1),
        scp(2),
        sftp(3),
        local(4)
    }

CfprApLicenseType ::= TEXTUAL-CONVENTION
    STATUS        current
    DESCRIPTION
        ""
    SYNTAX        INTEGER
    {
        increment(0),
        upgrade(1),
        feature(2)
    }

CfprApLsAgentCapability ::= TEXTUAL-CONVENTION
    STATUS        current
    DESCRIPTION
        ""
    SYNTAX        INTEGER
    {
        l2IfConfig(1),
        l3IfConfig(2),
        hostNameConfig(4),
        stats(8),
        states(16)
    }

CfprApLsAgentMode ::= TEXTUAL-CONVENTION
    STATUS        current
    DESCRIPTION
        ""
    SYNTAX        INTEGER
    {
        noAgent(1),
        readOnly(2),
        full(4)
    }

CfprApLsApply ::= TEXTUAL-CONVENTION
    STATUS        current
    DESCRIPTION
        ""
    SYNTAX        INTEGER
    {
        onAssociation(1),
        runTime(2)
    }

CfprApLsAssignment ::= TEXTUAL-CONVENTION
    STATUS        current
    DESCRIPTION
        ""
    SYNTAX        INTEGER
    {
        unassigned(0),
        assigned(1),
        failed(2)
    }

CfprApLsAssocState ::= TEXTUAL-CONVENTION
    STATUS        current
    DESCRIPTION
        ""
    SYNTAX        INTEGER
    {
        unassociated(0),
        associating(1),
        associated(2),
        disassociating(3),
        failed(4)
    }

CfprApLsComputeBindingOperState ::= TEXTUAL-CONVENTION
    STATUS        current
    DESCRIPTION
        ""
    SYNTAX        INTEGER
    {
        unused(0),
        used(1),
        failedToApply(2)
    }

CfprApLsConfigIssues ::= TEXTUAL-CONVENTION
    STATUS        current
    DESCRIPTION
        ""
    SYNTAX        BITS
    {
        insufficientResources(0),
        vnicCapacity(1),
        vhbaCapacity(2),
        fcoeCapacity(3),
        switchVirtualIfCapacity(4),
        macAddressAssignment(5),
        wwpnAssignment(6),
        wwnnAssignment(7),
        systemUuidAssignment(8),
        bootOrderSanImagePath(9),
        bootOrderPxe(10),
        computeUndiscovered(11),
        adaptorProtectedEthCapability(12),
        adaptorFcoeCapability(13),
        incompatibleNumberOfLocalDisks(14),
        adaptorRequirement(15),
        memoryRequirement(16),
        processorRequirement(17),
        serverPositionRequirement(18),
        computeUnavailable(19),
        wwnnDerivationFromVhba(20),
        bootConfigurationInvalid(21),
        connectionPlacement(22),
        wwpnDerivationVirtualizedPort(23),
        macDerivationVirtualizedPort(24),
        qosPolicyInvalid(25),
        vlanPortCapacity(26),
        physicalRequirement(27),
        destructiveLocalDiskConfig(28),
        powerGroupRequirement(29),
        migration(30),
        incompatibleBiosImage(31),
        incompatibleDiskTypes(32),
        incompatibleRaidLevel(33),
        invalidWwn(34),
        insufficientPowerBudget(35),
        bootipPolicyInvalid(36),
        hostimgPolicyInvalid(37),
        imgsecPolicyInvalid(38),
        provsrvPolicyInvalid(39),
        incompatBiosForSriovVnics(40),
        iscsiConfig(41),
        vnicNotHaReady(42),
        missingPrimaryVlan(43),
        missingRaidKey(44),
        bootOrderIscsi(45),
        vfcVnicPvlanConflict(46),
        vifResourcesOverprovisioned(47),
        pinningVlanMismatch(48),
        vnicVlanAssignmentError(49),
        iscsiInitiatorIpAddress(50),
        storagePathConfigurationError(51),
        zoneCapacity(52),
        dynamicVfVnic(53),
        boardControllerUpdateUnsupported(54),
        vnicVconProvisioningChange(55),
        namedVlanInaccessible(56),
        pinningInvalid(57),
        nonInterruptFsmRunning(58),
        missingFirmwareImage(59),
        remotePolicy(60),
        resourceOwnershipConflict(61),
        duplicateAddressConflict(62)
    }

CfprApLsConfigState ::= TEXTUAL-CONVENTION
    STATUS        current
    DESCRIPTION
        ""
    SYNTAX        INTEGER
    {
        notApplied(0),
        applying(1),
        failedToApply(2),
        applied(3)
    }

CfprApLsConfigWarnings ::= TEXTUAL-CONVENTION
    STATUS        current
    DESCRIPTION
        ""
    SYNTAX        BITS
    {
        kvmMgmtPolicyUnsupported(0)
    }

CfprApLsFcZoneGroupSwitchId ::= TEXTUAL-CONVENTION
    STATUS        current
    DESCRIPTION
        ""
    SYNTAX        INTEGER
    {
        none(0),
        a(1),
        b(2),
        dual(3)
    }

CfprApLsFcZoneState ::= TEXTUAL-CONVENTION
    STATUS        current
    DESCRIPTION
        ""
    SYNTAX        INTEGER
    {
        notApplied(0),
        applied(1),
        applying(2),
        applyPending(3),
        notActive(4),
        active(5),
        created(6),
        createFailed(7),
        deleted(8),
        zoneMergeFailure(9)
    }

CfprApLsOperState ::= TEXTUAL-CONVENTION
    STATUS        current
    DESCRIPTION
        ""
    SYNTAX        INTEGER
    {
        indeterminate(0),
        unassociated(1),
        ok(10),
        discovery(11),
        config(12),
        unconfig(13),
        powerOff(14),
        restart(15),
        maintenance(20),
        test(21),
        computeMismatch(29),
        computeFailed(30),
        degraded(31),
        discoveryFailed(32),
        configFailure(33),
        unconfigFailed(34),
        testFailed(35),
        maintenanceFailed(36),
        removed(40),
        disabled(41),
        inaccessible(50),
        thermalProblem(60),
        powerProblem(61),
        voltageProblem(62),
        inoperable(63),
        decomissioning(101),
        biosRestore(201),
        cmosReset(202),
        diagnostics(203),
        diagnosticsFailed(204),
        pendingReboot(210),
        pendingReassociation(211),
        svnicNotPresent(212)
    }

CfprApLsOwner ::= TEXTUAL-CONVENTION
    STATUS        current
    DESCRIPTION
        ""
    SYNTAX        INTEGER
    {
        management(1),
        physicalInherit(2),
        physicalDefaultConfig(4),
        tier(8)
    }

CfprApLsPowerState ::= TEXTUAL-CONVENTION
    STATUS        current
    DESCRIPTION
        ""
    SYNTAX        INTEGER
    {
        down(0),
        up(1),
        cycleImmediate(2),
        cycleWait(3),
        hardResetImmediate(4),
        hardResetWait(5),
        softShutDown(6),
        softShutDownOnly(7),
        cmosResetImmediate(12),
        bmcResetImmediate(13),
        bmcResetWait(14),
        diagnosticInterrupt(15),
        kvmReset(16),
        adminUp(31),
        adminDown(32),
        ipmiReset(33)
    }

CfprApLsResolveFromRemoteServer ::= TEXTUAL-CONVENTION
    STATUS        current
    DESCRIPTION
        ""
    SYNTAX        INTEGER
    {
        no(0),
        yes(1)
    }

CfprApLsServerFsmCurrentFsm ::= TEXTUAL-CONVENTION
    STATUS        current
    DESCRIPTION
        ""
    SYNTAX        INTEGER
    {
        nop(0),
        configure(158)
    }

CfprApLsServerFsmStageName ::= TEXTUAL-CONVENTION
    STATUS        current
    DESCRIPTION
        ""
    SYNTAX        INTEGER
    {
        nop(0),
        configureBegin(158),
        configureApplyTemplate(159),
        configureApplyIdentifiers(160),
        configureCheckAssignedIdentifiersForDup(161),
        configureResolvePolicies(162),
        configureResolveNetworkPolicies(163),
        configureResolveNetworkTemplates(164),
        configureResolveIdentifiers(165),
        configureApplyDefaultIdentifiers(166),
        configureCheckAssignedDefaultIdentifiersForDup(167),
        configureResolveDefaultIdentifiers(168),
        configureResolveDistributableNames(169),
        configureResolveDistributable(170),
        configureResolveImages(171),
        configureResolveSchedule(172),
        configureValidatePolicyOwnership(173),
        configureApplyPolicies(174),
        configureProvisionStorage(175),
        configureWaitForStorageProvision(176),
        configureResolveBootConfig(177),
        configureEvaluateAssociation(178),
        configureAnalyzeImpact(179),
        configureWaitForMaintPermission(180),
        configureWaitForMaintWindow(181),
        configureCommitStorage(182),
        configureWaitForCommitStorage(183),
        configureApplyConfig(184),
        configureWaitForAssocCompletion(185),
        configureFail(644),
        configureSuccess(645)
    }

CfprApLsServerFsmTaskFlags ::= TEXTUAL-CONVENTION
    STATUS        current
    DESCRIPTION
        ""
    SYNTAX        BITS
    {
        samDmeLsServerConfigureModification(14),
        samDmeLsServerConfigureFinalDisassoc(15),
        samDmeLsServerConfigureLsRename(16)
    }

CfprApLsServerFsmTaskItem ::= TEXTUAL-CONVENTION
    STATUS        current
    DESCRIPTION
        ""
    SYNTAX        INTEGER
    {
        nop(0),
        configure(158)
    }

CfprApLsType ::= TEXTUAL-CONVENTION
    STATUS        current
    DESCRIPTION
        ""
    SYNTAX        INTEGER
    {
        instance(0),
        initialTemplate(1),
        updatingTemplate(2)
    }

CfprApLsbootADefBootMode ::= TEXTUAL-CONVENTION
    STATUS        current
    DESCRIPTION
        ""
    SYNTAX        INTEGER
    {
        legacy(1),
        uefi(2)
    }

CfprApLsbootAccessType ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprApLsbootDefaultLocalImageType ::= TEXTUAL-CONVENTION
    STATUS        current
    DESCRIPTION
        ""
    SYNTAX        INTEGER
    {
        localAny(1),
        sdCard(2),
        localLun(3),
        usbIntern(4),
        usbExtern(5)
    }

CfprApLsbootIScsiAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprApLsbootIScsiType ::= TEXTUAL-CONVENTION
    STATUS        current
    DESCRIPTION
        ""
    SYNTAX        INTEGER
    {
        virtualMedia(1),
        storage(2),
        lan(3),
        iscsi(4),
        san(5)
    }

CfprApLsbootIScsiImagePathType ::= TEXTUAL-CONVENTION
    STATUS        current
    DESCRIPTION
        ""
    SYNTAX        INTEGER
    {
        primary(0),
        secondary(1)
    }

CfprApLsbootLanAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprApLsbootLanType ::= TEXTUAL-CONVENTION
    STATUS        current
    DESCRIPTION
        ""
    SYNTAX        INTEGER
    {
        virtualMedia(1),
        storage(2),
        lan(3),
        iscsi(4),
        san(5)
    }

CfprApLsbootLanBootProt ::= TEXTUAL-CONVENTION
    STATUS        current
    DESCRIPTION
        ""
    SYNTAX        INTEGER
    {
        pxe(0),
        gpxe(1),
        iSCSI(2)
    }

CfprApLsbootLanImagePathType ::= TEXTUAL-CONVENTION
    STATUS        current
    DESCRIPTION
        ""
    SYNTAX        INTEGER
    {
        primary(0),
        secondary(1)
    }

CfprApLsbootLocalHddImageType ::= TEXTUAL-CONVENTION
    STATUS        current
    DESCRIPTION
        ""
    SYNTAX        INTEGER
    {
        localAny(1),
        sdCard(2),
        localLun(3),
        usbIntern(4),
        usbExtern(5)
    }

CfprApLsbootPurpose ::= TEXTUAL-CONVENTION
    STATUS        current
    DESCRIPTION
        ""
    SYNTAX        INTEGER
    {
        utility(1),
        operational(2)
    }

CfprApLsbootSanAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprApLsbootSanType ::= TEXTUAL-CONVENTION
    STATUS        current
    DESCRIPTION
        ""
    SYNTAX        INTEGER
    {
        virtualMedia(1),
        storage(2),
        lan(3),
        iscsi(4),
        san(5)
    }

CfprApLsbootSanCatSanImageType ::= TEXTUAL-CONVENTION
    STATUS        current
    DESCRIPTION
        ""
    SYNTAX        INTEGER
    {
        primary(0),
        secondary(1)
    }

CfprApLsbootSanCatSanImagePathType ::= TEXTUAL-CONVENTION
    STATUS        current
    DESCRIPTION
        ""
    SYNTAX        INTEGER
    {
        primary(0),
        secondary(1)
    }

CfprApLsbootSanImageType ::= TEXTUAL-CONVENTION
    STATUS        current
    DESCRIPTION
        ""
    SYNTAX        INTEGER
    {
        primary(0),
        secondary(1)
    }

CfprApLsbootSanImagePathType ::= TEXTUAL-CONVENTION
    STATUS        current
    DESCRIPTION
        ""
    SYNTAX        INTEGER
    {
        primary(0),
        secondary(1)
    }

CfprApLsbootStorageAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprApLsbootStorageType ::= TEXTUAL-CONVENTION
    STATUS        current
    DESCRIPTION
        ""
    SYNTAX        INTEGER
    {
        virtualMedia(1),
        storage(2),
        lan(3),
        iscsi(4),
        san(5)
    }

CfprApLsbootUsbExternalImageType ::= TEXTUAL-CONVENTION
    STATUS        current
    DESCRIPTION
        ""
    SYNTAX        INTEGER
    {
        localAny(1),
        sdCard(2),
        localLun(3),
        usbIntern(4),
        usbExtern(5)
    }

CfprApLsbootUsbFlashStorageImageType ::= TEXTUAL-CONVENTION
    STATUS        current
    DESCRIPTION
        ""
    SYNTAX        INTEGER
    {
        localAny(1),
        sdCard(2),
        localLun(3),
        usbIntern(4),
        usbExtern(5)
    }

CfprApLsbootUsbInternalImageType ::= TEXTUAL-CONVENTION
    STATUS        current
    DESCRIPTION
        ""
    SYNTAX        INTEGER
    {
        localAny(1),
        sdCard(2),
        localLun(3),
        usbIntern(4),
        usbExtern(5)
    }

CfprApLsbootVirtualMediaType ::= TEXTUAL-CONVENTION
    STATUS        current
    DESCRIPTION
        ""
    SYNTAX        INTEGER
    {
        virtualMedia(1),
        storage(2),
        lan(3),
        iscsi(4),
        san(5)
    }

CfprApLsmaintAckChangeDetails ::= TEXTUAL-CONVENTION
    STATUS        current
    DESCRIPTION
        ""
    SYNTAX        BITS
    {
        binding(0),
        hostVirtEthIf(1),
        hostNonvirtEthIf(2),
        hostEthIfProfile(3),
        hostEthIfQos(4),
        hostEthIfNwCtrl(5),
        hostVirtFcIf(6),
        hostNonvirtFcIf(7),
        hostVirtFcIfPersBind(8),
        hostNonvirtFcIfPersBind(9),
        hostFcIfProfile(10),
        hostFcIfQos(11),
        hostFcoeIf(12),
        vif(13),
        vlan(14),
        vsan(15),
        ip(16),
        bootOrder(17),
        bootVirtVnic(18),
        bootNonvirtVnic(19),
        bootLocalStorage(20),
        bootVirtPxe(21),
        bootNonvirtPxe(22),
        bladeIdentity(24),
        agentPolicy(25),
        biosFw(26),
        storageControllerFw(27),
        adaptorHostFw(28),
        adaptorNwFw(29),
        mgmtControllerFw(30),
        localDiskPolicy(31),
        pin(32),
        sol(33),
        epAuth(34),
        biosProfile(35),
        checkpoint(36),
        implicitReboot(37),
        implicitHostFcIfProfileRedeploy(38),
        boardControllerFw(39),
        hostEthIfQosHostControl(40),
        localDiskFw(41),
        implicitHostEthIfProfileRedeploy(42),
        storagePath(43),
        bmcUpdateBiosFw(44),
        hostIfPcie(45),
        flexflashConfig(46),
        bootmodeConfig(48),
        securebootConfig(49),
        vmediaConfig(50),
        ssposUpdateFw(51)
    }

CfprApLsmaintAckChanges ::= TEXTUAL-CONVENTION
    STATUS        current
    DESCRIPTION
        ""
    SYNTAX        BITS
    {
        serverIdentity(0),
        storage(1),
        networking(2),
        vnicVhbaPlacement(3),
        bootOrder(4),
        serverAssignment(5),
        operationalPolicies(6)
    }

CfprApLsmaintAckDisr ::= TEXTUAL-CONVENTION
    STATUS        current
    DESCRIPTION
        ""
    SYNTAX        BITS
    {
        upTime(0),
        acPowerCycle(1)
    }

CfprApLsmaintChangeMode ::= TEXTUAL-CONVENTION
    STATUS        current
    DESCRIPTION
        ""
    SYNTAX        INTEGER
    {
        noChange(0),
        unconfig(1),
        forceUnconfig(2),
        rediscover(4),
        config(8),
        diagConfig(16),
        diagUnconfig(32),
        removeConfig(64),
        diag(128)
    }

CfprApMacpoolPoolAssignmentOrder ::= TEXTUAL-CONVENTION
    STATUS        current
    DESCRIPTION
        ""
    SYNTAX        INTEGER
    {
        default(0),
        sequential(1)
    }

CfprApMemoryAdminState ::= TEXTUAL-CONVENTION
    STATUS        current
    DESCRIPTION
        ""
    SYNTAX        INTEGER
    {
        policy(1),
        resetErrors(2)
    }

CfprApMemoryArrayId ::= TEXTUAL-CONVENTION
    STATUS        current
    DESCRIPTION
        ""
    SYNTAX        Gauge32 (1..8)

CfprApMemoryArrayEnvStatsThresholded ::= TEXTUAL-CONVENTION
    STATUS        current
    DESCRIPTION
        ""
    SYNTAX        BITS
    {
        inputCurrent(0),
        inputCurrentAvg(1),
        inputCurrentMax(2),
        inputCurrentMin(3)
    }

CfprApMemoryArrayEnvStatsHistThresholded ::= TEXTUAL-CONVENTION
    STATUS        current
    DESCRIPTION
        ""
    SYNTAX        BITS
    {
        inputCurrent(0),
        inputCurrentAvg(1),
        inputCurrentMax(2),
        inputCurrentMin(3)
    }

CfprApMemoryBufferUnitId ::= TEXTUAL-CONVENTION
    STATUS        current
    DESCRIPTION
        ""
    SYNTAX        Gauge32 (1..16)

CfprApMemoryBufferUnitEnvStatsThresholded ::= TEXTUAL-CONVENTION
    STATUS        current
    DESCRIPTION
        ""
    SYNTAX        BITS
    {
        temperature(0),
        temperatureAvg(1),
        temperatureMax(2),
        temperatureMin(3)
    }

CfprApMemoryBufferUnitEnvStatsHistThresholded ::= TEXTUAL-CONVENTION
    STATUS        current
    DESCRIPTION
        ""
    SYNTAX        BITS
    {
        temperature(0),
        temperatureAvg(1),
        temperatureMax(2),
        temperatureMin(3)
    }

CfprApMemoryErrorCorrection ::= TEXTUAL-CONVENTION
    STATUS        current
    DESCRIPTION
        ""
    SYNTAX        INTEGER
    {
        undiscovered(0),
        other(1),
        unknown(2),
        none(3),
        parity(4),
        singleBitECC(5),
        multiBitECC(6),
        crc(7)
    }

CfprApMemoryErrorStatsThresholded ::= TEXTUAL-CONVENTION
    STATUS        current
    DESCRIPTION
        ""
    SYNTAX        BITS
    {
        addressParityErrors(0),
        eccMultibitErrors(1),
        eccSinglebitErrors(2),
        mismatchErrors(3)
    }

CfprApMemoryFormFactor ::= TEXTUAL-CONVENTION
    STATUS        current
    DESCRIPTION
        ""
    SYNTAX        INTEGER
    {
        undiscovered(0),
        other(1),
        unknown(2),
        simm(3),
        dimm(9),
        tsop(10),
        rimm(12),
        sodimm(13),
        srimm(14),
        fbDimm(15)
    }

CfprApMemoryIssues ::= TEXTUAL-CONVENTION
    STATUS        current
    DESCRIPTION
        ""
    SYNTAX        BITS
    {
        uncorrectableEccError(0),
        correctableEccError(1),
        addressParityError(2),
        memoryMismatchError(3)
    }

CfprApMemoryRuntimeThresholded ::= TEXTUAL-CONVENTION
    STATUS        current
    DESCRIPTION
        ""
    SYNTAX        BITS
    {
        available(0),
        availableAvg(1),
        availableMax(2),
        availableMin(3),
        cached(4),
        cachedAvg(5),
        cachedMax(6),
        cachedMin(7),
        total(8),
        totalAvg(9),
        totalMax(10),
        totalMin(11)
    }

CfprApMemoryRuntimeType ::= TEXTUAL-CONVENTION
    STATUS        current
    DESCRIPTION
        ""
    SYNTAX        INTEGER
    {
        swap(1),
        total(2)
    }

CfprApMemoryRuntimeHistThresholded ::= TEXTUAL-CONVENTION
    STATUS        current
    DESCRIPTION
        ""
    SYNTAX        BITS
    {
        available(0),
        availableAvg(1),
        availableMax(2),
        availableMin(3),
        cached(4),
        cachedAvg(5),
        cachedMax(6),
        cachedMin(7),
        total(8),
        totalAvg(9),
        totalMax(10),
        totalMin(11)
    }

CfprApMemoryType ::= TEXTUAL-CONVENTION
    STATUS        current
    DESCRIPTION
        ""
    SYNTAX        INTEGER
    {
        undiscovered(0),
        other(1),
        unknown(2),
        dram(3),
        edram(4),
        vram(5),
        sram(6),
        ram(7),
        rom(8),
        flash(9),
        eeprom(10),
        feprom(11),
        eprom(12),
        cdram(13),
        n3DRAM(14),
        sdram(15),
        sgram(16),
        rdram(17),
        ddr(18),
        ddr2(19),
        ddr2FbDimm(20),
        ddr3(24),
        fbd2(25)
    }

CfprApMemoryUnitId ::= TEXTUAL-CONVENTION
    STATUS        current
    DESCRIPTION
        ""
    SYNTAX        Gauge32 (1..256)

CfprApMemoryUnitOperability ::= TEXTUAL-CONVENTION
    STATUS        current
    DESCRIPTION
        ""
    SYNTAX        INTEGER
    {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        malformedFru(14),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107),
        linkActivateBlocked(108)
    }

CfprApMemoryUnitEnvStatsThresholded ::= TEXTUAL-CONVENTION
    STATUS        current
    DESCRIPTION
        ""
    SYNTAX        BITS
    {
        temperature(0),
        temperatureAvg(1),
        temperatureMax(2),
        temperatureMin(3)
    }

CfprApMemoryUnitEnvStatsHistThresholded ::= TEXTUAL-CONVENTION
    STATUS        current
    DESCRIPTION
        ""
    SYNTAX        BITS
    {
        temperature(0),
        temperatureAvg(1),
        temperatureMax(2),
        temperatureMin(3)
    }

CfprApMemoryVisibility ::= TEXTUAL-CONVENTION
    STATUS        current
    DESCRIPTION
        ""
    SYNTAX        INTEGER
    {
        unknown(0),
        yes(1),
        no(2)
    }

CfprApMgmtAccess ::= TEXTUAL-CONVENTION
    STATUS        current
    DESCRIPTION
        ""
    SYNTAX        INTEGER
    {
        unspecified(0),
        inBand(1),
        outOfBand(2),
        internal(4),
        virtual(8)
    }

CfprApMgmtAdminState ::= TEXTUAL-CONVENTION
    STATUS        current
    DESCRIPTION
        ""
    SYNTAX        INTEGER
    {
        disable(0),
        enable(1)
    }

CfprApMgmtBackupPostAction ::= TEXTUAL-CONVENTION
    STATUS        current
    DESCRIPTION
        ""
    SYNTAX        INTEGER
    {
        none(0),
        remove(1)
    }

CfprApMgmtBackupProto ::= TEXTUAL-CONVENTION
    STATUS        current
    DESCRIPTION
        ""
    SYNTAX        INTEGER
    {
        none(0),
        ftp(1),
        tftp(2),
        scp(3),
        http(4),
        sftp(5),
        nfsCopy(6)
    }

CfprApMgmtBackupFsmCurrentFsm ::= TEXTUAL-CONVENTION
    STATUS        current
    DESCRIPTION
        ""
    SYNTAX        INTEGER
    {
        nop(0),
        backup(473)
    }

CfprApMgmtBackupFsmStageName ::= TEXTUAL-CONVENTION
    STATUS        current
    DESCRIPTION
        ""
    SYNTAX        INTEGER
    {
        nop(0),
        backupBegin(473),
        backupBackupLocal(474),
        backupUpload(475),
        backupFail(646),
        backupSuccess(647)
    }

CfprApMgmtBackupFsmTaskItem ::= TEXTUAL-CONVENTION
    STATUS        current
    DESCRIPTION
        ""
    SYNTAX        INTEGER
    {
        nop(0),
        backup(473)
    }

CfprApMgmtBackupInterval ::= TEXTUAL-CONVENTION
    STATUS        current
    DESCRIPTION
        ""
    SYNTAX        INTEGER
    {
        n1day(86400),
        n1week(604800),
        n2week(1209600)
    }

CfprApMgmtBackupIssue ::= TEXTUAL-CONVENTION
    STATUS        current
    DESCRIPTION
        ""
    SYNTAX        INTEGER
    {
        none(0),
        outdated(1)
    }

CfprApMgmtBackupJob ::= TEXTUAL-CONVENTION
    STATUS        current
    DESCRIPTION
        ""
    SYNTAX        INTEGER
    {
        immediate(2)
    }

CfprApMgmtBackupPolicyFsmCurrentFsm ::= TEXTUAL-CONVENTION
    STATUS        current
    DESCRIPTION
        ""
    SYNTAX        INTEGER
    {
        nop(0),
        reportConfigCopy(460)
    }

CfprApMgmtBackupPolicyFsmStageName ::= TEXTUAL-CONVENTION
    STATUS        current
    DESCRIPTION
        ""
    SYNTAX        INTEGER
    {
        nop(0),
        reportConfigCopyBegin(460),
        reportConfigCopyReport(461),
        reportConfigCopyFail(660),
        reportConfigCopySuccess(661)
    }

CfprApMgmtBackupStatus ::= TEXTUAL-CONVENTION
    STATUS        current
    DESCRIPTION
        ""
    SYNTAX        INTEGER
    {
        idle(0),
        exporting(1),
        succeeded(2),
        failed(3)
    }

CfprApMgmtBackupType ::= TEXTUAL-CONVENTION
    STATUS        current
    DESCRIPTION
        ""
    SYNTAX        INTEGER
    {
        fullState(1),
        configAll(2)
    }

CfprApMgmtCfgExportPolicyFsmCurrentFsm ::= TEXTUAL-CONVENTION
    STATUS        current
    DESCRIPTION
        ""
    SYNTAX        INTEGER
    {
        nop(0),
        reportConfigCopy(460)
    }

CfprApMgmtCfgExportPolicyFsmStageName ::= TEXTUAL-CONVENTION
    STATUS        current
    DESCRIPTION
        ""
    SYNTAX        INTEGER
    {
        nop(0),
        reportConfigCopyBegin(460),
        reportConfigCopyReport(461),
        reportConfigCopyFail(660),
        reportConfigCopySuccess(661)
    }

CfprApMgmtCimcSecureBootAdminState ::= TEXTUAL-CONVENTION
    STATUS        current
    DESCRIPTION
        ""
    SYNTAX        INTEGER
    {
        disable(0),
        enable(1)
    }

CfprApMgmtConfigState ::= TEXTUAL-CONVENTION
    STATUS        current
    DESCRIPTION
        ""
    SYNTAX        INTEGER
    {
        incomplete(0),
        unsupportedVlan(1),
        unsupportedServer(2),
        unresolvedVlan(3),
        unsupportedFirmware(4),
        valid(5)
    }

CfprApMgmtConnectionState ::= TEXTUAL-CONVENTION
    STATUS        current
    DESCRIPTION
        ""
    SYNTAX        INTEGER
    {
        unInitialized(0),
        acknowledged(1),
        unsupportedConnectivity(2)
    }

CfprApMgmtControllerFsmCurrentFsm ::= TEXTUAL-CONVENTION
    STATUS        current
    DESCRIPTION
        ""
    SYNTAX        INTEGER
    {
        nop(0),
        updateUCSManager(17),
        updateSwitch(22),
        updateIOM(31),
        extMgmtInterfaceConfig(205),
        registryConfig(393),
        sysConfig(483)
    }

CfprApMgmtControllerFsmStageName ::= TEXTUAL-CONVENTION
    STATUS        current
    DESCRIPTION
        ""
    SYNTAX        INTEGER
    {
        nop(0),
        updateUCSManagerBegin(17),
        updateUCSManagerCopyExtToLocal(18),
        updateUCSManagerCopyExtToPeer(19),
        updateUCSManagerStart(20),
        updateUCSManagerExecute(21),
        updateSwitchBegin(22),
        updateSwitchCopyToLocal(23),
        updateSwitchCopyToPeer(24),
        updateSwitchUpdateLocal(25),
        updateSwitchVerifyLocal(26),
        updateSwitchResetLocal(27),
        updateSwitchUpdateRemote(28),
        updateSwitchVerifyRemote(29),
        updateSwitchResetRemote(30),
        updateIOMBegin(31),
        updateIOMCopyImgFromRep(32),
        updateIOMCopyIOMImgToSub(33),
        extMgmtInterfaceConfigBegin(205),
        extMgmtInterfaceConfigCIMCVlanCfgLocal(206),
        extMgmtInterfaceConfigCIMCVlanCfgPeer(207),
        registryConfigBegin(393),
        registryConfigRemove(394),
        sysConfigBegin(483),
        sysConfigPrimary(484),
        sysConfigSecondary(485),
        extMgmtInterfaceConfigFail(648),
        extMgmtInterfaceConfigSuccess(649),
        registryConfigFail(650),
        registryConfigSuccess(651),
        sysConfigFail(652),
        sysConfigSuccess(653),
        updateIOMFail(654),
        updateIOMSuccess(655),
        updateSwitchFail(656),
        updateSwitchSuccess(657),
        updateUCSManagerFail(658),
        updateUCSManagerSuccess(659)
    }

CfprApMgmtControllerFsmTaskFlags ::= TEXTUAL-CONVENTION
    STATUS        current
    DESCRIPTION
        ""
    SYNTAX        BITS
    {
        samDmeMgmtControllerUpdateSwitchActivate(1),
        samDmeMgmtControllerUpdateSwitchReset(2)
    }

CfprApMgmtControllerFsmTaskItem ::= TEXTUAL-CONVENTION
    STATUS        current
    DESCRIPTION
        ""
    SYNTAX        INTEGER
    {
        nop(0),
        updateUCSManager(17),
        updateSwitch(22),
        updateIOM(31),
        extMgmtInterfaceConfig(205),
        registryConfig(393),
        sysConfig(483)
    }

CfprApMgmtDimmBlacklistingOperState ::= TEXTUAL-CONVENTION
    STATUS        current
    DESCRIPTION
        ""
    SYNTAX        INTEGER
    {
        unknown(0),
        enabled(1),
        disabled(2),
        unsupported(3)
    }

CfprApMgmtEntityChassisDeviceIoState1 ::= TEXTUAL-CONVENTION
    STATUS        current
    DESCRIPTION
        ""
    SYNTAX        INTEGER
    {
        unknown(0),
        ok(1),
        openError(2),
        readError(3),
        writeError(4)
    }

CfprApMgmtEntityChassisDeviceIoState2 ::= TEXTUAL-CONVENTION
    STATUS        current
    DESCRIPTION
        ""
    SYNTAX        INTEGER
    {
        unknown(0),
        ok(1),
        openError(2),
        readError(3),
        writeError(4)
    }

CfprApMgmtEntityChassisDeviceIoState3 ::= TEXTUAL-CONVENTION
    STATUS        current
    DESCRIPTION
        ""
    SYNTAX        INTEGER
    {
        unknown(0),
        ok(1),
        openError(2),
        readError(3),
        writeError(4)
    }

CfprApMgmtEntityHaFailureReason ::= TEXTUAL-CONVENTION
    STATUS        current
    DESCRIPTION
        ""
    SYNTAX        INTEGER
    {
        none(0),
        nodeDown(1),
        peerNodeDown(2),
        mgmtServicesUnresponsive(3),
        peerMgmtServicesUnresponsive(4),
        chassisConfigIncomplete(5),
        peerChassisConfigIncomplete(6),
        networkInterfaceDown(7)
    }

CfprApMgmtEntityHaReadiness ::= TEXTUAL-CONVENTION
    STATUS        current
    DESCRIPTION
        ""
    SYNTAX        INTEGER
    {
        unknown(0),
        ready(1),
        downgraded(2),
        notReady(3)
    }

CfprApMgmtEntityLeadership ::= TEXTUAL-CONVENTION
    STATUS        current
    DESCRIPTION
        ""
    SYNTAX        INTEGER
    {
        unknown(0),
        primary(1),
        subordinate(2),
        inapplicable(3),
        electionInProgress(4),
        electionFailed(5)
    }

CfprApMgmtEntityMgmtServicesState ::= TEXTUAL-CONVENTION
    STATUS        current
    DESCRIPTION
        ""
    SYNTAX        INTEGER
    {
        unknown(0),
        up(1),
        unresponsive(2),
        down(3),
        switchoverInProgress(4)
    }

CfprApMgmtEntityProblems ::= TEXTUAL-CONVENTION
    STATUS        current
    DESCRIPTION
        ""
    SYNTAX        BITS
    {
        leadership(0),
        membership(1),
        umbilical(2),
        haReady(3),
        versionMismatch(4)
    }

CfprApMgmtEntityState ::= TEXTUAL-CONVENTION
    STATUS        current
    DESCRIPTION
        ""
    SYNTAX        INTEGER
    {
        unknown(0),
        up(1),
        down(2)
    }

CfprApMgmtEntityUmbilicalState ::= TEXTUAL-CONVENTION
    STATUS        current
    DESCRIPTION
        ""
    SYNTAX        INTEGER
    {
        unknown(0),
        degraded(1),
        full(2),
        failed(3)
    }

CfprApMgmtExportPolicyAdminState ::= TEXTUAL-CONVENTION
    STATUS        current
    DESCRIPTION
        ""
    SYNTAX        INTEGER
    {
        disable(0),
        enable(1)
    }

CfprApMgmtExportPolicyProto ::= TEXTUAL-CONVENTION
    STATUS        current
    DESCRIPTION
        ""
    SYNTAX        INTEGER
    {
        none(0),
        ftp(1),
        tftp(2),
        scp(3),
        http(4),
        sftp(5),
        nfsCopy(6)
    }

CfprApMgmtExportPolicyFsmCurrentFsm ::= TEXTUAL-CONVENTION
    STATUS        current
    DESCRIPTION
        ""
    SYNTAX        INTEGER
    {
        nop(0),
        reportConfigCopy(460)
    }

CfprApMgmtExportPolicyFsmStageName ::= TEXTUAL-CONVENTION
    STATUS        current
    DESCRIPTION
        ""
    SYNTAX        INTEGER
    {
        nop(0),
        reportConfigCopyBegin(460),
        reportConfigCopyReport(461),
        reportConfigCopyFail(660),
        reportConfigCopySuccess(661)
    }

CfprApMgmtExportPolicyFsmTaskItem ::= TEXTUAL-CONVENTION
    STATUS        current
    DESCRIPTION
        ""
    SYNTAX        INTEGER
    {
        nop(0),
        reportConfigCopy(460)
    }

CfprApMgmtIPv6IfAddrFsmCurrentFsm ::= TEXTUAL-CONVENTION
    STATUS        current
    DESCRIPTION
        ""
    SYNTAX        INTEGER
    {
        nop(0),
        swMgmtOobIpv6IfConfig(399)
    }

CfprApMgmtIPv6IfAddrFsmStageName ::= TEXTUAL-CONVENTION
    STATUS        current
    DESCRIPTION
        ""
    SYNTAX        INTEGER
    {
        nop(0),
        swMgmtOobIpv6IfConfigBegin(399),
        swMgmtOobIpv6IfConfigSwitch(400),
        swMgmtOobIpv6IfConfigFail(662),
        swMgmtOobIpv6IfConfigSuccess(663)
    }

CfprApMgmtIPv6IfAddrFsmTaskItem ::= TEXTUAL-CONVENTION
    STATUS        current
    DESCRIPTION
        ""
    SYNTAX        INTEGER
    {
        nop(0),
        swMgmtOobIpv6IfConfig(399)
    }

CfprApMgmtIfFsmCurrentFsm ::= TEXTUAL-CONVENTION
    STATUS        current
    DESCRIPTION
        ""
    SYNTAX        INTEGER
    {
        nop(0),
        swMgmtOobIfConfig(395),
        swMgmtInbandIfConfig(397),
        virtualIfConfig(464),
        enableVip(467),
        disableVip(469),
        enableHA(471)
    }

CfprApMgmtIfFsmStageName ::= TEXTUAL-CONVENTION
    STATUS        current
    DESCRIPTION
        ""
    SYNTAX        INTEGER
    {
        nop(0),
        swMgmtOobIfConfigBegin(395),
        swMgmtOobIfConfigSwitch(396),
        swMgmtInbandIfConfigBegin(397),
        swMgmtInbandIfConfigSwitch(398),
        virtualIfConfigBegin(464),
        virtualIfConfigLocal(465),
        virtualIfConfigRemote(466),
        enableVipBegin(467),
        enableVipLocal(468),
        disableVipBegin(469),
        disableVipPeer(470),
        enableHABegin(471),
        enableHALocal(472),
        disableVipFail(664),
        disableVipSuccess(665),
        enableHAFail(666),
        enableHASuccess(667),
        enableVipFail(668),
        enableVipSuccess(669),
        swMgmtInbandIfConfigFail(670),
        swMgmtInbandIfConfigSuccess(671),
        swMgmtOobIfConfigFail(672),
        swMgmtOobIfConfigSuccess(673),
        virtualIfConfigFail(674),
        virtualIfConfigSuccess(675)
    }

CfprApMgmtIfFsmTaskItem ::= TEXTUAL-CONVENTION
    STATUS        current
    DESCRIPTION
        ""
    SYNTAX        INTEGER
    {
        nop(0),
        swMgmtOobIfConfig(395),
        swMgmtInbandIfConfig(397),
        virtualIfConfig(464),
        enableVip(467),
        disableVip(469),
        enableHA(471)
    }

CfprApMgmtImportAction ::= TEXTUAL-CONVENTION
    STATUS        current
    DESCRIPTION
        ""
    SYNTAX        INTEGER
    {
        replace(0)
    }

CfprApMgmtImportStatus ::= TEXTUAL-CONVENTION
    STATUS        current
    DESCRIPTION
        ""
    SYNTAX        INTEGER
    {
        idle(0),
        downloadSucceeded(1),
        configSucceeded(2),
        succeeded(3),
        failed(4)
    }

CfprApMgmtImporterPostAction ::= TEXTUAL-CONVENTION
    STATUS        current
    DESCRIPTION
        ""
    SYNTAX        INTEGER
    {
        none(0),
        remove(1)
    }

CfprApMgmtImporterProto ::= TEXTUAL-CONVENTION
    STATUS        current
    DESCRIPTION
        ""
    SYNTAX        INTEGER
    {
        none(0),
        ftp(1),
        tftp(2),
        scp(3),
        http(4),
        sftp(5),
        nfsCopy(6)
    }

CfprApMgmtImporterFsmCurrentFsm ::= TEXTUAL-CONVENTION
    STATUS        current
    DESCRIPTION
        ""
    SYNTAX        INTEGER
    {
        nop(0),
        import(476)
    }

CfprApMgmtImporterFsmStageName ::= TEXTUAL-CONVENTION
    STATUS        current
    DESCRIPTION
        ""
    SYNTAX        INTEGER
    {
        nop(0),
        importBegin(476),
        importDownloadLocal(477),
        importCleanUp(478),
        importConfigBreakout(479),
        importWaitForSwitch(480),
        importConfig(481),
        importReportResults(482),
        importFail(676),
        importSuccess(677)
    }

CfprApMgmtImporterFsmTaskItem ::= TEXTUAL-CONVENTION
    STATUS        current
    DESCRIPTION
        ""
    SYNTAX        INTEGER
    {
        nop(0),
        import(476)
    }

CfprApMgmtIntAuthPolicyMethod ::= TEXTUAL-CONVENTION
    STATUS        current
    DESCRIPTION
        ""
    SYNTAX        INTEGER
    {
        none(0),
        password(1)
    }

CfprApMgmtMode ::= TEXTUAL-CONVENTION
    STATUS        current
    DESCRIPTION
        ""
    SYNTAX        INTEGER
    {
        inBand(0)
    }

CfprApMgmtOperState ::= TEXTUAL-CONVENTION
    STATUS        current
    DESCRIPTION
        ""
    SYNTAX        INTEGER
    {
        unknown(0),
        notDeployed(1),
        deployed(2),
        up(3),
        down(4)
    }

CfprApMgmtPmonEntryState ::= TEXTUAL-CONVENTION
    STATUS        current
    DESCRIPTION
        ""
    SYNTAX        INTEGER
    {
        unknown(0),
        idle(1),
        running(2),
        pending(3),
        failed(4),
        error(5),
        exitPending(6),
        terminated(7),
        killed(8)
    }

CfprApMgmtSecureBootOperState ::= TEXTUAL-CONVENTION
    STATUS        current
    DESCRIPTION
        ""
    SYNTAX        INTEGER
    {
        disabled(0),
        enabled(1),
        unsupported(2),
        enabling(3)
    }

CfprApMgmtSource ::= TEXTUAL-CONVENTION
    STATUS        current
    DESCRIPTION
        ""
    SYNTAX        INTEGER
    {
        unspecified(0),
        sharedLom(1),
        sideband(2)
    }

CfprApMgmtStateQual ::= TEXTUAL-CONVENTION
    STATUS        current
    DESCRIPTION
        ""
    SYNTAX        INTEGER
    {
        unspecified(0),
        valid(1),
        misconnected(2)
    }

CfprApMgmtStorageSubsystemState ::= TEXTUAL-CONVENTION
    STATUS        current
    DESCRIPTION
        ""
    SYNTAX        INTEGER
    {
        unknown(0),
        uninitialized(1),
        initializing(2),
        initialized(3),
        unsupported(4)
    }

CfprApMgmtSubject ::= TEXTUAL-CONVENTION
    STATUS        current
    DESCRIPTION
        ""
    SYNTAX        INTEGER
    {
        unknown(0),
        blade(1),
        chassis(2),
        system(4),
        switch(8),
        adaptor(16),
        iocard(32),
        boardController(64)
    }

CfprApMgmtUpgradeStatus ::= TEXTUAL-CONVENTION
    STATUS        current
    DESCRIPTION
        ""
    SYNTAX        BITS
    {
        hwChangeDetected(0),
        fwChangeDetected(1),
        hwIncompatible(2),
        fwIncompatible(3),
        unsupportedHwVersion(4),
        unsupportedFwVersion(5),
        hwChangeSuccess(6),
        fwChangeSuccess(7)
    }

CfprApMoMoClassId ::= TEXTUAL-CONVENTION
    STATUS        current
    DESCRIPTION
        ""
    SYNTAX        INTEGER
    {
        unspecified(0),
        moTopProps(1),
        topRoot(2),
        topSystem(3),
        topMetaInf(4),
        topInfoPolicy(5),
        topSysDefaults(6),
        fsmTask(7),
        fsmFsm(8),
        fsmStage(9),
        namingNamedObject(10),
        namingNamedIdentifiedObject(11),
        conditionInfo(12),
        conditionReportable(13),
        conditionMutable(14),
        conditionImmutable(15),
        conditionMultiInstanceImmutable(16),
        conditionPolicy(17),
        conditionLog(18),
        conditionLoggable(19),
        aaaLog(20),
        aaaUserAction(21),
        aaaModLR(22),
        aaaSessionLR(23),
        eventEpCtrl(24),
        eventLog(25),
        eventRecord(26),
        eventHolder(27),
        eventInst(28),
        eventPolicy(29),
        faultBaseHolder(30),
        faultLocalTypedHolder(31),
        faultHolder(32),
        faultInst(33),
        faultBasePolicy(34),
        faultPolicy(35),
        faultSuppressPolicy(36),
        faultSuppressPolicyItem(37),
        faultSuppressTask(38),
        faultAffectedClass(39),
        statsItem(40),
        statsCurr(41),
        statsHist(42),
        statsHolder(43),
        statsCollectionPolicy(44),
        statsThresholdPolicy(45),
        statsThresholdClass(46),
        statsThresholdDefinition(47),
        statsThr32Definition(48),
        statsThr64Definition(49),
        statsThrFloatDefinition(50),
        statsThresholdValue(51),
        statsThr32Value(52),
        statsThr64Value(53),
        statsThrFloatValue(54),
        gmetaEp(55),
        gmetaHolder(56),
        gmetaClass(57),
        gmetaProp(58),
        gmetaPolicyMapHolder(59),
        equipmentPOSTCodeContainer(60),
        equipmentPOSTCodeTemplate(61),
        equipmentPOSTCodeReporter(62),
        equipmentPOSTCodeData(63),
        equipmentPOSTCode(64),
        equipmentPOST(65),
        swatInjection(66),
        swatTrigger(67),
        swatCondition(68),
        swatTarget(69),
        swatAction(70),
        swatResultstats(71),
        apeManager(72),
        apeMc(73),
        apeMcTable(74),
        apeFru(75),
        apeSdr(76),
        apeReading(77),
        apeParam(78),
        apeBootMethod(79),
        apeLANBoot(80),
        apeSANBoot(81),
        apeLocalDiskBoot(82),
        apeVirtualMediaBoot(83),
        apeHostAgent(84),
        apeDcosAgManager(85),
        apeSwitchFirmwareInv(86),
        apeControllerManager(87),
        apeControllerChassis(88),
        apeControllerEeprom(89),
        apeNicAgManager(90),
        apeAdapter(91),
        apeMenlo(92),
        apePalo(93),
        apeAdapterVnic(94),
        apeMenloVnic(95),
        apePaloVnic(96),
        apeVnicStats(97),
        apeMenloVnicStats(98),
        apePaloVnicStats(99),
        computeQualItem(100),
        computeQualifiedPolicy(101),
        computePhysicalQual(102),
        computeBladePosQual(103),
        computeRackPosQual(104),
        computeChassisQual(105),
        computeSlotQual(106),
        computeRackQual(107),
        computePool(108),
        computePoolingPolicy(109),
        computePooledPhysical(110),
        computePooledSlot(111),
        computePooledRackUnit(112),
        computeConfigPolicy(113),
        computeDiscPolicy(114),
        computeServerDiscPolicy(115),
        computeAChassisDiscPolicy(116),
        computeComputeDiscPolicy(117),
        computeChassisDiscPolicy(118),
        computePoolPolicyRef(119),
        computeItem(120),
        computeIOHub(121),
        computePhysical(122),
        computeLogical(123),
        computeABoard(124),
        computeBoard(125),
        computeExtBoard(126),
        computeBoardConnector(127),
        queryresultItem(128),
        queryresultUsage(129),
        queryresultDependency(130),
        dpsecMac(131),
        powerPolicy(132),
        powerGroupQual(133),
        powerAGroup(134),
        powerGroup(135),
        dcxVc(136),
        vnicL3If(137),
        vnicIPIf(138),
        vnicIPv4If(139),
        vnicIpAddr(140),
        vnicIpV4Addr(141),
        vnicIpV6Addr(142),
        vnicIpV4AddrConf(143),
        vnicIpV4AddrExplConf(144),
        vnicIpV6AddrConf(145),
        vnicIpV6AddrExplConf(146),
        vnicIpV4ProfDerivedAddr(147),
        vnicIpV4StaticAddr(148),
        vnicIpV6StaticAddr(149),
        vnicIpV4PooledAddr(150),
        vnicIpV4MgmtPooledAddr(151),
        vnicIpV6MgmtPooledAddr(152),
        vnicIPv4Dhcp(153),
        vnicIPv4Dns(154),
        vnicIPv4StaticRoute(155),
        vnicIPv4IscsiAddr(156),
        vnicIPv4PooledIscsiAddr(157),
        vnicBootIpPolicy(158),
        vnicConReq(159),
        vnicConPolicyRef(160),
        vnicDynamicConReq(161),
        vnicDynamicConPolicy(162),
        vnicSanConnPolicy(163),
        vnicLanConnPolicy(164),
        vnicFcNode(165),
        vnicIScsiNode(166),
        vnicBootTarget(167),
        vnicVlan(168),
        vnicIScsiTargetIf(169),
        vnicIScsiStaticTargetIf(170),
        vnicLun(171),
        vnicIScsiAutoTargetIf(172),
        vnicIScsiBootParams(173),
        vnicIScsiBootVnic(174),
        vnicConnection(175),
        vnicNicConn(176),
        vnicConnDef(177),
        vnicIf(178),
        vnicABeh(179),
        vnicDefBeh(180),
        vnicVnicBehPolicy(181),
        vnicVhbaBehPolicy(182),
        vnicUsnicConReq(183),
        vnicUsnicConPolicy(184),
        vnicUsnicConPolicyRef(185),
        vnicDynamicConPolicyRef(186),
        vnicL2If(187),
        vnicAFcIf(188),
        vnicEtherBaseIf(189),
        vnicAEtherIf(190),
        vnicFcOEIf(191),
        vnicFcIf(192),
        vnicEtherIf(193),
        vnicVmqConReq(194),
        vnicVmqConPolicy(195),
        vnicVmqConPolicyRef(196),
        adaptorUnit(197),
        adaptorHostIfProfile(198),
        adaptorHostEthIfProfile(199),
        adaptorHostFcIfProfile(200),
        adaptorProfileItem(201),
        adaptorQueueProfile(202),
        adaptorFcLogiProfile(203),
        adaptorEthQueueProfile(204),
        adaptorFcQueueProfile(205),
        adaptorEthWorkQueueProfile(206),
        adaptorEthArfsProfile(207),
        adaptorEthNVGREProfile(208),
        adaptorEthVxLANProfile(209),
        adaptorEthRoCEProfile(210),
        adaptorEthRecvQueueProfile(211),
        adaptorEthCompQueueProfile(212),
        adaptorEthInterruptProfile(213),
        adaptorRssProfile(214),
        adaptorRssHashProfile(215),
        adaptorTcpIpRssHashProfile(216),
        adaptorIpV4RssHashProfile(217),
        adaptorIpV6RssHashProfile(218),
        adaptorExtIpV6RssHashProfile(219),
        adaptorEthOffloadProfile(220),
        adaptorEthFailoverProfile(221),
        adaptorFcRecvQueueProfile(222),
        adaptorFcWorkQueueProfile(223),
        adaptorFcCdbWorkQueueProfile(224),
        adaptorFcPortFLogiProfile(225),
        adaptorFcPortPLogiProfile(226),
        adaptorFcPortProfile(227),
        adaptorFcErrorRecoveryProfile(228),
        adaptorFcInterruptProfile(229),
        adaptorHostIscsiIfProfile(230),
        adaptorProtocolProfile(231),
        adaptorFruCapProvider(232),
        adaptorCapSpec(233),
        adaptorIScsiCap(234),
        adaptorBehCap(235),
        adaptorHwAddrCap(236),
        adaptorHostIf(237),
        adaptorExtEthIf(238),
        adaptorExtIf(239),
        adaptorHostEthIf(240),
        adaptorHostFcIf(241),
        adaptorHostIfConnDef(242),
        adaptorUsnicConnDef(243),
        adaptorVlan(244),
        adaptorQual(245),
        adaptorCapQual(246),
        adaptorCapDef(247),
        memoryArray(248),
        memoryBufferUnit(249),
        memoryUnit(250),
        memoryQual(251),
        lsbootADef(252),
        lsbootDef(253),
        lsbootPolicy(254),
        lsbootBootSecurity(255),
        lsbootItem(256),
        lsbootCategory(257),
        lsbootStorage(258),
        lsbootSan(259),
        lsbootLan(260),
        lsbootIScsi(261),
        lsbootImagePath(262),
        lsbootLanImagePath(263),
        lsbootIScsiImagePath(264),
        lsbootVirtualMedia(265),
        lsbootImage(266),
        lsbootRemoteImage(267),
        lsbootSanImage(268),
        lsbootSanCatSanImage(269),
        lsbootLocalImage(270),
        lsbootLocalStorage(271),
        lsbootLocalMediaItem(272),
        lsbootDefaultLocalImage(273),
        lsbootUsbFlashStorageImage(274),
        lsbootLocalHddImage(275),
        lsbootUsbInternalImage(276),
        lsbootUsbExternalImage(277),
        lsbootSanImagePath(278),
        lsbootSanCatSanImagePath(279),
        lsVConAssign(280),
        lsServerExtension(281),
        vmNic(282),
        vmAdaptor(283),
        flowctrlDefinition(284),
        flowctrlItem(285),
        configImpact(286),
        iqnpoolTransportBlock(287),
        equipmentItem(288),
        equipmentStateful(289),
        equipmentStatefulBladeComp(290),
        equipmentPsu(291),
        equipmentFanModule(292),
        equipmentFan(293),
        equipmentXcvr(294),
        equipmentLocalDiskCapProvider(295),
        equipmentProcessorUnitCapProvider(296),
        equipmentBehCap(297),
        equipmentLocalDiskDef(298),
        etherPIo(299),
        etherServerIntFIo(300),
        storageADef(301),
        storageConnectionPolicy(302),
        storageTarget(303),
        storageFcTargetEp(304),
        storageVsanRef(305),
        storageConnectionDef(306),
        storageIniGroup(307),
        storageInitiator(308),
        storageQual(309),
        storageLocalDiskConfig(310),
        storageLocalDiskConfigPolicy(311),
        storageControllerBase(312),
        storageController(313),
        storageMezzFlashLife(314),
        storageFlexFlashController(315),
        storageDevice(316),
        storageUnit(317),
        storagePhysical(318),
        storageLogical(319),
        storageLocalDiskBase(320),
        storageLocalDisk(321),
        storageRaidBattery(322),
        storageFlexFlashCard(323),
        storageFlexFlashDrive(324),
        storageFlexFlashVirtualDrive(325),
        epqosDefinition(326),
        epqosItem(327),
        epqosEgress(328),
        qosDefinition(329),
        qosItem(330),
        mgmtCimcInterface(331),
        mgmtInterface(332),
        mgmtVnet(333),
        domainFeature(334),
        domainParameter(335),
        domainServerFeature(336),
        domainNetworkFeature(337),
        domainStorageFeature(338),
        domainEnvironmentFeature(339),
        domainServerParam(340),
        domainNetworkParam(341),
        domainStorageParam(342),
        domainEnvironmentParam(343),
        poolPoolMember(344),
        networkConn(345),
        networkEp(346),
        networkCIoEp(347),
        networkIfEp(348),
        networkPhysEp(349),
        networkVnetEp(350),
        pciCard(351),
        processorUnit(352),
        processorQual(353),
        iscsiAuthProfile(354),
        graphicsCard(355),
        graphicsController(356),
        biosVFeat(357),
        biosVProfile(358),
        biosVfIntelTurboBoostTech(359),
        biosVfInterleaveConfiguration(360),
        biosVfDramRefreshRate(361),
        biosVfEnhancedIntelSpeedStepTech(362),
        clitestTypeTest(363),
        biosVfIntelHyperThreadingTech(364),
        biosVfLocalX2Apic(365),
        biosVfCoreMultiProcessing(366),
        clitestTypeTestParent(367),
        clitestTypeTestChild(368),
        clitestTypeTest2(369),
        biosVfExecuteDisableBit(370),
        biosVfIntelVirtualizationTechnology(371),
        biosVfIntelVTForDirectedIO(372),
        biosVfDirectCacheAccess(373),
        biosVfSelectMemoryRASConfiguration(374),
        biosVfSparingMode(375),
        biosVfMirroringMode(376),
        biosVfNUMAOptimized(377),
        biosVfIntelEntrySASRAIDModule(378),
        biosVfOnboardSATAController(379),
        biosVfOnboardStorage(380),
        biosVfSerialPortAEnable(381),
        biosVfMaximumMemoryBelow4GB(382),
        biosVfMemoryMappedIOAbove4GB(383),
        biosVfSriovConfig(384),
        biosVfFrontPanelLockout(385),
        biosVfAssertNMIOnSERR(386),
        biosVfAssertNMIOnPERR(387),
        biosVfResumeOnACPowerLoss(388),
        biosVfConsoleRedirection(389),
        biosVfUEFIOSUseLegacyVideo(390),
        biosVfBootOptionRetry(391),
        biosVfUSBBootConfig(392),
        biosVfQuietBoot(393),
        biosVfPOSTErrorPause(394),
        biosVfProcessorC3Report(395),
        biosVfProcessorC6Report(396),
        biosVfProcessorCState(397),
        biosVfProcessorC7Report(398),
        biosVfProcessorC1E(399),
        biosVfOSBootWatchdogTimer(400),
        biosVfOSBootWatchdogTimerPolicy(401),
        biosVfOSBootWatchdogTimerTimeout(402),
        biosVfACPI10Support(403),
        biosVfLvDIMMSupport(404),
        biosVfOptionROMLoad(405),
        biosVfOptionROMEnable(406),
        biosVfPCISlotOptionROMEnable(407),
        biosVfPCISlotLinkSpeed(408),
        biosVfCPUPerformance(409),
        biosVfMaxVariableMTRRSetting(410),
        biosVfUSBSystemIdlePowerOptimizingSetting(411),
        biosVfUSBFrontPanelAccessLock(412),
        biosVfUCSMBootOrderRuleControl(413),
        biosVfUCSMBootModeControl(414),
        biosVfPackageCStateLimit(415),
        biosVfAllUSBDevices(416),
        biosVfUSBPortConfiguration(417),
        biosVfProcessorPrefetchConfig(418),
        biosVfScrubPolicies(419),
        biosVfVGAPriority(420),
        biosVfFRB2Timer(421),
        biosVfProcessorEnergyConfiguration(422),
        biosVfFrequencyFloorOverride(423),
        biosVfPSTATECoordination(424),
        biosVfDRAMClockThrottling(425),
        biosVfQPILinkFrequencySelect(426),
        biosVfTPMSupport(427),
        biosVfUSBConfiguration(428),
        biosVfAltitude(429),
        biosUnit(430),
        biosBOT(431),
        biosBootDevGrp(432),
        biosBootDev(433),
        solDef(434),
        solPolicy(435),
        fabricVnetEp(436),
        fabricAVsan(437),
        fabricEpVlan(438),
        fabricAVlan(439),
        fabricVlan(440),
        fabricVsan(441),
        fabricMulticastPolicy(442),
        fabricVnetReq(443),
        fabricVlanReq(444),
        fabricVnetGroupReq(445),
        fabricVlanGroupReq(446),
        fabricOrgVlanPolicy(447),
        fabricSan(448),
        fabricFcSan(449),
        fabricSanPc(450),
        fabricFcSanPc(451),
        fabricSanEp(452),
        fabricAFcoeSanEp(453),
        fabricFcoeSanPc(454),
        fabricFcoeSanEp(455),
        changeChangedObjectRef(456),
        fabricLacpPolicy(457),
        fabricVCon(458),
        fabricVConProfile(459),
        fabricLan(460),
        fabricEthLan(461),
        fabricCablingSw(462),
        fabricLanPc(463),
        fabricEthLanPc(464),
        fabricUdldPolicy(465),
        fabricEthLinkProfile(466),
        fabricEthLinkPolicy(467),
        fabricEthUdldPolicy(468),
        fabricEthCdpPolicy(469),
        fabricUdldLinkPolicy(470),
        fabricCdpLinkPolicy(471),
        fabricVnetEpSyncEp(472),
        fabricChangedObjectRef(473),
        fabricInternalDceSrv(474),
        fabricDceSrv(475),
        fabricExternalEstc(476),
        fabricEthEstc(477),
        fabricFcEstc(478),
        fabricEstcEp(479),
        fabricEstcPc(480),
        fabricEthEstcPc(481),
        fabricAFcoeEstcEp(482),
        fabricFcoeEstcEp(483),
        fabricExternalEp(484),
        fabricPIoEp(485),
        fabricInternal(486),
        fabricCloud(487),
        fabricFcEstcCloud(488),
        fabricCIoEp(489),
        fabricExternalPc(490),
        fabricSanCloud(491),
        fabricLanCloud(492),
        fabricCabling(493),
        fabricEthEstcCloud(494),
        fabricLinkPolicy(495),
        fabricDomain(496),
        fabricLanAccessMgr(497),
        fabricExternal(498),
        fabricEp(499),
        cimcvmediaItem(500),
        cimcvmediaMountConfig(501),
        cimcvmediaMountConfigDef(502),
        cimcvmediaMountConfigPolicy(503),
        cimcvmediaMountInfo(504),
        cimcvmediaActualMountList(505),
        cimcvmediaActualMountEntry(506),
        cimcvmediaExtMgmtRuleEntry(507),
        cimcvmediaConfigMountEntry(508),
        portIntFIo(509),
        portServerIntFIo(510),
        portSwitchIntFIo(511),
        portPhysSwitchIo(512),
        portPIo(513),
        fcPIo(514),
        nwctrlDefinition(515),
        gmetaPolicyMapElement(516),
        computeQual(517),
        computePoolable(518),
        computePooled(519),
        computeDefaults(520),
        computePlatform(521),
        computeInitConfigPolicy(522),
        computeAutoconfigPolicy(523),
        computeBladeInheritPolicy(524),
        computeScrubPolicy(525),
        computeKvmMgmtPolicy(526),
        computeMemoryConfigPolicy(527),
        computeMemoryConfiguration(528),
        computeBladeDiscPolicy(529),
        computeServerMgmtPolicy(530),
        computeChassisConnPolicy(531),
        computePsuDef(532),
        computePsuPolicy(533),
        computePsuControl(534),
        computeRackUnit(535),
        computeMbPowerStats(536),
        computeMbPowerStatsHist(537),
        computeMbTempStats(538),
        computeMbTempStatsHist(539),
        computeRackUnitMbTempStats(540),
        computeRackUnitMbTempStatsHist(541),
        computeIOHubEnvStats(542),
        computeIOHubEnvStatsHist(543),
        computePCIeFatalProtocolStats(544),
        computePCIeFatalReceiveStats(545),
        computePCIeFatalCompletionStats(546),
        computePCIeFatalStats(547),
        domainFeatureCont(548),
        domainServerFeatureCont(549),
        domainNetworkFeatureCont(550),
        domainStorageFeatureCont(551),
        domainEnvironmentFeatureCont(552),
        computeContainer(553),
        computeVirtualContainer(554),
        computeVirtual(555),
        computePartition(556),
        computeBlade(557),
        computeRtcBattery(558),
        computeBehCap(559),
        computePciCap(560),
        computePciSlotScanDef(561),
        computeMemoryUnitConstraintDef(562),
        computePhysicalAssocCtx(563),
        computeFwSyncAck(564),
        computeBoardController(565),
        computePnuOSImage(566),
        computeHealthLedSensorAlarm(567),
        firmwareCatalogue(568),
        firmwareUnit(569),
        firmwareRunning(570),
        firmwareUpdatable(571),
        firmwareBootUnit(572),
        firmwareBootDefinition(573),
        firmwareImage(574),
        firmwareInstallable(575),
        firmwareDistImage(576),
        firmwareDistributable(577),
        firmwareBundleInfo(578),
        firmwareCspVersion(579),
        firmwareCspAppList(580),
        firmwareDistCspBlackList(581),
        firmwareDownloader(582),
        firmwareCompItem(583),
        firmwareCompSource(584),
        firmwareCompTarget(585),
        firmwarePack(586),
        firmwareImageLock(587),
        firmwareInfraPack(588),
        firmwarePlatformPack(589),
        firmwarePackItem(590),
        firmwareComputePack(591),
        firmwareComputeHostPack(592),
        firmwareComputeMgmtPack(593),
        firmwareCatalogPack(594),
        firmwareType(595),
        firmwareConstraints(596),
        firmwareConstraint(597),
        firmwareDependency(598),
        firmwareSystem(599),
        firmwareInfra(600),
        firmwarePlatform(601),
        firmwareSupFirmware(602),
        firmwareHost(603),
        firmwareBlade(604),
        firmwareRack(605),
        firmwareStatus(606),
        firmwareSystemCompCheckResult(607),
        firmwareInstallImpact(608),
        firmwareHostPackModImpact(609),
        firmwareAck(610),
        firmwareUpgradeInfo(611),
        firmwareUpgradeDetail(612),
        firmwareBundleInfoDigest(613),
        firmwareUpgradeConstraint(614),
        firmwareAutoSyncPolicy(615),
        firmwareUcscInfo(616),
        firmwareCapProvider(617),
        firmwareABundleTypeCapProvider(618),
        firmwareBundleTypeCapProvider(619),
        firmwarePlatformBundleTypeCapProvider(620),
        firmwareBundleType(621),
        firmwareSpec(622),
        identIdentCtx(623),
        identSysInfo(624),
        identMetaVerse(625),
        identMetaSystem(626),
        identIdentRequest(627),
        identRequestEp(628),
        lldpAcquired(629),
        nhtestUniTest(630),
        powerEp(631),
        powerPrioWght(632),
        powerABudget(633),
        powerPlacement(634),
        powerGroupAdditionPolicy(635),
        powerBudget(636),
        powerProfiledPower(637),
        powerGroupMember(638),
        powerChassisMember(639),
        powerRackUnitMember(640),
        powerMgmtPolicy(641),
        powerGroupStats(642),
        powerGroupStatsHist(643),
        smSecSvc(644),
        smSlot(645),
        smMonitor(646),
        smHeartbeat(647),
        smHeartbeatConfig(648),
        smDiskFileSystem(649),
        smLDTemplate(650),
        smTemplateApp(651),
        smApp(652),
        smPortRequirement(653),
        smPortSubType(654),
        smAppInstance(655),
        smResource(656),
        smLogicalDevice(657),
        smMgmtBootstrap(658),
        smIP(659),
        smIPV6(660),
        smExternalPortLink(661),
        smMac(662),
        smSystemMac(663),
        smUserMac(664),
        smClusterBootstrap(665),
        smKey(666),
        smEncryptedKey(667),
        smNetMgmtBootstrapValue(668),
        smNetMgmtBootstrapKeyLimits(669),
        smNetMgmtBootstrapKeyEnumValue(670),
        smAppAttribute(671),
        smAppAttributeValue(672),
        swSspMonDomain(673),
        swSspLanMon(674),
        swSspEthLanMon(675),
        swSspMon(676),
        swSspEthMon(677),
        swSspEthMonSrcPhyEp(678),
        swSspEthMonSrcAppLinksEp(679),
        swSspEthMonSrcAppEp(680),
        swSspEthMonFilterEp(681),
        swEnvStats(682),
        swEnvStatsHist(683),
        swCardEnvStats(684),
        swCardEnvStatsHist(685),
        swSystemStats(686),
        swSystemStatsHist(687),
        swDomain(688),
        swPIoEp(689),
        swPortBreakout(690),
        swSubGroup(691),
        swCIoEp(692),
        swBorderDomain(693),
        swBorderEp(694),
        swBorderPc(695),
        swLanBorder(696),
        swLanEp(697),
        swLanPc(698),
        swPhys(699),
        swExtUtility(700),
        swPhysEtherEp(701),
        swPhysFcEp(702),
        swEthLanBorder(703),
        swEthLanEp(704),
        swMonSrcEp(705),
        swEthMonSrcEp(706),
        swFcMonSrcEp(707),
        swEthLanPc(708),
        swVlan(709),
        swVlanGroup(710),
        swVlanRef(711),
        swUlan(712),
        swAccessDomain(713),
        swAccessEp(714),
        swEstcEp(715),
        swFcEstcEp(716),
        swEthEstcEp(717),
        swTargetEp(718),
        swEthTargetEp(719),
        swEthEstcPc(720),
        swFcoeEstcEp(721),
        swUtilityDomain(722),
        swVlanPortNs(723),
        swMonDomain(724),
        swLanMon(725),
        swSanMon(726),
        swEthLanMon(727),
        swFcSanMon(728),
        swMon(729),
        swEthMon(730),
        swFcMon(731),
        swMonDestEp(732),
        swEthMonDestEp(733),
        swFcMonDestEp(734),
        swVlanPortNsOverride(735),
        swEthLanFlowMon(736),
        swFlowMonitor(737),
        swEthLanFlowMonitor(738),
        swNetflowMonitor(739),
        swNetflowMonitorRef(740),
        swFlowRecordDef(741),
        swEthLanFlowRecordDef(742),
        swNetflowRecordDef(743),
        swFlowMonExporter(744),
        swEthLanFlowMonExporter(745),
        swNetflowExporter(746),
        swEthFlowMonSession(747),
        swNetflowMonSession(748),
        swNFExporterRef(749),
        swIpRoute(750),
        swVirtL3Intf(751),
        swSanBorder(752),
        swSanEp(753),
        swFcSanBorder(754),
        swSanPc(755),
        swFcSanEp(756),
        swFcoeSanEp(757),
        swFcSanPc(758),
        swFcoeSanPc(759),
        swVsan(760),
        swFcZoneSet(761),
        swFcServerZoneGroup(762),
        swZoneInitiatorMember(763),
        swFcZone(764),
        swFcZoneMember(765),
        swZoneTargetMember(766),
        swFabricZoneNs(767),
        swFabricZoneNsOverride(768),
        swCmclan(769),
        dcxVifEp(770),
        dcxFcoeVifEp(771),
        dcxVIf(772),
        dcxUniverse(773),
        dcxNs(774),
        vnicTempl(775),
        vnicSanConnTempl(776),
        vnicLanConnTempl(777),
        vnicFcGroupTempl(778),
        vnicProfileSet(779),
        vnicProfile(780),
        vnicVProfileAlias(781),
        vnicProfileAlias(782),
        vnicOProfileAlias(783),
        vnicInternalProfile(784),
        vnicDynamicCon(785),
        vnicDynamicIdUniverse(786),
        vnicDynamicProvider(787),
        vnicDynamicProviderEp(788),
        vnicRackServerDiscoveryProfile(789),
        vnicProfileRef(790),
        vnicVnic(791),
        vnicEtherBase(792),
        vnicMacHistory(793),
        vnicWwpnHistory(794),
        vnicWwnnHistory(795),
        vnicIqnHistory(796),
        vnicIpV4History(797),
        vnicIpV6History(798),
        vnicEther(799),
        vnicFcBase(800),
        vnicFc(801),
        vnicIScsiBase(802),
        vnicIScsiLCP(803),
        vnicIScsi(804),
        vnicIpc(805),
        vnicScsi(806),
        vnicAGroup(807),
        vnicFcGroupDef(808),
        vnicL2Lif(809),
        vnicEthLif(810),
        vnicFcLif(811),
        vnicLifVlan(812),
        vnicLifVsan(813),
        vnicAIpcIf(814),
        vnicAScsiIf(815),
        vnicIpcIf(816),
        vnicScsiIf(817),
        macpoolPool(818),
        macpoolPooled(819),
        macpoolFormat(820),
        macpoolBlock(821),
        macpoolAddr(822),
        macpoolPoolable(823),
        macpoolUniverse(824),
        callhomeItem(825),
        callhomeEp(826),
        callhomeSource(827),
        callhomeSmtp(828),
        callhomeAnonymousReporting(829),
        callhomePeriodicSystemInventory(830),
        callhomeProfile(831),
        callhomeDest(832),
        callhomePolicy(833),
        callhomeHttpProxy(834),
        callhomeTestAlert(835),
        adaptorUnitExtn(836),
        adaptorHostPort(837),
        adaptorVsan(838),
        adaptorFcOEIf(839),
        adaptorUnitAssocCtx(840),
        adaptorCIoEp(841),
        adaptorExternalPc(842),
        adaptorExtIfPc(843),
        adaptorExtEthIfPc(844),
        adaptorPIoEp(845),
        adaptorExternalEp(846),
        adaptorExtIfEp(847),
        adaptorExtEthIfPcEp(848),
        adaptorHostServiceEthIf(849),
        adaptorHostIscsiIf(850),
        adaptorIscsiTargetIf(851),
        adaptorIscsiProt(852),
        adaptorIscsiAuth(853),
        adaptorEthPortStats(854),
        adaptorEthPortStatsHist(855),
        adaptorEthPortBySizeSmallStats(856),
        adaptorEthPortBySizeSmallStatsHist(857),
        adaptorEthPortBySizeLargeStats(858),
        adaptorEthPortBySizeLargeStatsHist(859),
        adaptorEthPortOutsizedStats(860),
        adaptorEthPortOutsizedStatsHist(861),
        adaptorEthPortMcastStats(862),
        adaptorEthPortMcastStatsHist(863),
        adaptorEthPortErrStats(864),
        adaptorEthPortErrStatsHist(865),
        adaptorFcPortStats(866),
        adaptorFcPortStatsHist(867),
        adaptorVnicStats(868),
        adaptorVnicStatsHist(869),
        adaptorFcIfFC4Stats(870),
        adaptorFcIfFC4StatsHist(871),
        adaptorMenloBaseErrorStats(872),
        adaptorMenloBaseErrorStatsHist(873),
        adaptorMenloMcpuStats(874),
        adaptorMenloMcpuStatsHist(875),
        adaptorMenloMcpuErrorStats(876),
        adaptorMenloMcpuErrorStatsHist(877),
        adaptorMenloEthStats(878),
        adaptorMenloEthStatsHist(879),
        adaptorMenloEthErrorStats(880),
        adaptorMenloEthErrorStatsHist(881),
        adaptorMenloFcStats(882),
        adaptorMenloFcStatsHist(883),
        adaptorMenloFcErrorStats(884),
        adaptorMenloFcErrorStatsHist(885),
        adaptorMenloQStats(886),
        adaptorMenloQStatsHist(887),
        adaptorMenloQErrorStats(888),
        adaptorMenloQErrorStatsHist(889),
        adaptorMenloNetEgStats(890),
        adaptorMenloNetEgStatsHist(891),
        adaptorMenloNetInStats(892),
        adaptorMenloNetInStatsHist(893),
        adaptorMenloHostPortStats(894),
        adaptorMenloHostPortStatsHist(895),
        adaptorMenloDcePortStats(896),
        adaptorMenloDcePortStatsHist(897),
        adaptorEtherIfStats(898),
        adaptorEtherIfStatsHist(899),
        adaptorFcIfFrameStats(900),
        adaptorFcIfFrameStatsHist(901),
        adaptorFcIfEventStats(902),
        adaptorFcIfEventStatsHist(903),
        adaptorFwCapProvider(904),
        adaptorFruCapRef(905),
        adaptorLldpCap(906),
        adaptorLanCap(907),
        adaptorSanCap(908),
        adaptorMgmtCap(909),
        adaptorNwMgmtCap(910),
        adaptorHostMgmtCap(911),
        adaptorUplinkHwAddrCap(912),
        adaptorHostethHwAddrCap(913),
        adaptorHostfcHwAddrCap(914),
        adaptorFamilyTypeDef(915),
        adaptorDiagCap(916),
        adaptorHostPortCap(917),
        licenseEp(918),
        licenseFeature(919),
        licenseServerHostId(920),
        licenseFile(921),
        licenseSource(922),
        licenseContents(923),
        licenseFeatureLine(924),
        licenseInstance(925),
        licenseSourceFile(926),
        licenseProp(927),
        licenseDownloader(928),
        licenseSmartConfig(929),
        licenseTarget(930),
        licenseCapProvider(931),
        licenseFeatureCapProvider(932),
        memoryRuntime(933),
        memoryRuntimeHist(934),
        memoryArrayEnvStats(935),
        memoryArrayEnvStatsHist(936),
        memoryBufferUnitEnvStats(937),
        memoryBufferUnitEnvStatsHist(938),
        memoryUnitEnvStats(939),
        memoryUnitEnvStatsHist(940),
        memoryErrorStats(941),
        imgprovPolicy(942),
        imgprovTarget(943),
        imgsecPolicy(944),
        imgsecKey(945),
        hostimgPolicy(946),
        hostimgTarget(947),
        lsmaintMaintPolicy(948),
        lsmaintAck(949),
        lsServer(950),
        lsIssues(951),
        lsUuidHistory(952),
        lsPower(953),
        lsComputeBinding(954),
        lsBinding(955),
        lsRequirement(956),
        lsAgentPolicy(957),
        lsServerAssocCtx(958),
        lsFcLocale(959),
        lsFcZoneGroup(960),
        lsZoneInitiatorMember(961),
        lsFcZone(962),
        lsFcZoneMember(963),
        lsZoneTargetMember(964),
        lsVersionBeh(965),
        lsTier(966),
        extvmmNetworkSets(967),
        extvmmVMNetworkSets(968),
        extvmmFabricNetwork(969),
        extvmmFabricNetworkDefinition(970),
        extvmmVMNetworkDefinition(971),
        extvmmVMNetwork(972),
        extvmmVMNDRef(973),
        extvmmUpLinkPP(974),
        extvmmFNDReference(975),
        vmLifeCyclePolicy(976),
        vmCont(977),
        vmDirCont(978),
        vmDCOrg(979),
        vmDC(980),
        vmOrg(981),
        vmSwitch(982),
        vmVnicProfInst(983),
        vmVnicProfCl(984),
        extvmmEp(985),
        extvmmMasterExtKey(986),
        extvmmKeyInst(987),
        extvmmKeyStore(988),
        extvmmKeyRing(989),
        extvmmSwitchSet(990),
        extvmmProvider(991),
        extvmmSwitchDelTask(992),
        vmEp(993),
        vmClientContainer(994),
        vmVirtual(995),
        vmComputeEp(996),
        vmHv(997),
        vmInstance(998),
        vmHba(999),
        vmVlan(1000),
        vmVsan(1001),
        vmVif(1002),
        configImpactResponse(1003),
        configManagedEpImpactResponse(1004),
        configSorter(1005),
        iqnpoolPool(1006),
        iqnpoolPooled(1007),
        iqnpoolAbsBlock(1008),
        iqnpoolBlock(1009),
        iqnpoolAddr(1010),
        iqnpoolFormat(1011),
        iqnpoolPoolable(1012),
        iqnpoolUniverse(1013),
        rmetaClass(1014),
        rmetaProp(1015),
        rmetaRnComponent(1016),
        ipDnsSuffix(1017),
        ipIPv4WinsServer(1018),
        observeObservedCont(1019),
        observeObserved(1020),
        observeFilter(1021),
        featureDefinition(1022),
        featureProvider(1023),
        featureBaseRef(1024),
        featureDefinitionRef(1025),
        featureDefinitionInstance(1026),
        featureFruCapProviderRef(1027),
        featureFruCapProviderInstance(1028),
        featureContextEp(1029),
        featureProviderInstance(1030),
        computeNpu(1031),
        equipmentHolder(1032),
        equipmentStatefulChComp(1033),
        equipmentEnvSensor(1034),
        equipmentCard(1035),
        equipmentIOCardBase(1036),
        equipmentSwitchCard(1037),
        equipmentBeaconLed(1038),
        equipmentChassis(1039),
        equipmentRommon(1040),
        equipmentFpga(1041),
        equipmentIOCard(1042),
        equipmentSwitchIOCard(1043),
        equipmentLed(1044),
        equipmentIndicatorLed(1045),
        equipmentLocatorLed(1046),
        equipmentHealthLed(1047),
        equipmentAssocCtx(1048),
        equipmentFex(1049),
        equipmentHwCapProvider(1050),
        equipmentPicture(1051),
        equipmentFruCapProvider(1052),
        equipmentIntegratedComponentCapProvider(1053),
        equipmentHolderCapProvider(1054),
        equipmentSwitchCapProvider(1055),
        equipmentSwitchIOCardCapProvider(1056),
        equipmentSwitchCap(1057),
        equipmentPortCap(1058),
        equipmentBreakOutCapProvider(1059),
        equipmentFailToWireCapProvider(1060),
        equipmentFailToWirePortDef(1061),
        equipmentUnifiedPortCapProvider(1062),
        equipmentMaxPortSpeedCapProvider(1063),
        equipmentServerPortCapProvider(1064),
        equipmentBeaconCapProvider(1065),
        equipmentMgmtCapProvider(1066),
        equipmentCatalogCapProvider(1067),
        equipmentMgmtExtCapProvider(1068),
        equipmentDbgPluginCapProvider(1069),
        equipmentChassisCapProvider(1070),
        equipmentBladeCapProvider(1071),
        equipmentRackUnitCapProvider(1072),
        equipmentAdvancedBootOrder(1073),
        equipmentCimcVmedia(1074),
        equipmentSecureBoot(1075),
        equipmentPowerCapDef(1076),
        equipmentBladeAGLibrary(1077),
        equipmentBaseBoardCapProvider(1078),
        equipmentTpmCapProvider(1079),
        equipmentBladeBiosCapProvider(1080),
        equipmentGraphicsCardCapProvider(1081),
        equipmentGraphicsCardCapRef(1082),
        equipmentLocalDiskControllerCapProvider(1083),
        equipmentLocalDiskControllerCapRef(1084),
        equipmentHostIfCapProvider(1085),
        equipmentMemoryUnitCapProvider(1086),
        equipmentIOCardCapProvider(1087),
        equipmentFexCapProvider(1088),
        equipmentPsuCapProvider(1089),
        equipmentFanModuleCapProvider(1090),
        equipmentGemCapProvider(1091),
        equipmentGemPortCap(1092),
        equipmentDiscoveryCap(1093),
        equipmentSecureController(1094),
        equipmentTpm(1095),
        equipmentManufacturingDef(1096),
        equipmentRackFanModuleDef(1097),
        equipmentPhysicalDef(1098),
        equipmentInbandMgmtCap(1099),
        equipmentKvmMgmtCap(1100),
        equipmentBiosDef(1101),
        equipmentDimmMapping(1102),
        equipmentDimmEntry(1103),
        equipmentServiceDef(1104),
        equipmentAdaptorDef(1105),
        equipmentPciDef(1106),
        equipmentProcessorUnitDef(1107),
        equipmentRaidDef(1108),
        equipmentFlashLife(1109),
        equipmentHDDFaultMonDef(1110),
        equipmentPortGroupDef(1111),
        equipmentFanModuleDef(1112),
        equipmentPsuDef(1113),
        equipmentPortGroupAggregationDef(1114),
        equipmentPortGroupSwComplexDef(1115),
        equipmentPortSwComplexRef(1116),
        equipmentBoardControllerDef(1117),
        equipmentFirmwareConstraint(1118),
        equipmentVersionConstraint(1119),
        equipmentBladeAggregationCapRef(1120),
        equipmentPhysDevicesPerBoard(1121),
        equipmentDowngradeConstraint(1122),
        equipmentLocalDiskControllerDef(1123),
        equipmentMemoryUnitDiscoveryModifierDef(1124),
        equipmentSlotArrayRef(1125),
        equipmentSlotArray(1126),
        equipmentBladeConnDef(1127),
        equipmentBladeIOMConnDef(1128),
        equipmentBladeSwitchConnDef(1129),
        equipmentAdaptorConnDef(1130),
        equipmentIOCardTypeDef(1131),
        equipmentSwitchTypeDef(1132),
        equipmentServerFeatureCap(1133),
        equipmentUuidFeatureCap(1134),
        equipmentChassisStats(1135),
        equipmentChassisStatsHist(1136),
        equipmentIOCardStats(1137),
        equipmentIOCardStatsHist(1138),
        equipmentPsuStats(1139),
        equipmentPsuStatsHist(1140),
        equipmentPsuInputStats(1141),
        equipmentPsuInputStatsHist(1142),
        equipmentPsuOutputStats(1143),
        equipmentPsuOutputStatsHist(1144),
        equipmentFanModuleStats(1145),
        equipmentFanModuleStatsHist(1146),
        equipmentFanStats(1147),
        equipmentFanStatsHist(1148),
        equipmentFexEnvStats(1149),
        equipmentFexEnvStatsHist(1150),
        equipmentFexPowerSummary(1151),
        equipmentFexPowerSummaryHist(1152),
        equipmentFexPsuInputStats(1153),
        equipmentFexPsuInputStatsHist(1154),
        equipmentRackUnitPsuStats(1155),
        equipmentRackUnitPsuStatsHist(1156),
        equipmentNetworkElementFanStats(1157),
        equipmentNetworkElementFanStatsHist(1158),
        equipmentRackUnitFanStats(1159),
        equipmentRackUnitFanStatsHist(1160),
        sdSysSecSvc(1161),
        sdSlot(1162),
        sdAppInstance(1163),
        sdResource(1164),
        sdLogicalDevice(1165),
        sdExternalPortLink(1166),
        sdMac(1167),
        sdSystemMac(1168),
        sdUserMac(1169),
        sdClusterBootstrap(1170),
        sdLdu(1171),
        sdLink(1172),
        sdExternalLduLink(1173),
        sdAppLduLink(1174),
        sdNPPortCfg(1175),
        sdNPInterfaceCfg(1176),
        sdNPPortBundleCfg(1177),
        sdMgmtBootstrap(1178),
        sdIP(1179),
        sdIPV6(1180),
        sdKey(1181),
        sdEncryptedKey(1182),
        sdAppAttribute(1183),
        sdAppAttributeCtrl(1184),
        sdMgmtInfo(1185),
        sdNetMgmtBootstrap(1186),
        sdInternalMgmtBootstrap(1187),
        sdUpgradeTask(1188),
        etherPortChanIdElem(1189),
        etherPortChanIdUniverse(1190),
        etherPIoEndPoint(1191),
        etherSwitchIntFIo(1192),
        etherConfig(1193),
        etherIfConfig(1194),
        etherSwIfConfig(1195),
        etherNicIfConfig(1196),
        etherCIoEp(1197),
        etherPc(1198),
        etherInternalPc(1199),
        etherExternalPc(1200),
        etherServerIntFIoPc(1201),
        etherSwitchIntFIoPc(1202),
        etherPIoEp(1203),
        etherExternalEp(1204),
        etherIntFIoEp(1205),
        etherServerIntFIoPcEp(1206),
        etherSwitchIntFIoPcEp(1207),
        etherFailToWire(1208),
        etherFtwPortPair(1209),
        etherTxStats(1210),
        etherTxStatsHist(1211),
        etherRxStats(1212),
        etherRxStatsHist(1213),
        etherErrStats(1214),
        etherErrStatsHist(1215),
        etherNiErrStats(1216),
        etherNiErrStatsHist(1217),
        etherLossStats(1218),
        etherLossStatsHist(1219),
        etherPauseStats(1220),
        etherPauseStatsHist(1221),
        etherFcoeInterfaceStats(1222),
        etherFcoeInterfaceStatsHist(1223),
        extpolConnectorContainer(1224),
        extpolEp(1225),
        extpolConnector(1226),
        extpolSvc(1227),
        extpolRegistry(1228),
        extpolProviderCont(1229),
        extpolProvider(1230),
        extpolControllerCont(1231),
        extpolController(1232),
        extpolClientCont(1233),
        extpolClient(1234),
        extpolSystemContext(1235),
        storageEp(1236),
        storageNodeEp(1237),
        storageEpUser(1238),
        storageAuthKey(1239),
        storageTransportIf(1240),
        storageTargetIf(1241),
        storageIScsiTargetIf(1242),
        storageFcTargetIf(1243),
        storageL2If(1244),
        storageFcIf(1245),
        storageEtherIf(1246),
        storageSystem(1247),
        ipIpV4Addr(1248),
        ipIPv4Dns(1249),
        ipServiceIf(1250),
        ipIpV4StaticAddr(1251),
        initiatorEp(1252),
        initiatorRequestorEp(1253),
        initiatorGroupEp(1254),
        initiatorInitiatorEp(1255),
        initiatorIScsiInitiatorEp(1256),
        initiatorFcInitiatorEp(1257),
        initiatorStoreEp(1258),
        initiatorUnitEp(1259),
        initiatorLunEp(1260),
        initiatorRequestorGrpEp(1261),
        initiatorMemberEp(1262),
        storageOperation(1263),
        storageDomainEp(1264),
        storageDrive(1265),
        storageTransportableFlashModule(1266),
        storageLocalLun(1267),
        storageVirtualDrive(1268),
        storageLocalDiskSlotEp(1269),
        storageEnclosure(1270),
        storageLunDisk(1271),
        storageItem(1272),
        storageLocalDiskConfigDef(1273),
        storageLocalDiskPartition(1274),
        sysfileEp(1275),
        sysfileRepository(1276),
        sysfileExporter(1277),
        sysfileImporter(1278),
        sysfileMutation(1279),
        sysfileInstance(1280),
        sysfileDigest(1281),
        ippoolPool(1282),
        ippoolPooled(1283),
        ippoolIpV6Pooled(1284),
        ippoolBlock(1285),
        ippoolIpV6Block(1286),
        ippoolAddr(1287),
        ippoolIpV6Addr(1288),
        ippoolPoolable(1289),
        ippoolUniverse(1290),
        applicationCatalogue(1291),
        applicationDownloader(1292),
        pkiEp(1293),
        pkiItem(1294),
        pkiCertReq(1295),
        pkiKeyRing(1296),
        pkiTP(1297),
        aaaDefinition(1298),
        aaaItem(1299),
        commDefinition(1300),
        commItem(1301),
        pkiDefinition(1302),
        aaaRealm(1303),
        aaaConfig(1304),
        aaaAuthMethod(1305),
        aaaDefaultAuth(1306),
        aaaConsoleAuth(1307),
        aaaDomainAuth(1308),
        aaaDomain(1309),
        aaaAuthRealm(1310),
        aaaEp(1311),
        aaaRadiusEp(1312),
        aaaLdapEp(1313),
        aaaTacacsPlusEp(1314),
        aaaProvider(1315),
        aaaRadiusProvider(1316),
        aaaLdapProvider(1317),
        aaaTacacsPlusProvider(1318),
        aaaLdapGroupRule(1319),
        aaaUserGroup(1320),
        aaaLdapGroup(1321),
        aaaProviderGroup(1322),
        aaaProviderRef(1323),
        aaaUserEp(1324),
        aaaSystemUser(1325),
        aaaEpAuthProfile(1326),
        aaaUserLogin(1327),
        aaaBanner(1328),
        aaaPreLoginBanner(1329),
        aaaShellLogin(1330),
        aaaWebLogin(1331),
        aaaEpLogin(1332),
        aaaRemoteUser(1333),
        aaaEpUser(1334),
        aaaUser(1335),
        aaaSshAuth(1336),
        aaaUserRole(1337),
        aaaRole(1338),
        aaaUserLocale(1339),
        aaaLocale(1340),
        aaaOrg(1341),
        aaaSession(1342),
        aaaExtMgmtCutThruTkn(1343),
        aaaPwdProfile(1344),
        aaaUserData(1345),
        aaaCimcSession(1346),
        aaaSessionInfoTable(1347),
        aaaSessionInfo(1348),
        commSvcEp(1349),
        commSvcChannel(1350),
        commWebChannel(1351),
        commEvtChannel(1352),
        commSvc(1353),
        commWeb(1354),
        commHttps(1355),
        commWsman(1356),
        commShell(1357),
        commTelnet(1358),
        commSsh(1359),
        commSnmp(1360),
        commSnmpUser(1361),
        commDateTime(1362),
        commSnmpTrap(1363),
        commDns(1364),
        commClient(1365),
        commClientItem(1366),
        commNtpProvider(1367),
        commDnsProvider(1368),
        commSyslog(1369),
        commSyslogConsole(1370),
        commSyslogMonitor(1371),
        commSyslogFile(1372),
        commSyslogClient(1373),
        commSyslogSource(1374),
        commSvcLimits(1375),
        commShellSvcLimits(1376),
        commWebSvcLimits(1377),
        sysdebugEp(1378),
        sysdebugRepository(1379),
        sysdebugCoreFileRepository(1380),
        sysdebugExporter(1381),
        sysdebugCoreFileExportTarget(1382),
        sysdebugLogExportStatus(1383),
        sysdebugLogExportPolicy(1384),
        sysdebugAutoCoreFileExportTarget(1385),
        sysdebugManualCoreFileExportTarget(1386),
        sysdebugFile(1387),
        sysdebugCore(1388),
        sysdebugTechSupFileRepository(1389),
        sysdebugTechSupport(1390),
        sysdebugTechSupportCmdOpt(1391),
        sysdebugLogControlEp(1392),
        sysdebugLogControlDomain(1393),
        sysdebugLogControlModule(1394),
        sysdebugLogControlDestinationFile(1395),
        sysdebugLogControlDestinationSyslog(1396),
        sysdebugMEpLog(1397),
        sysdebugMEpLogDef(1398),
        sysdebugMEpLogPolicy(1399),
        sysdebugLogBehavior(1400),
        sysdebugBackupBehavior(1401),
        procManager(1402),
        procProcCounts(1403),
        procTxCounts(1404),
        procStimulusCounts(1405),
        procPrtCounts(1406),
        procProcs(1407),
        procPrt(1408),
        procDoer(1409),
        procSvc(1410),
        diagSrvCapProvider(1411),
        diagCtrl(1412),
        diagRslt(1413),
        diagSrvCtrl(1414),
        diagRunPolicy(1415),
        diagTest(1416),
        diagBladeTest(1417),
        diagNetworkTest(1418),
        versionEp(1419),
        versionVersion(1420),
        versionApplication(1421),
        epqosDefinitionDelTask(1422),
        qosclassDefinition(1423),
        qosclassItem(1424),
        qosclassFc(1425),
        qosclassEth(1426),
        qosclassEthBE(1427),
        qosclassEthClassified(1428),
        extmgmtIf(1429),
        extmgmtIfMonPolicy(1430),
        extmgmtMiiStatus(1431),
        extmgmtGatewayPing(1432),
        extmgmtNdiscTargets(1433),
        extmgmtArpTargets(1434),
        poolUniverse(1435),
        poolElement(1436),
        poolPoolable(1437),
        poolPool(1438),
        networkElement(1439),
        networkOperLevel(1440),
        networkLanNeighbors(1441),
        networkANeighborEntry(1442),
        networkLanNeighborEntry(1443),
        networkSanNeighbors(1444),
        networkSanNeighborEntry(1445),
        networkIfStats(1446),
        networkDomainEp(1447),
        networkPIoEp(1448),
        fcpoolInitiators(1449),
        fcpoolInitiator(1450),
        fcpoolInitiatorEp(1451),
        fcpoolBlock(1452),
        fcpoolFormat(1453),
        fcpoolAddr(1454),
        fcpoolPoolable(1455),
        fcpoolUniverse(1456),
        fcpoolBootTarget(1457),
        nhTableHolder(1458),
        nhLinkTable(1459),
        nhEcmpIdent(1460),
        nhIpmcIdent(1461),
        nhLdevItem(1462),
        nhInstItem(1463),
        nhLinks(1464),
        nhEndPoint(1465),
        nhPortCfg(1466),
        nhMacVlanCfg(1467),
        nhSystemMac(1468),
        nhUserMac(1469),
        trigAck(1470),
        trigConfAck(1471),
        trigResAck(1472),
        trigInst(1473),
        trigWindow(1474),
        trigToken(1475),
        trigClientToken(1476),
        trigBaseSched(1477),
        trigSched(1478),
        trigLocalSched(1479),
        trigSchedWindow(1480),
        trigBaseAbsWindow(1481),
        trigAbsWindow(1482),
        trigLocalAbsWindow(1483),
        trigRecurrWindow(1484),
        trigMeta(1485),
        trigTriggered(1486),
        trigTriggerable(1487),
        trigTest(1488),
        dhcpInst(1489),
        dhcpLease(1490),
        dhcpAcquired(1491),
        osInstance(1492),
        osController(1493),
        osAgent(1494),
        pciEquipSlot(1495),
        pciUnit(1496),
        uuidpoolPool(1497),
        uuidpoolPooled(1498),
        uuidpoolBlock(1499),
        uuidpoolAddr(1500),
        uuidpoolFormat(1501),
        uuidpoolPoolable(1502),
        uuidpoolUniverse(1503),
        processorComponent(1504),
        processorCore(1505),
        processorThread(1506),
        processorRuntime(1507),
        processorRuntimeHist(1508),
        processorEnvStats(1509),
        processorEnvStatsHist(1510),
        processorErrorStats(1511),
        processorUnitAssocCtx(1512),
        biosSettings(1513),
        biosARef(1514),
        biosRef(1515),
        biosFeatureRef(1516),
        biosParameterRef(1517),
        biosSettingRef(1518),
        biosVIdentityParams(1519),
        syntheticDirectory(1520),
        syntheticFile(1521),
        syntheticFsObj(1522),
        syntheticTime(1523),
        syntheticFileSystem(1524),
        policyObject(1525),
        policyHolder(1526),
        policyBinding(1527),
        policyDefinition(1528),
        policyItem(1529),
        orgOrg(1530),
        orgSourceMask(1531),
        capabilityCatalogue(1532),
        capabilityProvider(1533),
        capabilityDef(1534),
        capabilityItem(1535),
        capabilityFeatureLimits(1536),
        capabilitySystemLimits(1537),
        capabilityNetworkLimits(1538),
        capabilityStorageLimits(1539),
        capabilityEp(1540),
        capabilityMgmtExtension(1541),
        capabilityUpdater(1542),
        capabilityUpdate(1543),
        solConfig(1544),
        solIf(1545),
        fabricLanMonCloud(1546),
        fabricSanMonCloud(1547),
        fabricEthMonLan(1548),
        fabricFcMonSan(1549),
        fabricMon(1550),
        fabricEthMon(1551),
        fabricFcMon(1552),
        fabricMonDestEp(1553),
        fabricEthMonDestEp(1554),
        fabricFcMonDestEp(1555),
        fabricMonSrcEp(1556),
        fabricEthMonSrcEp(1557),
        fabricFcMonSrcEp(1558),
        fabricMonSrcRef(1559),
        fabricEthMonSrcRef(1560),
        fabricFcMonSrcRef(1561),
        fabricMonSrcFiltEp(1562),
        fabricEthMonFiltEp(1563),
        fabricFcMonFiltEp(1564),
        fabricMonFiltRef(1565),
        fabricEthMonFiltRef(1566),
        fabricFcMonFiltRef(1567),
        fabricEpVsan(1568),
        fabricVsanEp(1569),
        fabricVsanMembership(1570),
        fabricVlanEp(1571),
        fabricVnetPermit(1572),
        fabricVlanPermit(1573),
        fabricAFcSanEp(1574),
        fabricFcSanEp(1575),
        fabricFcSanPcEp(1576),
        fabricFcoeSanPcEp(1577),
        fabricFcVsanPortEp(1578),
        fabricFcoeVsanPortEp(1579),
        fabricFcVsanPc(1580),
        fabricFcoeVsanPc(1581),
        fabricSanPinGroup(1582),
        fabricSanPinTarget(1583),
        fabricNetGroup(1584),
        fabricPooledVlan(1585),
        fabricPoolableVlan(1586),
        ipIpV4StaticTargetAddr(1587),
        fabricNetflowIPv4Addr(1588),
        fabricFlowMon(1589),
        fabricLanFlowMon(1590),
        fabricEthLanFlowMon(1591),
        fabricNetflowMonSession(1592),
        fabricFlowMonSrcEp(1593),
        fabricLanFlowMonSrcEp(1594),
        fabricEthLanFlowMonSrcEp(1595),
        fabricNetflowMonSrcEp(1596),
        fabricFlowMonSrcRef(1597),
        fabricEthFlowMonSrcRef(1598),
        fabricNetflowMonSrcRef(1599),
        fabricFlowMonExporterProfile(1600),
        fabricFlowMonDefinition(1601),
        fabricFlowMonItem(1602),
        fabricFlowMonitoringCategory(1603),
        fabricEthLanFlowMonitoring(1604),
        fabricEthFlowMonLan(1605),
        fabricFlowMonitor(1606),
        fabricLanFlowMonitor(1607),
        fabricEthLanFlowMonitor(1608),
        fabricNetflowMonitor(1609),
        fabricNetflowMonitorRef(1610),
        fabricFlowMonCollector(1611),
        fabricLanFlowMonCollector(1612),
        fabricEthLanFlowMonCollector(1613),
        fabricNetflowCollector(1614),
        fabricFlowMonExporter(1615),
        fabricLanFlowMonExporter(1616),
        fabricEthLanFlowMonExporter(1617),
        fabricNetflowMonExporter(1618),
        fabricNetflowMonExporterRef(1619),
        fabricNetflowTimeoutPolicy(1620),
        fabricLocale(1621),
        fabricPath(1622),
        fabricPathEp(1623),
        fabricPathConn(1624),
        fabricLanEp(1625),
        fabricAEthLanEp(1626),
        fabricEthVlanPortEp(1627),
        fabricEthLanEp(1628),
        fabricEthLanPcEp(1629),
        fabricLanPinGroup(1630),
        fabricLanPinTarget(1631),
        fabricSwChEp(1632),
        fabricSwChPhEp(1633),
        fabricComputeEp(1634),
        fabricChassisEp(1635),
        fabricComputeSlotEp(1636),
        fabricIf(1637),
        fabricComputePhEp(1638),
        fabricLastAckedSlot(1639),
        fabricSspLanMonCloud(1640),
        fabricSspMon(1641),
        fabricSspEthMon(1642),
        fabricSspEthMonSrcPhyTopEp(1643),
        fabricSspEthMonSrcAppLinksEp(1644),
        fabricSspEthMonSrcPhyEp(1645),
        fabricSspEthMonSrcPhyAggrEp(1646),
        fabricSspEthMonSrcAppEp(1647),
        fabricSspEthMonFilterEp(1648),
        fabricDceSwSrv(1649),
        fabricSwSrvEp(1650),
        fabricADceSwSrvEp(1651),
        fabricDceSwSrvEp(1652),
        fabricSwSrvPc(1653),
        fabricSubGroup(1654),
        fabricSwSubGroup(1655),
        fabricDceSwSrvPc(1656),
        fabricDceSwSrvPcEp(1657),
        fabricAEthEstcEp(1658),
        fabricAFcEstcEp(1659),
        fabricFcEstcEp(1660),
        fabricEthEstcEp(1661),
        fabricTargetEp(1662),
        fabricEthTargetEp(1663),
        fabricBHVlan(1664),
        fabricEthEstcPcEp(1665),
        fabricEthVlanPc(1666),
        fabricEpMgr(1667),
        fabricBreakout(1668),
        fabricInternalEp(1669),
        fabricInternalPc(1670),
        fabricPinGroup(1671),
        fabricPinTarget(1672),
        fabricZoneIdUniverse(1673),
        bmcSELCounter(1674),
        mgmtBackupExportExtPolicy(1675),
        mgmtBackupPolicyConfig(1676),
        mgmtImportConfigInfo(1677),
        mgmtExportPolicy(1678),
        mgmtCfgExportPolicy(1679),
        mgmtBackupPolicy(1680),
        mgmtEntity(1681),
        mgmtPmonEntry(1682),
        mgmtBackup(1683),
        mgmtImporter(1684),
        mgmtAccessPolicy(1685),
        mgmtAccessPolicyItem(1686),
        mgmtAccessPort(1687),
        mgmtIntAuthPolicy(1688),
        mgmtCimcSecureBoot(1689),
        mgmtController(1690),
        mgmtIf(1691),
        mgmtIPv6IfConfig(1692),
        mgmtIPv6Addr(1693),
        mgmtIPv6IfAddr(1694),
        mgmtConnection(1695),
        mgmtInbandProfile(1696),
        mgmtProfDerivedInterface(1697),
        fsmStatus(1698),
        nfsEp(1699),
        nfsMountDef(1700),
        nfsMountInst(1701),
        portDomainEp(1702),
        portTrustMode(1703),
        portGroup(1704),
        portSubGroup(1705),
        fcConfig(1706),
        fcIfConfig(1707),
        fcSwIfConfig(1708),
        fcNicIfConfig(1709),
        fcStats(1710),
        fcStatsHist(1711),
        fcErrStats(1712),
        fcErrStatsHist(1713),
        ruleDefinition(1714),
        ruleItem(1715),
        ruleRequirement(1716),
        ruleSizeRequirement(1717),
        networkruleDefinition(1718),
        networkruleItem(1719),
        networkruleRequirement(1720),
        policyControlEp(1721),
        policyCentraleSync(1722),
        policyIdResolvePolicy(1723),
        policyControl(1724),
        policyDateTime(1725),
        policyCommunication(1726),
        policyDns(1727),
        policySecurity(1728),
        policyMonitoring(1729),
        policyFault(1730),
        policyInfraFirmware(1731),
        policyConfigBackup(1732),
        policyMEp(1733),
        policyDiscovery(1734),
        policyPowerMgmt(1735),
        policyPsu(1736),
        policyControlled(1737),
        policyControlledInstance(1738),
        policyControlledType(1739),
        policyPolicyEp(1740),
        policyPolicyScopeCont(1741),
        policyPolicyScopeContext(1742),
        policyPolicyScope(1743),
        policyPolicyRequestor(1744),
        policyDigest(1745),
        policyLocalMap(1746),
        policyElement(1747),
        policyRefReq(1748),
        aaaEpFsmTask(1749),
        aaaRealmFsmTask(1750),
        aaaUserEpFsmTask(1751),
        adaptorExtEthIfFsmTask(1752),
        adaptorHostEthIfFsmTask(1753),
        adaptorHostFcIfFsmTask(1754),
        applicationDownloaderFsmTask(1755),
        callhomeEpFsmTask(1756),
        capabilityCatalogueFsmTask(1757),
        capabilityMgmtExtensionFsmTask(1758),
        capabilityUpdaterFsmTask(1759),
        commSvcEpFsmTask(1760),
        computeBladeFsmTask(1761),
        computePhysicalFsmTask(1762),
        computeServerDiscPolicyFsmTask(1763),
        epqosDefinitionDelTaskFsmTask(1764),
        epqosDefinitionFsmTask(1765),
        equipmentBeaconLedFsmTask(1766),
        equipmentChassisFsmTask(1767),
        equipmentIOCardBaseFsmTask(1768),
        equipmentIOCardFsmTask(1769),
        equipmentLocatorLedFsmTask(1770),
        etherFtwPortPairFsmTask(1771),
        etherServerIntFIoFsmTask(1772),
        extpolEpFsmTask(1773),
        extpolProviderFsmTask(1774),
        extpolRegistryFsmTask(1775),
        fabricEpMgrFsmTask(1776),
        fabricLanCloudFsmTask(1777),
        fabricSanCloudFsmTask(1778),
        fabricVnetEpSyncEpFsmTask(1779),
        firmwareDistributableFsmTask(1780),
        firmwareDownloaderFsmTask(1781),
        firmwareImageFsmTask(1782),
        firmwarePlatformPackFsmTask(1783),
        firmwareSupFirmwareFsmTask(1784),
        firmwareSystemFsmTask(1785),
        gmetaHolderFsmTask(1786),
        identIdentRequestFsmTask(1787),
        identMetaSystemFsmTask(1788),
        licenseDownloaderFsmTask(1789),
        licenseFileFsmTask(1790),
        licenseInstanceFsmTask(1791),
        licenseSmartConfigFsmTask(1792),
        lsServerFsmTask(1793),
        mgmtBackupFsmTask(1794),
        mgmtControllerFsmTask(1795),
        mgmtExportPolicyFsmTask(1796),
        mgmtIPv6IfAddrFsmTask(1797),
        mgmtIfFsmTask(1798),
        mgmtImporterFsmTask(1799),
        nfsMountDefFsmTask(1800),
        nfsMountInstFsmTask(1801),
        nhTableHolderFsmTask(1802),
        observeObservedFsmTask(1803),
        pkiEpFsmTask(1804),
        policyControlEpFsmTask(1805),
        policyControlledTypeFsmTask(1806),
        policyPolicyScopeFsmTask(1807),
        portPIoFsmTask(1808),
        qosclassDefinitionFsmTask(1809),
        sdAppAttributeCtrlFsmTask(1810),
        sdAppInstanceFsmTask(1811),
        sdClusterBootstrapFsmTask(1812),
        sdLduFsmTask(1813),
        sdLinkFsmTask(1814),
        sdLogicalDeviceFsmTask(1815),
        sdMgmtInfoFsmTask(1816),
        sdNetMgmtBootstrapFsmTask(1817),
        sdSlotFsmTask(1818),
        sdUpgradeTaskFsmTask(1819),
        smAppFsmTask(1820),
        smAppInstanceFsmTask(1821),
        smSecSvcFsmTask(1822),
        statsCollectionPolicyFsmTask(1823),
        storageSystemFsmTask(1824),
        swAccessDomainFsmTask(1825),
        swEthLanBorderFsmTask(1826),
        swEthLanFlowMonFsmTask(1827),
        swEthMonFsmTask(1828),
        swExtUtilityFsmTask(1829),
        swFcMonFsmTask(1830),
        swFcSanBorderFsmTask(1831),
        swPhysFsmTask(1832),
        swSspEthMonFsmTask(1833),
        swSspEthMonSrcPhyEpFsmTask(1834),
        swUtilityDomainFsmTask(1835),
        syntheticFsObjFsmTask(1836),
        sysdebugAutoCoreFileExportTargetFsmTask(1837),
        sysdebugCoreFsmTask(1838),
        sysdebugLogControlEpFsmTask(1839),
        sysdebugLogExportPolicyFsmTask(1840),
        sysdebugManualCoreFileExportTargetFsmTask(1841),
        sysdebugTechSupportFsmTask(1842),
        sysfileMutationFsmTask(1843),
        aaaEpFsm(1844),
        aaaEpFsmStage(1845),
        aaaLdapEpFsm(1846),
        aaaLdapEpFsmStage(1847),
        aaaRadiusEpFsm(1848),
        aaaRadiusEpFsmStage(1849),
        aaaTacacsPlusEpFsm(1850),
        aaaTacacsPlusEpFsmStage(1851),
        aaaRealmFsm(1852),
        aaaRealmFsmStage(1853),
        aaaAuthRealmFsm(1854),
        aaaAuthRealmFsmStage(1855),
        aaaUserEpFsm(1856),
        aaaUserEpFsmStage(1857),
        adaptorExtEthIfFsm(1858),
        adaptorExtEthIfFsmStage(1859),
        adaptorHostEthIfFsm(1860),
        adaptorHostEthIfFsmStage(1861),
        adaptorHostFcIfFsm(1862),
        adaptorHostFcIfFsmStage(1863),
        applicationDownloaderFsm(1864),
        applicationDownloaderFsmStage(1865),
        callhomeEpFsm(1866),
        callhomeEpFsmStage(1867),
        capabilityCatalogueFsm(1868),
        capabilityCatalogueFsmStage(1869),
        capabilityMgmtExtensionFsm(1870),
        capabilityMgmtExtensionFsmStage(1871),
        capabilityUpdaterFsm(1872),
        capabilityUpdaterFsmStage(1873),
        commSvcEpFsm(1874),
        commSvcEpFsmStage(1875),
        computeBladeFsm(1876),
        computeBladeFsmStage(1877),
        computePhysicalFsm(1878),
        computePhysicalFsmStage(1879),
        computeRackUnitFsm(1880),
        computeRackUnitFsmStage(1881),
        computeServerDiscPolicyFsm(1882),
        computeServerDiscPolicyFsmStage(1883),
        epqosDefinitionDelTaskFsm(1884),
        epqosDefinitionDelTaskFsmStage(1885),
        epqosDefinitionFsm(1886),
        epqosDefinitionFsmStage(1887),
        equipmentBeaconLedFsm(1888),
        equipmentBeaconLedFsmStage(1889),
        equipmentChassisFsm(1890),
        equipmentChassisFsmStage(1891),
        equipmentIOCardBaseFsm(1892),
        equipmentIOCardBaseFsmStage(1893),
        equipmentIOCardFsm(1894),
        equipmentIOCardFsmStage(1895),
        equipmentSwitchIOCardFsm(1896),
        equipmentSwitchIOCardFsmStage(1897),
        equipmentLocatorLedFsm(1898),
        equipmentLocatorLedFsmStage(1899),
        etherFtwPortPairFsm(1900),
        etherFtwPortPairFsmStage(1901),
        etherServerIntFIoFsm(1902),
        etherServerIntFIoFsmStage(1903),
        extpolEpFsm(1904),
        extpolEpFsmStage(1905),
        extpolProviderFsm(1906),
        extpolProviderFsmStage(1907),
        extpolRegistryFsm(1908),
        extpolRegistryFsmStage(1909),
        fabricEpMgrFsm(1910),
        fabricEpMgrFsmStage(1911),
        fabricLanCloudFsm(1912),
        fabricLanCloudFsmStage(1913),
        fabricSanCloudFsm(1914),
        fabricSanCloudFsmStage(1915),
        fabricVnetEpSyncEpFsm(1916),
        fabricVnetEpSyncEpFsmStage(1917),
        firmwareDistributableFsm(1918),
        firmwareDistributableFsmStage(1919),
        firmwareDownloaderFsm(1920),
        firmwareDownloaderFsmStage(1921),
        firmwareImageFsm(1922),
        firmwareImageFsmStage(1923),
        firmwarePlatformPackFsm(1924),
        firmwarePlatformPackFsmStage(1925),
        firmwareSupFirmwareFsm(1926),
        firmwareSupFirmwareFsmStage(1927),
        firmwareSystemFsm(1928),
        firmwareSystemFsmStage(1929),
        gmetaHolderFsm(1930),
        gmetaHolderFsmStage(1931),
        identIdentRequestFsm(1932),
        identIdentRequestFsmStage(1933),
        identMetaSystemFsm(1934),
        identMetaSystemFsmStage(1935),
        licenseDownloaderFsm(1936),
        licenseDownloaderFsmStage(1937),
        licenseFileFsm(1938),
        licenseFileFsmStage(1939),
        licenseInstanceFsm(1940),
        licenseInstanceFsmStage(1941),
        licenseSmartConfigFsm(1942),
        licenseSmartConfigFsmStage(1943),
        lsServerFsm(1944),
        lsServerFsmStage(1945),
        mgmtBackupFsm(1946),
        mgmtBackupFsmStage(1947),
        mgmtControllerFsm(1948),
        mgmtControllerFsmStage(1949),
        mgmtExportPolicyFsm(1950),
        mgmtExportPolicyFsmStage(1951),
        mgmtBackupPolicyFsm(1952),
        mgmtBackupPolicyFsmStage(1953),
        mgmtCfgExportPolicyFsm(1954),
        mgmtCfgExportPolicyFsmStage(1955),
        mgmtIPv6IfAddrFsm(1956),
        mgmtIPv6IfAddrFsmStage(1957),
        mgmtIfFsm(1958),
        mgmtIfFsmStage(1959),
        mgmtImporterFsm(1960),
        mgmtImporterFsmStage(1961),
        nfsMountDefFsm(1962),
        nfsMountDefFsmStage(1963),
        nfsMountInstFsm(1964),
        nfsMountInstFsmStage(1965),
        nhTableHolderFsm(1966),
        nhTableHolderFsmStage(1967),
        observeObservedFsm(1968),
        observeObservedFsmStage(1969),
        pkiEpFsm(1970),
        pkiEpFsmStage(1971),
        policyControlEpFsm(1972),
        policyControlEpFsmStage(1973),
        policyControlledTypeFsm(1974),
        policyControlledTypeFsmStage(1975),
        policyPolicyScopeFsm(1976),
        policyPolicyScopeFsmStage(1977),
        portPIoFsm(1978),
        portPIoFsmStage(1979),
        etherPIoFsm(1980),
        etherPIoFsmStage(1981),
        fcPIoFsm(1982),
        fcPIoFsmStage(1983),
        qosclassDefinitionFsm(1984),
        qosclassDefinitionFsmStage(1985),
        sdAppAttributeCtrlFsm(1986),
        sdAppAttributeCtrlFsmStage(1987),
        sdAppInstanceFsm(1988),
        sdAppInstanceFsmStage(1989),
        sdClusterBootstrapFsm(1990),
        sdClusterBootstrapFsmStage(1991),
        sdLduFsm(1992),
        sdLduFsmStage(1993),
        sdLinkFsm(1994),
        sdLinkFsmStage(1995),
        sdAppLduLinkFsm(1996),
        sdAppLduLinkFsmStage(1997),
        sdExternalLduLinkFsm(1998),
        sdExternalLduLinkFsmStage(1999),
        sdLogicalDeviceFsm(2000),
        sdLogicalDeviceFsmStage(2001),
        sdMgmtInfoFsm(2002),
        sdMgmtInfoFsmStage(2003),
        sdNetMgmtBootstrapFsm(2004),
        sdNetMgmtBootstrapFsmStage(2005),
        sdSlotFsm(2006),
        sdSlotFsmStage(2007),
        sdUpgradeTaskFsm(2008),
        sdUpgradeTaskFsmStage(2009),
        smAppFsm(2010),
        smAppFsmStage(2011),
        smAppInstanceFsm(2012),
        smAppInstanceFsmStage(2013),
        smSecSvcFsm(2014),
        smSecSvcFsmStage(2015),
        statsCollectionPolicyFsm(2016),
        statsCollectionPolicyFsmStage(2017),
        storageSystemFsm(2018),
        storageSystemFsmStage(2019),
        swAccessDomainFsm(2020),
        swAccessDomainFsmStage(2021),
        swEthLanBorderFsm(2022),
        swEthLanBorderFsmStage(2023),
        swEthLanFlowMonFsm(2024),
        swEthLanFlowMonFsmStage(2025),
        swEthMonFsm(2026),
        swEthMonFsmStage(2027),
        swExtUtilityFsm(2028),
        swExtUtilityFsmStage(2029),
        swFcMonFsm(2030),
        swFcMonFsmStage(2031),
        swFcSanBorderFsm(2032),
        swFcSanBorderFsmStage(2033),
        swPhysFsm(2034),
        swPhysFsmStage(2035),
        swSspEthMonFsm(2036),
        swSspEthMonFsmStage(2037),
        swSspEthMonSrcPhyEpFsm(2038),
        swSspEthMonSrcPhyEpFsmStage(2039),
        swUtilityDomainFsm(2040),
        swUtilityDomainFsmStage(2041),
        syntheticFsObjFsm(2042),
        syntheticFsObjFsmStage(2043),
        sysdebugAutoCoreFileExportTargetFsm(2044),
        sysdebugAutoCoreFileExportTargetFsmStage(2045),
        sysdebugCoreFsm(2046),
        sysdebugCoreFsmStage(2047),
        sysdebugLogControlEpFsm(2048),
        sysdebugLogControlEpFsmStage(2049),
        sysdebugLogExportPolicyFsm(2050),
        sysdebugLogExportPolicyFsmStage(2051),
        sysdebugManualCoreFileExportTargetFsm(2052),
        sysdebugManualCoreFileExportTargetFsmStage(2053),
        sysdebugTechSupportFsm(2054),
        sysdebugTechSupportFsmStage(2055),
        sysfileMutationFsm(2056),
        sysfileMutationFsmStage(2057),
        firmwareInfraPackFsmTask(2058),
        firmwareInfraPackFsm(2059),
        firmwareInfraPackFsmStage(2060),
        equipmentCardStatsHist(2062)
    }

CfprApNetworkConfigIssues ::= TEXTUAL-CONVENTION
    STATUS        current
    DESCRIPTION
        ""
    SYNTAX        BITS
    {
        conflictingVlanAccess(0),
        namedVlanInaccessible(1),
        permitUnresolved(2),
        pinningInvalid(3),
        switchVirtualIfCapacity(4),
        unsupportedMulticastPolicy(5),
        vlanPortCapacity(6),
        networkFeatureCapabilityMismatch(7)
    }

CfprApNetworkConnectionType ::= TEXTUAL-CONVENTION
    STATUS        current
    DESCRIPTION
        ""
    SYNTAX        BITS
    {
        lan(0),
        san(1),
        ipc(2)
    }

CfprApNetworkElementOperability ::= TEXTUAL-CONVENTION
    STATUS        current
    DESCRIPTION
        ""
    SYNTAX        INTEGER
    {
        unknown(0),
        operable(1),
        inoperable(2),
        removed(3)
    }

CfprApNetworkIfStatsType ::= TEXTUAL-CONVENTION
    STATUS        current
    DESCRIPTION
        ""
    SYNTAX        INTEGER
    {
        generic(0),
        broadcast(1),
        multicast(2),
        unicast(3),
        total(4)
    }

CfprApNetworkIfStatsUnits ::= TEXTUAL-CONVENTION
    STATUS        current
    DESCRIPTION
        ""
    SYNTAX        INTEGER
    {
        raw(0),
        packets(1),
        octets(2)
    }

CfprApNetworkIfStatus ::= TEXTUAL-CONVENTION
    STATUS        current
    DESCRIPTION
        ""
    SYNTAX        INTEGER
    {
        unknown(0),
        down(1),
        up(2)
    }

CfprApNetworkInventoryStatus ::= TEXTUAL-CONVENTION
    STATUS        current
    DESCRIPTION
        ""
    SYNTAX        BITS
    {
        switchFru(0),
        vlanPortCount(1),
        cardInventory(2),
        ethPortInventory(3),
        fcPortInventory(4),
        mgmtPortInventory(5),
        ethPcInventory(6),
        fcPcInventory(7),
        switchInventory(8),
        xcvrInventory(9),
        remoteEthPortInventory(10),
        vlanCompGrpInventory(11)
    }

CfprApNetworkLocale ::= TEXTUAL-CONVENTION
    STATUS        current
    DESCRIPTION
        ""
    SYNTAX        BITS
    {
        server(0),
        chassis(1),
        internal(2),
        external(3)
    }

CfprApNetworkPhysEpIfType ::= TEXTUAL-CONVENTION
    STATUS        current
    DESCRIPTION
        ""
    SYNTAX        INTEGER
    {
        unknown(0),
        physical(1),
        aggregation(2),
        virtual(3),
        fabric(4)
    }

CfprApNetworkPortOperState ::= TEXTUAL-CONVENTION
    STATUS        current
    DESCRIPTION
        ""
    SYNTAX        INTEGER
    {
        indeterminate(0),
        up(1),
        adminDown(2),
        linkDown(3),
        failed(4),
        noLicense(5),
        linkUp(6),
        hardwareFailure(7),
        softwareFailure(8),
        errorDisabled(9),
        sfpNotPresent(10),
        udldAggrDown(11)
    }

CfprApNetworkPortRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApNetworkPortType ::= TEXTUAL-CONVENTION
    STATUS        current
    DESCRIPTION
        ""
    SYNTAX        INTEGER
    {
        unknown(0),
        physical(1),
        aggregation(2),
        virtual(3),
        fabric(4)
    }

CfprApNetworkSide ::= TEXTUAL-CONVENTION
    STATUS        current
    DESCRIPTION
        ""
    SYNTAX        INTEGER
    {
        left(0),
        right(1)
    }

CfprApNetworkSwitchId ::= TEXTUAL-CONVENTION
    STATUS        current
    DESCRIPTION
        ""
    SYNTAX        INTEGER
    {
        none(0),
        a(1),
        b(2)
    }

CfprApNetworkTransport ::= TEXTUAL-CONVENTION
    STATUS        current
    DESCRIPTION
        ""
    SYNTAX        BITS
    {
        ether(0),
        dce(1),
        fc(2)
    }

CfprApNetworkVlanCountStatus ::= TEXTUAL-CONVENTION
    STATUS        current
    DESCRIPTION
        ""
    SYNTAX        INTEGER
    {
        withinLimit(0),
        aboveLimit(1)
    }

CfprApNetworkVnetEpIfType ::= TEXTUAL-CONVENTION
    STATUS        current
    DESCRIPTION
        ""
    SYNTAX        INTEGER
    {
        unknown(0),
        physical(1),
        aggregation(2),
        virtual(3),
        fabric(4)
    }

CfprApNfsClientConfigState ::= TEXTUAL-CONVENTION
    STATUS        current
    DESCRIPTION
        ""
    SYNTAX        INTEGER
    {
        unregistered(0),
        registered(1),
        configured(2),
        failed(3)
    }

CfprApNfsDefAdminState ::= TEXTUAL-CONVENTION
    STATUS        current
    DESCRIPTION
        ""
    SYNTAX        INTEGER
    {
        disabled(0),
        enabled(1),
        suspended(2)
    }

CfprApNfsMntAdminState ::= TEXTUAL-CONVENTION
    STATUS        current
    DESCRIPTION
        ""
    SYNTAX        INTEGER
    {
        none(0),
        unmount(1),
        mount(2),
        remount(3)
    }

CfprApNfsMntOperState ::= TEXTUAL-CONVENTION
    STATUS        current
    DESCRIPTION
        ""
    SYNTAX        INTEGER
    {
        unmounted(0),
        mounted(1)
    }

CfprApNfsMountDefFsmCurrentFsm ::= TEXTUAL-CONVENTION
    STATUS        current
    DESCRIPTION
        ""
    SYNTAX        INTEGER
    {
        nop(0),
        reportNfsMountSuspend(494)
    }

CfprApNfsMountDefFsmStageName ::= TEXTUAL-CONVENTION
    STATUS        current
    DESCRIPTION
        ""
    SYNTAX        INTEGER
    {
        nop(0),
        reportNfsMountSuspendBegin(494),
        reportNfsMountSuspendReport(495),
        reportNfsMountSuspendFail(678),
        reportNfsMountSuspendSuccess(679)
    }

CfprApNfsMountDefFsmTaskItem ::= TEXTUAL-CONVENTION
    STATUS        current
    DESCRIPTION
        ""
    SYNTAX        INTEGER
    {
        nop(0),
        reportNfsMountSuspend(494)
    }

CfprApNfsMountInstFsmCurrentFsm ::= TEXTUAL-CONVENTION
    STATUS        current
    DESCRIPTION
        ""
    SYNTAX        INTEGER
    {
        nop(0),
        mount(486),
        unmount(491)
    }

CfprApNfsMountInstFsmStageName ::= TEXTUAL-CONVENTION
    STATUS        current
    DESCRIPTION
        ""
    SYNTAX        INTEGER
    {
        nop(0),
        mountBegin(486),
        mountRegisterClient(487),
        mountVerifyRegistration(488),
        mountMountLocal(489),
        mountMountPeer(490),
        unmountBegin(491),
        unmountUnmountLocal(492),
        unmountUnmountPeer(493),
        mountFail(680),
        mountSuccess(681),
        unmountFail(682),
        unmountSuccess(683)
    }

CfprApNfsMountInstFsmTaskItem ::= TEXTUAL-CONVENTION
    STATUS        current
    DESCRIPTION
        ""
    SYNTAX        INTEGER
    {
        nop(0),
        mount(486),
        unmount(491)
    }

CfprApNfsPurpose ::= TEXTUAL-CONVENTION
    STATUS        current
    DESCRIPTION
        ""
    SYNTAX        INTEGER
    {
        image(0),
        backup(1)
    }

CfprApNhConfMode ::= TEXTUAL-CONVENTION
    STATUS        current
    DESCRIPTION
        ""
    SYNTAX        INTEGER
    {
        ok(0),
        config(1),
        unconfig(2),
        error(3),
        fail(4)
    }

CfprApNhEpIdType ::= TEXTUAL-CONVENTION
    STATUS        current
    DESCRIPTION
        ""
    SYNTAX        INTEGER
    {
        intf(1),
        lbgBlade(2),
        lbgClust(3),
        bcg(4),
        flg(5)
    }

CfprApNhEpType ::= TEXTUAL-CONVENTION
    STATUS        current
    DESCRIPTION
        ""
    SYNTAX        INTEGER
    {
        ingress(1),
        egress(2),
        pcGrp(3)
    }

CfprApNhExecState ::= TEXTUAL-CONVENTION
    STATUS        current
    DESCRIPTION
        ""
    SYNTAX        INTEGER
    {
        ready(0),
        init(1)
    }

CfprApNhLinkType ::= TEXTUAL-CONVENTION
    STATUS        current
    DESCRIPTION
        ""
    SYNTAX        INTEGER
    {
        unicast(1),
        bcast(2)
    }

CfprApNhMacVlanType ::= TEXTUAL-CONVENTION
    STATUS        current
    DESCRIPTION
        ""
    SYNTAX        INTEGER
    {
        normal(0),
        miss(1),
        ucAll(2),
        mcAll(3),
        macAll(4),
        fpmac(5)
    }

CfprApNhPortType ::= TEXTUAL-CONVENTION
    STATUS        current
    DESCRIPTION
        ""
    SYNTAX        INTEGER
    {
        phy(0),
        pch(1),
        vif(2)
    }

CfprApNhTableHolderFsmCurrentFsm ::= TEXTUAL-CONVENTION
    STATUS        current
    DESCRIPTION
        ""
    SYNTAX        INTEGER
    {
        nop(0),
        configureLinks(401),
        bootstrapLinks(405)
    }

CfprApNhTableHolderFsmStageName ::= TEXTUAL-CONVENTION
    STATUS        current
    DESCRIPTION
        ""
    SYNTAX        INTEGER
    {
        nop(0),
        configureLinksBegin(401),
        configureLinksConfigInterface(402),
        configureLinksApplyConfig(403),
        configureLinksVerifyLinkConfig(404),
        bootstrapLinksBegin(405),
        bootstrapLinksApplyConfig(406),
        bootstrapLinksFail(684),
        bootstrapLinksSuccess(685),
        configureLinksFail(686),
        configureLinksSuccess(687)
    }

CfprApNhTableHolderFsmTaskItem ::= TEXTUAL-CONVENTION
    STATUS        current
    DESCRIPTION
        ""
    SYNTAX        INTEGER
    {
        nop(0),
        configureLinks(401),
        bootstrapLinks(405)
    }

CfprApNhTableType ::= TEXTUAL-CONVENTION
    STATUS        current
    DESCRIPTION
        ""
    SYNTAX        INTEGER
    {
        data(1),
        ctrl(2)
    }

CfprApNhTpHashType ::= TEXTUAL-CONVENTION
    STATUS        current
    DESCRIPTION
        ""
    SYNTAX        INTEGER
    {
        normal(0),
        twoTuple(1)
    }

CfprApNhtestTestState ::= TEXTUAL-CONVENTION
    STATUS        current
    DESCRIPTION
        ""
    SYNTAX        INTEGER
    {
        ready(0),
        config(1),
        abort(2),
        unconfig(3),
        portmac(4),
        clean(5),
        delld(6),
        allocip(7),
        freeip(8)
    }

CfprApNwctrlAdminState ::= TEXTUAL-CONVENTION
    STATUS        current
    DESCRIPTION
        ""
    SYNTAX        INTEGER
    {
        disabled(0),
        enabled(1)
    }

CfprApNwctrlLinkFailAction ::= TEXTUAL-CONVENTION
    STATUS        current
    DESCRIPTION
        ""
    SYNTAX        INTEGER
    {
        linkDown(0),
        warning(1)
    }

CfprApNwctrlRegistrationMode ::= TEXTUAL-CONVENTION
    STATUS        current
    DESCRIPTION
        ""
    SYNTAX        INTEGER
    {
        onlyNativeVlan(0),
        allHostVlans(1)
    }

CfprApObserveObservedFsmCurrentFsm ::= TEXTUAL-CONVENTION
    STATUS        current
    DESCRIPTION
        ""
    SYNTAX        INTEGER
    {
        nop(0),
        resolvePolicyFsm(239),
        resolveResourceFsm(241),
        resolveVMFsm(243),
        resolveControllerFsm(245)
    }

CfprApObserveObservedFsmStageName ::= TEXTUAL-CONVENTION
    STATUS        current
    DESCRIPTION
        ""
    SYNTAX        INTEGER
    {
        nop(0),
        resolvePolicyFsmBegin(239),
        resolvePolicyFsmExecute(240),
        resolveResourceFsmBegin(241),
        resolveResourceFsmExecute(242),
        resolveVMFsmBegin(243),
        resolveVMFsmExecute(244),
        resolveControllerFsmBegin(245),
        resolveControllerFsmExecute(246),
        resolveControllerFsmFail(688),
        resolveControllerFsmSuccess(689),
        resolvePolicyFsmFail(690),
        resolvePolicyFsmSuccess(691),
        resolveResourceFsmFail(692),
        resolveResourceFsmSuccess(693),
        resolveVMFsmFail(694),
        resolveVMFsmSuccess(695)
    }

CfprApObserveObservedFsmTaskItem ::= TEXTUAL-CONVENTION
    STATUS        current
    DESCRIPTION
        ""
    SYNTAX        INTEGER
    {
        nop(0),
        resolvePolicyFsm(239),
        resolveResourceFsm(241),
        resolveVMFsm(243),
        resolveControllerFsm(245)
    }

CfprApOrgLevel ::= TEXTUAL-CONVENTION
    STATUS        current
    DESCRIPTION
        ""
    SYNTAX        INTEGER
    {
        root(0),
        n1(1),
        n2(2),
        n3(3),
        n4(4),
        n5(5)
    }

CfprApOrgSrcMask ::= TEXTUAL-CONVENTION
    STATUS        current
    DESCRIPTION
        ""
    SYNTAX        BITS
    {
        local(0),
        global(1)
    }

CfprApOsBootingUpType ::= TEXTUAL-CONVENTION
    STATUS        current
    DESCRIPTION
        ""
    SYNTAX        INTEGER
    {
        outOfService(0),
        bootingUp(1),
        inService(2),
        failure(3)
    }

CfprApOsControllerBootMode ::= TEXTUAL-CONVENTION
    STATUS        current
    DESCRIPTION
        ""
    SYNTAX        INTEGER
    {
        normal(0),
        local(1),
        mio(2)
    }

CfprApOsControllerFormatDisk ::= TEXTUAL-CONVENTION
    STATUS        current
    DESCRIPTION
        ""
    SYNTAX        INTEGER
    {
        noOp(0),
        quickFormat(1),
        removeCfgapp(2)
    }

CfprApOsDeployState ::= TEXTUAL-CONVENTION
    STATUS        current
    DESCRIPTION
        ""
    SYNTAX        INTEGER
    {
        undefined(0),
        inProgress(1),
        complete(2),
        retry(3),
        failed(4),
        throttled(5)
    }

CfprApOsInitState ::= TEXTUAL-CONVENTION
    STATUS        current
    DESCRIPTION
        ""
    SYNTAX        INTEGER
    {
        undefined(0),
        inProgress(1),
        complete(2),
        retry(3),
        failed(4),
        throttled(5)
    }

CfprApOsOsMode ::= TEXTUAL-CONVENTION
    STATUS        current
    DESCRIPTION
        ""
    SYNTAX        INTEGER
    {
        normal(0),
        failsafe(1)
    }

CfprApOsOsType ::= TEXTUAL-CONVENTION
    STATUS        current
    DESCRIPTION
        ""
    SYNTAX        INTEGER
    {
        unspecified(0),
        pnuOS(1),
        linux(2),
        windows(3),
        solaris(4),
        vmwareESX(5),
        fxOS(6)
    }

CfprApOsUpgradeReturnCode ::= TEXTUAL-CONVENTION
    STATUS        current
    DESCRIPTION
        ""
    SYNTAX        INTEGER
    {
        null(0),
        requesting(1),
        successful(2),
        downloading(3),
        validating(4),
        failedComm(5),
        failedDownloading(6),
        failedValidation(7)
    }

CfprApOsUpgradeState ::= TEXTUAL-CONVENTION
    STATUS        current
    DESCRIPTION
        ""
    SYNTAX        INTEGER
    {
        undefined(0),
        inProgress(1),
        complete(2),
        retry(3),
        failed(4),
        throttled(5)
    }

CfprApPciEquipSlotId ::= TEXTUAL-CONVENTION
    STATUS        current
    DESCRIPTION
        ""
    SYNTAX        Gauge32 (1..5000)

CfprApPkiCertStatus ::= TEXTUAL-CONVENTION
    STATUS        current
    DESCRIPTION
        ""
    SYNTAX        INTEGER
    {
        valid(0),
        expired(1),
        revoked(2),
        notYetValid(3),
        emptyCert(4),
        unknown(5),
        failedToVerifyWithTp(6),
        failedToVerifyWithPrivateKey(7),
        certChainTooLong(8),
        selfSignedCertificate(9)
    }

CfprApPkiEpFsmCurrentFsm ::= TEXTUAL-CONVENTION
    STATUS        current
    DESCRIPTION
        ""
    SYNTAX        INTEGER
    {
        nop(0),
        updateEp(344)
    }

CfprApPkiEpFsmStageName ::= TEXTUAL-CONVENTION
    STATUS        current
    DESCRIPTION
        ""
    SYNTAX        INTEGER
    {
        nop(0),
        updateEpBegin(344),
        updateEpSetKeyRingLocal(345),
        updateEpSetKeyRingPeer(346),
        updateEpPostSetKeyRingLocal(347),
        updateEpPostSetKeyRingPeer(348),
        updateEpFail(696),
        updateEpSuccess(697)
    }

CfprApPkiEpFsmTaskItem ::= TEXTUAL-CONVENTION
    STATUS        current
    DESCRIPTION
        ""
    SYNTAX        INTEGER
    {
        nop(0),
        updateEp(344)
    }

CfprApPkiKeyringState ::= TEXTUAL-CONVENTION
    STATUS        current
    DESCRIPTION
        ""
    SYNTAX        INTEGER
    {
        started(1),
        created(2),
        reqCreated(3),
        tpSet(4),
        completed(5)
    }

CfprApPkiModulus ::= TEXTUAL-CONVENTION
    STATUS        current
    DESCRIPTION
        ""
    SYNTAX        INTEGER
    {
        modinvalid(0),
        mod1536(1536),
        mod2048(2048),
        mod2560(2560),
        mod3072(3072),
        mod3584(3584),
        mod4096(4096)
    }

CfprApPolicyCleanupMode ::= TEXTUAL-CONVENTION
    STATUS        current
    DESCRIPTION
        ""
    SYNTAX        INTEGER
    {
        localizeGlobal(0),
        deepRemoveGlobal(1)
    }

CfprApPolicyControlSource ::= TEXTUAL-CONVENTION
    STATUS        current
    DESCRIPTION
        ""
    SYNTAX        INTEGER
    {
        local(0),
        policy(1),
        pendingPolicy(2)
    }

CfprApPolicyControlEpFsmCurrentFsm ::= TEXTUAL-CONVENTION
    STATUS        current
    DESCRIPTION
        ""
    SYNTAX        INTEGER
    {
        nop(0),
        operate(502)
    }

CfprApPolicyControlEpFsmStageName ::= TEXTUAL-CONVENTION
    STATUS        current
    DESCRIPTION
        ""
    SYNTAX        INTEGER
    {
        nop(0),
        operateBegin(502),
        operateResolve(503),
        operateFail(698),
        operateSuccess(699)
    }

CfprApPolicyControlEpFsmTaskItem ::= TEXTUAL-CONVENTION
    STATUS        current
    DESCRIPTION
        ""
    SYNTAX        INTEGER
    {
        nop(0),
        operate(502)
    }

CfprApPolicyControlEpType ::= TEXTUAL-CONVENTION
    STATUS        current
    DESCRIPTION
        ""
    SYNTAX        INTEGER
    {
        policy(0)
    }

CfprApPolicyControlledTypeFsmCurrentFsm ::= TEXTUAL-CONVENTION
    STATUS        current
    DESCRIPTION
        ""
    SYNTAX        INTEGER
    {
        nop(0),
        operate(504)
    }

CfprApPolicyControlledTypeFsmStageName ::= TEXTUAL-CONVENTION
    STATUS        current
    DESCRIPTION
        ""
    SYNTAX        INTEGER
    {
        nop(0),
        operateBegin(504),
        operateResolveAll(505),
        operateFail(700),
        operateSuccess(701)
    }

CfprApPolicyControlledTypeFsmTaskItem ::= TEXTUAL-CONVENTION
    STATUS        current
    DESCRIPTION
        ""
    SYNTAX        INTEGER
    {
        nop(0),
        operate(504)
    }

CfprApPolicyIdResolvePolicyType ::= TEXTUAL-CONVENTION
    STATUS        current
    DESCRIPTION
        ""
    SYNTAX        INTEGER
    {
        noDuplicateCheck(0),
        looseDuplicateCheck(1),
        strictDuplicateCheck(2)
    }

CfprApPolicyPolicyOperStatus ::= TEXTUAL-CONVENTION
    STATUS        current
    DESCRIPTION
        ""
    SYNTAX        INTEGER
    {
        ok(0),
        resolved(1),
        released(2)
    }

CfprApPolicyPolicyOwner ::= TEXTUAL-CONVENTION
    STATUS        current
    DESCRIPTION
        ""
    SYNTAX        INTEGER
    {
        local(0),
        policy(1),
        pendingPolicy(2)
    }

CfprApPolicyPolicyResolveType ::= TEXTUAL-CONVENTION
    STATUS        current
    DESCRIPTION
        ""
    SYNTAX        INTEGER
    {
        name(0),
        rn(1)
    }

CfprApPolicyPolicyScopeFsmCurrentFsm ::= TEXTUAL-CONVENTION
    STATUS        current
    DESCRIPTION
        ""
    SYNTAX        INTEGER
    {
        nop(0),
        releasePolicyFsm(506),
        releaseOperationFsm(508),
        releaseStorageFsm(510),
        resolveManyPolicyFsm(512),
        resolveManyOperationFsm(514),
        resolveManyStorageFsm(516),
        releaseManyPolicyFsm(518),
        releaseManyOperationFsm(520),
        releaseManyStorageFsm(522),
        resolveAllPolicyFsm(524),
        resolveAllOperationFsm(526),
        resolveAllStorageFsm(528),
        releaseAllPolicyFsm(530),
        releaseAllOperationFsm(532),
        releaseAllStorageFsm(534)
    }

CfprApPolicyPolicyScopeFsmStageName ::= TEXTUAL-CONVENTION
    STATUS        current
    DESCRIPTION
        ""
    SYNTAX        INTEGER
    {
        nop(0),
        releasePolicyFsmBegin(506),
        releasePolicyFsmRelease(507),
        releaseOperationFsmBegin(508),
        releaseOperationFsmRelease(509),
        releaseStorageFsmBegin(510),
        releaseStorageFsmRelease(511),
        resolveManyPolicyFsmBegin(512),
        resolveManyPolicyFsmResolveMany(513),
        resolveManyOperationFsmBegin(514),
        resolveManyOperationFsmResolveMany(515),
        resolveManyStorageFsmBegin(516),
        resolveManyStorageFsmResolveMany(517),
        releaseManyPolicyFsmBegin(518),
        releaseManyPolicyFsmReleaseMany(519),
        releaseManyOperationFsmBegin(520),
        releaseManyOperationFsmReleaseMany(521),
        releaseManyStorageFsmBegin(522),
        releaseManyStorageFsmReleaseMany(523),
        resolveAllPolicyFsmBegin(524),
        resolveAllPolicyFsmResolveAll(525),
        resolveAllOperationFsmBegin(526),
        resolveAllOperationFsmResolveAll(527),
        resolveAllStorageFsmBegin(528),
        resolveAllStorageFsmResolveAll(529),
        releaseAllPolicyFsmBegin(530),
        releaseAllPolicyFsmReleaseAll(531),
        releaseAllOperationFsmBegin(532),
        releaseAllOperationFsmReleaseAll(533),
        releaseAllStorageFsmBegin(534),
        releaseAllStorageFsmReleaseAll(535),
        releaseAllOperationFsmFail(702),
        releaseAllOperationFsmSuccess(703),
        releaseAllPolicyFsmFail(704),
        releaseAllPolicyFsmSuccess(705),
        releaseAllStorageFsmFail(706),
        releaseAllStorageFsmSuccess(707),
        releaseManyOperationFsmFail(708),
        releaseManyOperationFsmSuccess(709),
        releaseManyPolicyFsmFail(710),
        releaseManyPolicyFsmSuccess(711),
        releaseManyStorageFsmFail(712),
        releaseManyStorageFsmSuccess(713),
        releaseOperationFsmFail(714),
        releaseOperationFsmSuccess(715),
        releasePolicyFsmFail(716),
        releasePolicyFsmSuccess(717),
        releaseStorageFsmFail(718),
        releaseStorageFsmSuccess(719),
        resolveAllOperationFsmFail(720),
        resolveAllOperationFsmSuccess(721),
        resolveAllPolicyFsmFail(722),
        resolveAllPolicyFsmSuccess(723),
        resolveAllStorageFsmFail(724),
        resolveAllStorageFsmSuccess(725),
        resolveManyOperationFsmFail(726),
        resolveManyOperationFsmSuccess(727),
        resolveManyPolicyFsmFail(728),
        resolveManyPolicyFsmSuccess(729),
        resolveManyStorageFsmFail(730),
        resolveManyStorageFsmSuccess(731)
    }

CfprApPolicyPolicyScopeFsmTaskItem ::= TEXTUAL-CONVENTION
    STATUS        current
    DESCRIPTION
        ""
    SYNTAX        INTEGER
    {
        nop(0),
        releasePolicyFsm(506),
        releaseOperationFsm(508),
        releaseStorageFsm(510),
        resolveManyPolicyFsm(512),
        resolveManyOperationFsm(514),
        resolveManyStorageFsm(516),
        releaseManyPolicyFsm(518),
        releaseManyOperationFsm(520),
        releaseManyStorageFsm(522),
        resolveAllPolicyFsm(524),
        resolveAllOperationFsm(526),
        resolveAllStorageFsm(528),
        releaseAllPolicyFsm(530),
        releaseAllOperationFsm(532),
        releaseAllStorageFsm(534)
    }

CfprApPolicyRegistrationStateType ::= TEXTUAL-CONVENTION
    STATUS        current
    DESCRIPTION
        ""
    SYNTAX        INTEGER
    {
        registering(0),
        registered(1),
        failed(2),
        lostVisibility(3),
        unregistered(4)
    }

CfprApPolicyRepairStateType ::= TEXTUAL-CONVENTION
    STATUS        current
    DESCRIPTION
        ""
    SYNTAX        INTEGER
    {
        done(0),
        notDone(1)
    }

CfprApPolicyResumeAckState ::= TEXTUAL-CONVENTION
    STATUS        current
    DESCRIPTION
        ""
    SYNTAX        INTEGER
    {
        noAck(0),
        acked(1)
    }

CfprApPolicyState ::= TEXTUAL-CONVENTION
    STATUS        current
    DESCRIPTION
        ""
    SYNTAX        INTEGER
    {
        ok(0),
        outOfSync(1)
    }

CfprApPolicySuspendState ::= TEXTUAL-CONVENTION
    STATUS        current
    DESCRIPTION
        ""
    SYNTAX        INTEGER
    {
        off(0),
        on(1)
    }

CfprApPoolElementOwner ::= TEXTUAL-CONVENTION
    STATUS        current
    DESCRIPTION
        ""
    SYNTAX        INTEGER
    {
        endPoint(0),
        pool(1)
    }

CfprApPoolPoolAssignmentOrder ::= TEXTUAL-CONVENTION
    STATUS        current
    DESCRIPTION
        ""
    SYNTAX        INTEGER
    {
        default(0),
        sequential(1)
    }

CfprApPortDuplex ::= TEXTUAL-CONVENTION
    STATUS        current
    DESCRIPTION
        ""
    SYNTAX        INTEGER
    {
        halfDuplex(1),
        fullDuplex(2),
        auto(4)
    }

CfprApPortEncap ::= TEXTUAL-CONVENTION
    STATUS        current
    DESCRIPTION
        ""
    SYNTAX        INTEGER
    {
        unknown(0),
        dot1q(1),
        isl(2),
        negotiate(3),
        proprietary(4)
    }

CfprApPortEthAdminSpeed ::= TEXTUAL-CONVENTION
    STATUS        current
    DESCRIPTION
        ""
    SYNTAX        INTEGER
    {
        indeterminate(0),
        n1gbps(1),
        n10gbps(2),
        n20gbps(3),
        n40gbps(4)
    }

CfprApPortEthSpeed ::= TEXTUAL-CONVENTION
    STATUS        current
    DESCRIPTION
        ""
    SYNTAX        INTEGER
    {
        indeterminate(0),
        n1gbps(1),
        n10gbps(2),
        n20gbps(3),
        n40gbps(4),
        n100gbps(5),
        n10mbps(6),
        n100mbps(7)
    }

CfprApPortGroupType ::= TEXTUAL-CONVENTION
    STATUS        current
    DESCRIPTION
        ""
    SYNTAX        INTEGER
    {
        switchEther(1),
        switchFc(4),
        host(8),
        fabric(16),
        fabricPc(17),
        hostPc(18),
        adaptorExt(19),
        adaptorPc(20),
        serverPc(21)
    }

CfprApPortMode ::= TEXTUAL-CONVENTION
    STATUS        current
    DESCRIPTION
        ""
    SYNTAX        INTEGER
    {
        unknown(0),
        access(1),
        trunk(2),
        fabric(3),
        nProxy(4),
        f(5),
        e(6),
        sd(7)
    }

CfprApPortPIoFsmCurrentFsm ::= TEXTUAL-CONVENTION
    STATUS        current
    DESCRIPTION
        ""
    SYNTAX        INTEGER
    {
        nop(0),
        inCompatSfpPresence(235),
        inCompatSfpReplaced(237)
    }

CfprApPortPIoFsmStageName ::= TEXTUAL-CONVENTION
    STATUS        current
    DESCRIPTION
        ""
    SYNTAX        INTEGER
    {
        nop(0),
        inCompatSfpPresenceBegin(235),
        inCompatSfpPresenceShutdown(236),
        inCompatSfpReplacedBegin(237),
        inCompatSfpReplacedEnablePort(238),
        inCompatSfpPresenceFail(732),
        inCompatSfpPresenceSuccess(733),
        inCompatSfpReplacedFail(734),
        inCompatSfpReplacedSuccess(735)
    }

CfprApPortPIoFsmTaskItem ::= TEXTUAL-CONVENTION
    STATUS        current
    DESCRIPTION
        ""
    SYNTAX        INTEGER
    {
        nop(0),
        inCompatSfpPresence(235),
        inCompatSfpReplaced(237)
    }

CfprApPortSpeed ::= TEXTUAL-CONVENTION
    STATUS        current
    DESCRIPTION
        ""
    SYNTAX        INTEGER
    {
        indeterminate(0),
        n1gbps(1),
        n2gbps(2),
        n4gbps(3),
        n8gbps(4),
        auto(5)
    }

CfprApPortSubGroupConfigState ::= TEXTUAL-CONVENTION
    STATUS        current
    DESCRIPTION
        ""
    SYNTAX        INTEGER
    {
        enabled(1),
        disabled(2)
    }

CfprApPortSubGroupSlotId ::= TEXTUAL-CONVENTION
    STATUS        current
    DESCRIPTION
        ""
    SYNTAX        Gauge32 (1..4)

CfprApPortTrust ::= TEXTUAL-CONVENTION
    STATUS        current
    DESCRIPTION
        ""
    SYNTAX        INTEGER
    {
        trusted(0),
        untrusted(1)
    }

CfprApPowerCapAction ::= TEXTUAL-CONVENTION
    STATUS        current
    DESCRIPTION
        ""
    SYNTAX        INTEGER
    {
        nothing(0),
        clockDown(1),
        throttled(2)
    }

CfprApPowerChThrAction ::= TEXTUAL-CONVENTION
    STATUS        current
    DESCRIPTION
        ""
    SYNTAX        INTEGER
    {
        nothing(0),
        throttleBladeDisc(1),
        stopBladeDisc(2)
    }

CfprApPowerGroupState ::= TEXTUAL-CONVENTION
    STATUS        current
    DESCRIPTION
        ""
    SYNTAX        BITS
    {
        capOk(0),
        capInsufficient(1),
        capMismatch(2)
    }

CfprApPowerGroupStatsThresholded ::= TEXTUAL-CONVENTION
    STATUS        current
    DESCRIPTION
        ""
    SYNTAX        BITS
    {
        power(0),
        powerAvg(1),
        powerMax(2),
        powerMin(3)
    }

CfprApPowerGroupStatsHistThresholded ::= TEXTUAL-CONVENTION
    STATUS        current
    DESCRIPTION
        ""
    SYNTAX        BITS
    {
        power(0),
        powerAvg(1),
        powerMax(2),
        powerMin(3)
    }

CfprApPowerLockState ::= TEXTUAL-CONVENTION
    STATUS        current
    DESCRIPTION
        ""
    SYNTAX        INTEGER
    {
        unknown(0),
        locked(1),
        unlocked(2)
    }

CfprApPowerMemberState ::= TEXTUAL-CONVENTION
    STATUS        current
    DESCRIPTION
        ""
    SYNTAX        INTEGER
    {
        uninitialized(0),
        capOk(1),
        fwMismatch(2),
        psuInsufficient(3),
        psuRedundancyFailed(4),
        capInsufficient(5)
    }

CfprApPowerMgmtStyle ::= TEXTUAL-CONVENTION
    STATUS        current
    DESCRIPTION
        ""
    SYNTAX        INTEGER
    {
        manualPerBlade(0),
        intelligentPolicyDriven(1)
    }

CfprApPowerOperState ::= TEXTUAL-CONVENTION
    STATUS        current
    DESCRIPTION
        ""
    SYNTAX        INTEGER
    {
        notCapped(0),
        budgeting(1),
        budgeted(2),
        deploying(3),
        deployed(4),
        discoveryRetry(5),
        nonCompliant(6),
        firmwareMismatch(7),
        discoveryBudgeted(8),
        unbudgeted(9)
    }

CfprApPowerPrioritySharing ::= TEXTUAL-CONVENTION
    STATUS        current
    DESCRIPTION
        ""
    SYNTAX        INTEGER
    {
        noPreference(0),
        highestPrioInChassis(1),
        highestPrioInPowerGroup(2)
    }

CfprApPowerProfilingMethod ::= TEXTUAL-CONVENTION
    STATUS        current
    DESCRIPTION
        ""
    SYNTAX        INTEGER
    {
        unknown(0),
        default(1),
        static(2),
        pnuos(3),
        nodemgr(4)
    }

CfprApPowerPsuLineMode ::= TEXTUAL-CONVENTION
    STATUS        current
    DESCRIPTION
        ""
    SYNTAX        INTEGER
    {
        unknown(0),
        undetermined(1),
        highLine(2),
        lowLine(3),
        mixedLine(4),
        lowerLine(5)
    }

CfprApPowerPsuState ::= TEXTUAL-CONVENTION
    STATUS        current
    DESCRIPTION
        ""
    SYNTAX        INTEGER
    {
        ok(0),
        insufficient(1)
    }

CfprApPowerReallocation ::= TEXTUAL-CONVENTION
    STATUS        current
    DESCRIPTION
        ""
    SYNTAX        INTEGER
    {
        chassis(0),
        none(1)
    }

CfprApPowerReqConflict ::= TEXTUAL-CONVENTION
    STATUS        current
    DESCRIPTION
        ""
    SYNTAX        INTEGER
    {
        ignore(0),
        failPlacement(1)
    }

CfprApProcStatAdminState ::= TEXTUAL-CONVENTION
    STATUS        current
    DESCRIPTION
        ""
    SYNTAX        INTEGER
    {
        on(1),
        clearStats(2),
        logStats(3)
    }

CfprApProcessorEnvStatsThresholded ::= TEXTUAL-CONVENTION
    STATUS        current
    DESCRIPTION
        ""
    SYNTAX        BITS
    {
        inputCurrent(0),
        inputCurrentAvg(1),
        inputCurrentMax(2),
        inputCurrentMin(3),
        temperature(4),
        temperatureAvg(5),
        temperatureMax(6),
        temperatureMin(7)
    }

CfprApProcessorEnvStatsHistThresholded ::= TEXTUAL-CONVENTION
    STATUS        current
    DESCRIPTION
        ""
    SYNTAX        BITS
    {
        inputCurrent(0),
        inputCurrentAvg(1),
        inputCurrentMax(2),
        inputCurrentMin(3),
        temperature(4),
        temperatureAvg(5),
        temperatureMax(6),
        temperatureMin(7)
    }

CfprApProcessorErrorStatsThresholded ::= TEXTUAL-CONVENTION
    STATUS        current
    DESCRIPTION
        ""
    SYNTAX        BITS
    {
        mirroringInterSockErrors(0),
        mirroringIntraSockErrors(1),
        smiLinkCorrErrors(2),
        smiLinkUncorrErrors(3),
        sparingErrors(4)
    }

CfprApProcessorQualArch ::= TEXTUAL-CONVENTION
    STATUS        current
    DESCRIPTION
        ""
    SYNTAX        INTEGER
    {
        any(0),
        intelP4C(1),
        opteron(132),
        turion64(134),
        dualCoreOpteron(135),
        pentium4(178),
        xeon(179),
        xeonMP(181)
    }

CfprApProcessorRuntimeThresholded ::= TEXTUAL-CONVENTION
    STATUS        current
    DESCRIPTION
        ""
    SYNTAX        BITS
    {
        load(0),
        loadAvg(1),
        loadMax(2),
        loadMin(3)
    }

CfprApProcessorRuntimeHistThresholded ::= TEXTUAL-CONVENTION
    STATUS        current
    DESCRIPTION
        ""
    SYNTAX        BITS
    {
        load(0),
        loadAvg(1),
        loadMax(2),
        loadMin(3)
    }

CfprApProcessorUnitArch ::= TEXTUAL-CONVENTION
    STATUS        current
    DESCRIPTION
        ""
    SYNTAX        INTEGER
    {
        any(0),
        intelP4C(1),
        opteron(132),
        turion64(134),
        dualCoreOpteron(135),
        pentium4(178),
        xeon(179),
        xeonMP(181)
    }

CfprApQosHostControl ::= TEXTUAL-CONVENTION
    STATUS        current
    DESCRIPTION
        ""
    SYNTAX        INTEGER
    {
        none(0),
        full(1),
        fullWithException(2)
    }

CfprApQosPriority ::= TEXTUAL-CONVENTION
    STATUS        current
    DESCRIPTION
        ""
    SYNTAX        INTEGER
    {
        fc(1),
        platinum(2),
        gold(3),
        silver(4),
        bronze(5),
        bestEffort(6)
    }

CfprApQosclassDefinitionFsmCurrentFsm ::= TEXTUAL-CONVENTION
    STATUS        current
    DESCRIPTION
        ""
    SYNTAX        INTEGER
    {
        nop(0),
        configGlobalQoS(390)
    }

CfprApQosclassDefinitionFsmStageName ::= TEXTUAL-CONVENTION
    STATUS        current
    DESCRIPTION
        ""
    SYNTAX        INTEGER
    {
        nop(0),
        configGlobalQoSBegin(390),
        configGlobalQoSSetLocal(391),
        configGlobalQoSSetPeer(392),
        configGlobalQoSFail(736),
        configGlobalQoSSuccess(737)
    }

CfprApQosclassDefinitionFsmTaskItem ::= TEXTUAL-CONVENTION
    STATUS        current
    DESCRIPTION
        ""
    SYNTAX        INTEGER
    {
        nop(0),
        configGlobalQoS(390)
    }

CfprApQosclassEthBEAdminState ::= TEXTUAL-CONVENTION
    STATUS        current
    DESCRIPTION
        ""
    SYNTAX        INTEGER
    {
        disabled(0),
        enabled(1)
    }

CfprApQosclassEthBEDrop ::= TEXTUAL-CONVENTION
    STATUS        current
    DESCRIPTION
        ""
    SYNTAX        INTEGER
    {
        drop(0),
        noDrop(1)
    }

CfprApQosclassEthBEPriority ::= TEXTUAL-CONVENTION
    STATUS        current
    DESCRIPTION
        ""
    SYNTAX        INTEGER
    {
        fc(1),
        platinum(2),
        gold(3),
        silver(4),
        bronze(5),
        bestEffort(6)
    }

CfprApQosclassEthClassifiedAdminState ::= TEXTUAL-CONVENTION
    STATUS        current
    DESCRIPTION
        ""
    SYNTAX        INTEGER
    {
        disabled(0),
        enabled(1)
    }

CfprApQosclassEthClassifiedDrop ::= TEXTUAL-CONVENTION
    STATUS        current
    DESCRIPTION
        ""
    SYNTAX        INTEGER
    {
        drop(0),
        noDrop(1)
    }

CfprApQosclassEthClassifiedPriority ::= TEXTUAL-CONVENTION
    STATUS        current
    DESCRIPTION
        ""
    SYNTAX        INTEGER
    {
        fc(1),
        platinum(2),
        gold(3),
        silver(4),
        bronze(5),
        bestEffort(6)
    }

CfprApQosclassFcAdminState ::= TEXTUAL-CONVENTION
    STATUS        current
    DESCRIPTION
        ""
    SYNTAX        INTEGER
    {
        disabled(0),
        enabled(1)
    }

CfprApQosclassFcDrop ::= TEXTUAL-CONVENTION
    STATUS        current
    DESCRIPTION
        ""
    SYNTAX        INTEGER
    {
        drop(0),
        noDrop(1)
    }

CfprApQosclassFcPriority ::= TEXTUAL-CONVENTION
    STATUS        current
    DESCRIPTION
        ""
    SYNTAX        INTEGER
    {
        fc(1),
        platinum(2),
        gold(3),
        silver(4),
        bronze(5),
        bestEffort(6)
    }

CfprApRmetaModType ::= TEXTUAL-CONVENTION
    STATUS        current
    DESCRIPTION
        ""
    SYNTAX        INTEGER
    {
        readOnly(0),
        readWrite(1),
        readCreate(2)
    }

CfprApSdActionType ::= TEXTUAL-CONVENTION
    STATUS        current
    DESCRIPTION
        ""
    SYNTAX        INTEGER
    {
        none(0),
        add(1),
        update(2),
        delete(3)
    }

CfprApSdAppAttributeCtrlFsmCurrentFsm ::= TEXTUAL-CONVENTION
    STATUS        current
    DESCRIPTION
        ""
    SYNTAX        INTEGER
    {
        nop(0),
        getAppAttributes(300)
    }

CfprApSdAppAttributeCtrlFsmStageName ::= TEXTUAL-CONVENTION
    STATUS        current
    DESCRIPTION
        ""
    SYNTAX        INTEGER
    {
        nop(0),
        getAppAttributesBegin(300),
        getAppAttributesGetAttributes(301),
        getAppAttributesFail(738),
        getAppAttributesSuccess(739)
    }

CfprApSdAppAttributeCtrlFsmTaskItem ::= TEXTUAL-CONVENTION
    STATUS        current
    DESCRIPTION
        ""
    SYNTAX        INTEGER
    {
        nop(0),
        getAppAttributes(300)
    }

CfprApSdAppInstAdminState ::= TEXTUAL-CONVENTION
    STATUS        current
    DESCRIPTION
        ""
    SYNTAX        INTEGER
    {
        enabled(0),
        disabled(1)
    }

CfprApSdAppInstState ::= TEXTUAL-CONVENTION
    STATUS        current
    DESCRIPTION
        ""
    SYNTAX        INTEGER
    {
        notInstalled(0),
        installing(1),
        installFailed(2),
        offline(3),
        starting(4),
        startFailed(5),
        started(6),
        online(7),
        stopping(8),
        stopFailed(9),
        notResponding(10),
        updating(11),
        updateFailed(12),
        updateSucceeded(13),
        unsupported(14)
    }

CfprApSdAppInstanceCurrentJobProgress ::= TEXTUAL-CONVENTION
    STATUS        current
    DESCRIPTION
        ""
    SYNTAX        Gauge32 (0..100)

CfprApSdAppInstanceFsmCurrentFsm ::= TEXTUAL-CONVENTION
    STATUS        current
    DESCRIPTION
        ""
    SYNTAX        INTEGER
    {
        nop(0),
        installApplication(250),
        startApplication(254),
        upgradeApplication(263),
        stopApplication(267),
        uninstallApplication(272),
        bundleDataPorts(278)
    }

CfprApSdAppInstanceFsmStageName ::= TEXTUAL-CONVENTION
    STATUS        current
    DESCRIPTION
        ""
    SYNTAX        INTEGER
    {
        nop(0),
        installApplicationBegin(250),
        installApplicationSendCommand(251),
        installApplicationWaitStage(252),
        installApplicationUpdateAppInstance(253),
        startApplicationBegin(254),
        startApplicationSendCommand(255),
        startApplicationWaitStage(256),
        startApplicationUpdateAppInstance(257),
        upgradeApplicationBegin(263),
        upgradeApplicationSendCommand(264),
        upgradeApplicationWaitStage(265),
        upgradeApplicationUpdateAppInstance(266),
        stopApplicationBegin(267),
        stopApplicationReleaseAppLicense(268),
        stopApplicationSendCommand(269),
        stopApplicationWaitStage(270),
        stopApplicationUpdateAppInstance(271),
        uninstallApplicationBegin(272),
        uninstallApplicationReleaseAppLicense(273),
        uninstallApplicationSendCommand(274),
        uninstallApplicationWaitStage(275),
        bundleDataPortsBegin(278),
        bundleDataPortsConfigureLinks(279),
        bundleDataPortsWaitForConfigCompletion(280),
        bundleDataPortsUpdateBundleStatus(281),
        bundleDataPortsSendBundleStatus(282),
        bundleDataPortsFail(740),
        bundleDataPortsSuccess(741),
        installApplicationFail(742),
        installApplicationSuccess(743),
        startApplicationFail(744),
        startApplicationSuccess(745),
        stopApplicationFail(746),
        stopApplicationSuccess(747),
        uninstallApplicationFail(748),
        uninstallApplicationSuccess(749),
        upgradeApplicationFail(750),
        upgradeApplicationSuccess(751)
    }

CfprApSdAppInstanceFsmTaskFlags ::= TEXTUAL-CONVENTION
    STATUS        current
    DESCRIPTION
        ""
    SYNTAX        BITS
    {
        samDmeSdAppInstanceStopApplicationReleaseLicense(22),
        samDmeSdAppInstanceStopApplicationStopAppInstance(23)
    }

CfprApSdAppInstanceFsmTaskItem ::= TEXTUAL-CONVENTION
    STATUS        current
    DESCRIPTION
        ""
    SYNTAX        INTEGER
    {
        nop(0),
        installApplication(250),
        startApplication(254),
        upgradeApplication(263),
        stopApplication(267),
        uninstallApplication(272),
        bundleDataPorts(278)
    }

CfprApSdAppLduLinkFsmCurrentFsm ::= TEXTUAL-CONVENTION
    STATUS        current
    DESCRIPTION
        ""
    SYNTAX        INTEGER
    {
        nop(0),
        updateInterfaceStatus(289)
    }

CfprApSdAppLduLinkFsmStageName ::= TEXTUAL-CONVENTION
    STATUS        current
    DESCRIPTION
        ""
    SYNTAX        INTEGER
    {
        nop(0),
        updateInterfaceStatusBegin(289),
        updateInterfaceStatusSendStatus(290),
        updateInterfaceStatusFail(756),
        updateInterfaceStatusSuccess(757)
    }

CfprApSdAppResetState ::= TEXTUAL-CONVENTION
    STATUS        current
    DESCRIPTION
        ""
    SYNTAX        INTEGER
    {
        none(0),
        waitBladeReboot(1)
    }

CfprApSdCfgPortForwardingMode ::= TEXTUAL-CONVENTION
    STATUS        current
    DESCRIPTION
        ""
    SYNTAX        INTEGER
    {
        none(0),
        individual(1),
        promiscuous(2)
    }

CfprApSdClusterBootstrapChassisId ::= TEXTUAL-CONVENTION
    STATUS        current
    DESCRIPTION
        ""
    SYNTAX        Gauge32 (1..16)

CfprApSdClusterBootstrapFsmCurrentFsm ::= TEXTUAL-CONVENTION
    STATUS        current
    DESCRIPTION
        ""
    SYNTAX        INTEGER
    {
        nop(0),
        updateClusterConfiguration(291)
    }

CfprApSdClusterBootstrapFsmStageName ::= TEXTUAL-CONVENTION
    STATUS        current
    DESCRIPTION
        ""
    SYNTAX        INTEGER
    {
        nop(0),
        updateClusterConfigurationBegin(291),
        updateClusterConfigurationSendConfig(292),
        updateClusterConfigurationFail(752),
        updateClusterConfigurationSuccess(753)
    }

CfprApSdClusterBootstrapFsmTaskItem ::= TEXTUAL-CONVENTION
    STATUS        current
    DESCRIPTION
        ""
    SYNTAX        INTEGER
    {
        nop(0),
        updateClusterConfiguration(291)
    }

CfprApSdClusterStatus ::= TEXTUAL-CONVENTION
    STATUS        current
    DESCRIPTION
        ""
    SYNTAX        INTEGER
    {
        unknown(0),
        joined(1),
        left(2)
    }

CfprApSdExternalLduLinkFsmCurrentFsm ::= TEXTUAL-CONVENTION
    STATUS        current
    DESCRIPTION
        ""
    SYNTAX        INTEGER
    {
        nop(0),
        updateInterfaceStatus(289)
    }

CfprApSdExternalLduLinkFsmStageName ::= TEXTUAL-CONVENTION
    STATUS        current
    DESCRIPTION
        ""
    SYNTAX        INTEGER
    {
        nop(0),
        updateInterfaceStatusBegin(289),
        updateInterfaceStatusSendStatus(290),
        updateInterfaceStatusFail(756),
        updateInterfaceStatusSuccess(757)
    }

CfprApSdInterfaceType ::= TEXTUAL-CONVENTION
    STATUS        current
    DESCRIPTION
        ""
    SYNTAX        INTEGER
    {
        root(0),
        sub(1)
    }

CfprApSdJobState ::= TEXTUAL-CONVENTION
    STATUS        current
    DESCRIPTION
        ""
    SYNTAX        INTEGER
    {
        unknown(0),
        queued(1),
        failed(2),
        succeeded(3)
    }

CfprApSdJobType ::= TEXTUAL-CONVENTION
    STATUS        current
    DESCRIPTION
        ""
    SYNTAX        INTEGER
    {
        unknown(0),
        install(1),
        uninstall(2),
        upgrade(3),
        start(4),
        stop(5),
        formatDisk(6),
        uploadPlatformImage(7)
    }

CfprApSdLdOperState ::= TEXTUAL-CONVENTION
    STATUS        current
    DESCRIPTION
        ""
    SYNTAX        INTEGER
    {
        unknown(0),
        ok(1),
        incompleteConfiguration(2)
    }

CfprApSdLduFsmCurrentFsm ::= TEXTUAL-CONVENTION
    STATUS        current
    DESCRIPTION
        ""
    SYNTAX        INTEGER
    {
        nop(0),
        provisionLDU(258)
    }

CfprApSdLduFsmStageName ::= TEXTUAL-CONVENTION
    STATUS        current
    DESCRIPTION
        ""
    SYNTAX        INTEGER
    {
        nop(0),
        provisionLDUBegin(258),
        provisionLDUCheckBladeReadiness(259),
        provisionLDUWaitForAppsInstallation(260),
        provisionLDUWaitForLinkConfiguration(261),
        provisionLDUStartApps(262),
        provisionLDUFail(754),
        provisionLDUSuccess(755)
    }

CfprApSdLduFsmTaskItem ::= TEXTUAL-CONVENTION
    STATUS        current
    DESCRIPTION
        ""
    SYNTAX        INTEGER
    {
        nop(0),
        provisionLDU(258)
    }

CfprApSdLduOperState ::= TEXTUAL-CONVENTION
    STATUS        current
    DESCRIPTION
        ""
    SYNTAX        INTEGER
    {
        unknown(0),
        active(1),
        suspended(2)
    }

CfprApSdLinkDirection ::= TEXTUAL-CONVENTION
    STATUS        current
    DESCRIPTION
        ""
    SYNTAX        INTEGER
    {
        rin(1),
        out(2),
        both(3)
    }

CfprApSdLinkFsmCurrentFsm ::= TEXTUAL-CONVENTION
    STATUS        current
    DESCRIPTION
        ""
    SYNTAX        INTEGER
    {
        nop(0),
        updateInterfaceStatus(289)
    }

CfprApSdLinkFsmStageName ::= TEXTUAL-CONVENTION
    STATUS        current
    DESCRIPTION
        ""
    SYNTAX        INTEGER
    {
        nop(0),
        updateInterfaceStatusBegin(289),
        updateInterfaceStatusSendStatus(290),
        updateInterfaceStatusFail(756),
        updateInterfaceStatusSuccess(757)
    }

CfprApSdLinkFsmTaskItem ::= TEXTUAL-CONVENTION
    STATUS        current
    DESCRIPTION
        ""
    SYNTAX        INTEGER
    {
        nop(0),
        updateInterfaceStatus(289)
    }

CfprApSdLinkOperState ::= TEXTUAL-CONVENTION
    STATUS        current
    DESCRIPTION
        ""
    SYNTAX        INTEGER
    {
        unknown(0),
        up(1),
        down(2)
    }

CfprApSdLogicalDeviceFsmCurrentFsm ::= TEXTUAL-CONVENTION
    STATUS        current
    DESCRIPTION
        ""
    SYNTAX        INTEGER
    {
        nop(0),
        configureLinks(283)
    }

CfprApSdLogicalDeviceFsmStageName ::= TEXTUAL-CONVENTION
    STATUS        current
    DESCRIPTION
        ""
    SYNTAX        INTEGER
    {
        nop(0),
        configureLinksBegin(283),
        configureLinksSendInterfaces(284),
        configureLinksUnconfigureLinks(285),
        configureLinksConfigureSwitch(286),
        configureLinksWaitForSwitchConfig(287),
        configureLinksUnconfigureLogicalDevice(288),
        configureLinksFail(758),
        configureLinksSuccess(759)
    }

CfprApSdLogicalDeviceFsmTaskItem ::= TEXTUAL-CONVENTION
    STATUS        current
    DESCRIPTION
        ""
    SYNTAX        INTEGER
    {
        nop(0),
        configureLinks(283)
    }

CfprApSdMacType ::= TEXTUAL-CONVENTION
    STATUS        current
    DESCRIPTION
        ""
    SYNTAX        INTEGER
    {
        unicast(1),
        multicast(2)
    }

CfprApSdMgmtInfoFsmCurrentFsm ::= TEXTUAL-CONVENTION
    STATUS        current
    DESCRIPTION
        ""
    SYNTAX        INTEGER
    {
        nop(0),
        updateMgmtInfo(302)
    }

CfprApSdMgmtInfoFsmStageName ::= TEXTUAL-CONVENTION
    STATUS        current
    DESCRIPTION
        ""
    SYNTAX        INTEGER
    {
        nop(0),
        updateMgmtInfoBegin(302),
        updateMgmtInfoSendUpdate(303),
        updateMgmtInfoFail(760),
        updateMgmtInfoSuccess(761)
    }

CfprApSdMgmtInfoFsmTaskItem ::= TEXTUAL-CONVENTION
    STATUS        current
    DESCRIPTION
        ""
    SYNTAX        INTEGER
    {
        nop(0),
        updateMgmtInfo(302)
    }

CfprApSdNetMgmtBootstrapFsmCurrentFsm ::= TEXTUAL-CONVENTION
    STATUS        current
    DESCRIPTION
        ""
    SYNTAX        INTEGER
    {
        nop(0),
        updateNetMgmtBootstrap(304)
    }

CfprApSdNetMgmtBootstrapFsmStageName ::= TEXTUAL-CONVENTION
    STATUS        current
    DESCRIPTION
        ""
    SYNTAX        INTEGER
    {
        nop(0),
        updateNetMgmtBootstrapBegin(304),
        updateNetMgmtBootstrapSendUpdate(305),
        updateNetMgmtBootstrapFail(762),
        updateNetMgmtBootstrapSuccess(763)
    }

CfprApSdNetMgmtBootstrapFsmTaskItem ::= TEXTUAL-CONVENTION
    STATUS        current
    DESCRIPTION
        ""
    SYNTAX        INTEGER
    {
        nop(0),
        updateNetMgmtBootstrap(304)
    }

CfprApSdPortBundleOpType ::= TEXTUAL-CONVENTION
    STATUS        current
    DESCRIPTION
        ""
    SYNTAX        INTEGER
    {
        bundled(0),
        deBundled(1)
    }

CfprApSdPortBundleStatus ::= TEXTUAL-CONVENTION
    STATUS        current
    DESCRIPTION
        ""
    SYNTAX        INTEGER
    {
        unknown(0),
        failure(1),
        partial(2),
        success(3)
    }

CfprApSdPortForwardingMode ::= TEXTUAL-CONVENTION
    STATUS        current
    DESCRIPTION
        ""
    SYNTAX        INTEGER
    {
        individual(0),
        promiscuous(1)
    }

CfprApSdSlotFsmCurrentFsm ::= TEXTUAL-CONVENTION
    STATUS        current
    DESCRIPTION
        ""
    SYNTAX        INTEGER
    {
        nop(0),
        changePlatformLogLevel(276),
        formatDisk(293),
        synchTimeZone(298)
    }

CfprApSdSlotFsmStageName ::= TEXTUAL-CONVENTION
    STATUS        current
    DESCRIPTION
        ""
    SYNTAX        INTEGER
    {
        nop(0),
        changePlatformLogLevelBegin(276),
        changePlatformLogLevelSendCommand(277),
        formatDiskBegin(293),
        formatDiskCheckBladeReadiness(294),
        formatDiskStartDiskFormat(295),
        formatDiskResetBladePower(296),
        formatDiskWaitForDiskFormatComplete(297),
        synchTimeZoneBegin(298),
        synchTimeZoneUpdateTimeZone(299),
        changePlatformLogLevelFail(764),
        changePlatformLogLevelSuccess(765),
        formatDiskFail(766),
        formatDiskSuccess(767),
        synchTimeZoneFail(768),
        synchTimeZoneSuccess(769)
    }

CfprApSdSlotFsmTaskItem ::= TEXTUAL-CONVENTION
    STATUS        current
    DESCRIPTION
        ""
    SYNTAX        INTEGER
    {
        nop(0),
        changePlatformLogLevel(276),
        formatDisk(293),
        synchTimeZone(298)
    }

CfprApSdUpgradeTaskFsmCurrentFsm ::= TEXTUAL-CONVENTION
    STATUS        current
    DESCRIPTION
        ""
    SYNTAX        INTEGER
    {
        nop(0),
        stopUpgradeStartApp(306)
    }

CfprApSdUpgradeTaskFsmStageName ::= TEXTUAL-CONVENTION
    STATUS        current
    DESCRIPTION
        ""
    SYNTAX        INTEGER
    {
        nop(0),
        stopUpgradeStartAppBegin(306),
        stopUpgradeStartAppStopApp(307),
        stopUpgradeStartAppWaitForStopApp(308),
        stopUpgradeStartAppWaitForBladeReboot(309),
        stopUpgradeStartAppUpgradeApp(310),
        stopUpgradeStartAppWaitForUpgradeApp(311),
        stopUpgradeStartAppStartApp(312),
        stopUpgradeStartAppFail(770),
        stopUpgradeStartAppSuccess(771)
    }

CfprApSdUpgradeTaskFsmTaskItem ::= TEXTUAL-CONVENTION
    STATUS        current
    DESCRIPTION
        ""
    SYNTAX        INTEGER
    {
        nop(0),
        stopUpgradeStartApp(306)
    }

CfprApServerConfigIssues ::= TEXTUAL-CONVENTION
    STATUS        current
    DESCRIPTION
        ""
    SYNTAX        BITS
    {
        insufficientResources(0),
        boardControllerUpdateUnsupported(1),
        bootConfigurationInvalid(2),
        bootOrderIscsi(3),
        bootOrderPxe(4),
        bootOrderSanImagePath(5),
        computeUnavailable(6),
        computeUndiscovered(7),
        incompatBiosForSriovVnics(8),
        incompatibleBiosImage(9),
        insufficientPowerBudget(10),
        macAddressAssignment(11),
        memoryRequirement(12),
        migration(13),
        missingFirmwareImage(14),
        nonInterruptFsmRunning(15),
        physicalRequirement(16),
        powerGroupRequirement(17),
        processorRequirement(18),
        remotePolicy(19),
        serverPositionRequirement(20),
        remoteServiceProfile(21),
        systemUuidAssignment(22),
        wwnnDerivationFromVhba(23),
        resourceOwnershipConflict(24),
        bootipPolicyInvalid(25),
        hostimgPolicyInvalid(26),
        imgsecPolicyInvalid(27),
        provsrvPolicyInvalid(28),
        qosPolicyInvalid(29),
        bootConfigurationUnsupported(30),
        serverFeatureCapabilityMismatch(31),
        domainRequirement(32),
        duplicateAddressConflict(33),
        vmediaPolicyUnsupported(34),
        bootPolicyVmediaInvalid(35),
        vmediaMountConfigInvalid(36),
        softPinningVlanMismatch(37),
        cimcDowngradeRestriction(38),
        ivbCimcDowngradeRestriction(39),
        ivbBiosDowngradeRestriction(40),
        incompatibleSsposImage(41)
    }

CfprApSmActionStages ::= TEXTUAL-CONVENTION
    STATUS        current
    DESCRIPTION
        ""
    SYNTAX        INTEGER
    {
        available(0),
        perform(1),
        performing(2),
        failure(3),
        notAvailable(4)
    }

CfprApSmAppAdminState ::= TEXTUAL-CONVENTION
    STATUS        current
    DESCRIPTION
        ""
    SYNTAX        INTEGER
    {
        active(0),
        deleted(1)
    }

CfprApSmAppAggregatorType ::= TEXTUAL-CONVENTION
    STATUS        current
    DESCRIPTION
        ""
    SYNTAX        INTEGER
    {
        unknown(0),
        none(1),
        partial(2),
        full(3),
        serviceStandard(4)
    }

CfprApSmAppClusterOperState ::= TEXTUAL-CONVENTION
    STATUS        current
    DESCRIPTION
        ""
    SYNTAX        INTEGER
    {
        notApplicable(0),
        inCluster(1),
        notInCluster(2),
        joiningCluster(3),
        leavingCluster(4)
    }

CfprApSmAppCommand ::= TEXTUAL-CONVENTION
    STATUS        current
    DESCRIPTION
        ""
    SYNTAX        INTEGER
    {
        ok(0),
        retryAction(1),
        clearMgmtBootstrap(2)
    }

CfprApSmAppFsmCurrentFsm ::= TEXTUAL-CONVENTION
    STATUS        current
    DESCRIPTION
        ""
    SYNTAX        INTEGER
    {
        nop(0),
        delete(79),
        updateApplication(83)
    }

CfprApSmAppFsmStageName ::= TEXTUAL-CONVENTION
    STATUS        current
    DESCRIPTION
        ""
    SYNTAX        INTEGER
    {
        nop(0),
        deleteBegin(79),
        deleteLocal(80),
        updateApplicationBegin(83),
        updateApplicationUpdate(84),
        deleteFail(772),
        deleteSuccess(773),
        updateApplicationFail(776),
        updateApplicationSuccess(777)
    }

CfprApSmAppFsmTaskItem ::= TEXTUAL-CONVENTION
    STATUS        current
    DESCRIPTION
        ""
    SYNTAX        INTEGER
    {
        nop(0),
        delete(79),
        updateApplication(83)
    }

CfprApSmAppInstanceCurrentJobProgress ::= TEXTUAL-CONVENTION
    STATUS        current
    DESCRIPTION
        ""
    SYNTAX        Gauge32 (0..100)

CfprApSmAppInstanceFsmCurrentFsm ::= TEXTUAL-CONVENTION
    STATUS        current
    DESCRIPTION
        ""
    SYNTAX        INTEGER
    {
        nop(0),
        resetApplication(85)
    }

CfprApSmAppInstanceFsmStageName ::= TEXTUAL-CONVENTION
    STATUS        current
    DESCRIPTION
        ""
    SYNTAX        INTEGER
    {
        nop(0),
        resetApplicationBegin(85),
        resetApplicationStopDecoratorApps(86),
        resetApplicationWairForStopDecorators(87),
        resetApplicationStopMainApp(88),
        resetApplicationWaitForBladeReboot(89),
        resetApplicationWaitForStopMainApp(90),
        resetApplicationStartApps(91),
        resetApplicationFail(774),
        resetApplicationSuccess(775)
    }

CfprApSmAppInstanceFsmTaskItem ::= TEXTUAL-CONVENTION
    STATUS        current
    DESCRIPTION
        ""
    SYNTAX        INTEGER
    {
        nop(0),
        resetApplication(85)
    }

CfprApSmClusterBootstrapChassisId ::= TEXTUAL-CONVENTION
    STATUS        current
    DESCRIPTION
        ""
    SYNTAX        Gauge32 (1..16)

CfprApSmClusterMode ::= TEXTUAL-CONVENTION
    STATUS        current
    DESCRIPTION
        ""
    SYNTAX        INTEGER
    {
        spannedEtherchannel(0)
    }

CfprApSmCspType ::= TEXTUAL-CONVENTION
    STATUS        current
    DESCRIPTION
        ""
    SYNTAX        INTEGER
    {
        unknown(0),
        application(1),
        osPatch(2)
    }

CfprApSmDeployType ::= TEXTUAL-CONVENTION
    STATUS        current
    DESCRIPTION
        ""
    SYNTAX        INTEGER
    {
        unknown(0),
        native(1),
        lxc(2),
        vm(3)
    }

CfprApSmDiskState ::= TEXTUAL-CONVENTION
    STATUS        current
    DESCRIPTION
        ""
    SYNTAX        INTEGER
    {
        ok(0),
        formatting(1),
        formatFailure(2)
    }

CfprApSmHeartbeatState ::= TEXTUAL-CONVENTION
    STATUS        current
    DESCRIPTION
        ""
    SYNTAX        INTEGER
    {
        disable(0),
        enable(1)
    }

CfprApSmLogLevel ::= TEXTUAL-CONVENTION
    STATUS        current
    DESCRIPTION
        ""
    SYNTAX        INTEGER
    {
        debug(0),
        info(1),
        warning(2),
        error(3),
        critical(4)
    }

CfprApSmLogicalDeviceMode ::= TEXTUAL-CONVENTION
    STATUS        current
    DESCRIPTION
        ""
    SYNTAX        INTEGER
    {
        unknown(0),
        clustered(1),
        standalone(2),
        none(3)
    }

CfprApSmMgmtSubType ::= TEXTUAL-CONVENTION
    STATUS        current
    DESCRIPTION
        ""
    SYNTAX        INTEGER
    {
        default(0),
        firepower(1)
    }

CfprApSmNetMgmtBootstrapScope ::= TEXTUAL-CONVENTION
    STATUS        current
    DESCRIPTION
        ""
    SYNTAX        INTEGER
    {
        global(0),
        instanceOnly(1)
    }

CfprApSmNetMgmtBootstrapType ::= TEXTUAL-CONVENTION
    STATUS        current
    DESCRIPTION
        ""
    SYNTAX        INTEGER
    {
        nA(0),
        appagent(1),
        disk(2)
    }

CfprApSmSecSvcFsmCurrentFsm ::= TEXTUAL-CONVENTION
    STATUS        current
    DESCRIPTION
        ""
    SYNTAX        INTEGER
    {
        nop(0),
        restoreApplication(81),
        autoDeployCSP(92)
    }

CfprApSmSecSvcFsmStageName ::= TEXTUAL-CONVENTION
    STATUS        current
    DESCRIPTION
        ""
    SYNTAX        INTEGER
    {
        nop(0),
        restoreApplicationBegin(81),
        restoreApplicationRestore(82),
        autoDeployCSPBegin(92),
        autoDeployCSPWaitForPortReady(93),
        autoDeployCSPCreateLogicalDevice(94),
        autoDeployCSPFail(778),
        autoDeployCSPSuccess(779),
        restoreApplicationFail(780),
        restoreApplicationSuccess(781),
        autoDeployCSPWaitForChassisMoReady(833)
    }

CfprApSmSecSvcFsmTaskItem ::= TEXTUAL-CONVENTION
    STATUS        current
    DESCRIPTION
        ""
    SYNTAX        INTEGER
    {
        nop(0),
        restoreApplication(81),
        autoDeployCSP(92)
    }

CfprApSmSlotAdminState ::= TEXTUAL-CONVENTION
    STATUS        current
    DESCRIPTION
        ""
    SYNTAX        INTEGER
    {
        ok(0),
        reinitialize(1)
    }

CfprApSmSlotOperState ::= TEXTUAL-CONVENTION
    STATUS        current
    DESCRIPTION
        ""
    SYNTAX        INTEGER
    {
        notAvailable(0),
        offline(1),
        online(2),
        notResponding(3),
        fault(4),
        tokenMismatch(5)
    }

CfprApSolAdminState ::= TEXTUAL-CONVENTION
    STATUS        current
    DESCRIPTION
        ""
    SYNTAX        INTEGER
    {
        disable(0),
        enable(1)
    }

CfprApSolSpeed ::= TEXTUAL-CONVENTION
    STATUS        current
    DESCRIPTION
        ""
    SYNTAX        INTEGER
    {
        n9600(6),
        n19200(7),
        n38400(8),
        n57600(9),
        n115200(10)
    }

CfprApStatsCollectionDomain ::= TEXTUAL-CONVENTION
    STATUS        current
    DESCRIPTION
        ""
    SYNTAX        INTEGER
    {
        unknown(0),
        chassis(1),
        server(2),
        port(3),
        fex(4)
    }

CfprApStatsCollectionInterval ::= TEXTUAL-CONVENTION
    STATUS        current
    DESCRIPTION
        ""
    SYNTAX        INTEGER
    {
        n30seconds(30),
        n1minute(60),
        n2minutes(120),
        n5minutes(300)
    }

CfprApStatsCollectionPolicyFsmCurrentFsm ::= TEXTUAL-CONVENTION
    STATUS        current
    DESCRIPTION
        ""
    SYNTAX        INTEGER
    {
        nop(0),
        updateEp(407)
    }

CfprApStatsCollectionPolicyFsmStageName ::= TEXTUAL-CONVENTION
    STATUS        current
    DESCRIPTION
        ""
    SYNTAX        INTEGER
    {
        nop(0),
        updateEpBegin(407),
        updateEpSetEpA(408),
        updateEpSetEpB(409),
        updateEpFail(782),
        updateEpSuccess(783)
    }

CfprApStatsCollectionPolicyFsmTaskItem ::= TEXTUAL-CONVENTION
    STATUS        current
    DESCRIPTION
        ""
    SYNTAX        INTEGER
    {
        nop(0),
        updateEp(407)
    }

CfprApStatsReportingInterval ::= TEXTUAL-CONVENTION
    STATUS        current
    DESCRIPTION
        ""
    SYNTAX        INTEGER
    {
        n2minutes(120),
        n15minutes(900),
        n30minutes(1800),
        n60minutes(3600),
        n2hours(7200),
        n4hours(14400),
        n8hours(28800)
    }

CfprApStatsThr32DefinitionPropType ::= TEXTUAL-CONVENTION
    STATUS        current
    DESCRIPTION
        ""
    SYNTAX        INTEGER
    {
        uint32(1),
        uint64(2),
        float(3)
    }

CfprApStatsThr32ValuePropType ::= TEXTUAL-CONVENTION
    STATUS        current
    DESCRIPTION
        ""
    SYNTAX        INTEGER
    {
        uint32(1),
        uint64(2),
        float(3)
    }

CfprApStatsThr64DefinitionPropType ::= TEXTUAL-CONVENTION
    STATUS        current
    DESCRIPTION
        ""
    SYNTAX        INTEGER
    {
        uint32(1),
        uint64(2),
        float(3)
    }

CfprApStatsThr64ValuePropType ::= TEXTUAL-CONVENTION
    STATUS        current
    DESCRIPTION
        ""
    SYNTAX        INTEGER
    {
        uint32(1),
        uint64(2),
        float(3)
    }

CfprApStatsThrFloatDefinitionPropType ::= TEXTUAL-CONVENTION
    STATUS        current
    DESCRIPTION
        ""
    SYNTAX        INTEGER
    {
        uint32(1),
        uint64(2),
        float(3)
    }

CfprApStatsThrFloatValuePropType ::= TEXTUAL-CONVENTION
    STATUS        current
    DESCRIPTION
        ""
    SYNTAX        INTEGER
    {
        uint32(1),
        uint64(2),
        float(3)
    }

CfprApStatsThresholdDirection ::= TEXTUAL-CONVENTION
    STATUS        current
    DESCRIPTION
        ""
    SYNTAX        INTEGER
    {
        aboveNormal(1),
        belowNormal(2)
    }

CfprApStorageAccessType ::= TEXTUAL-CONVENTION
    STATUS        current
    DESCRIPTION
        ""
    SYNTAX        INTEGER
    {
        unknown(0),
        readWrite(1),
        readOnly(2),
        blocked(3)
    }

CfprApStorageActualWriteType ::= TEXTUAL-CONVENTION
    STATUS        current
    DESCRIPTION
        ""
    SYNTAX        INTEGER
    {
        unknown(0),
        writeThrough(1),
        writeBack(2)
    }

CfprApStorageAllocState ::= TEXTUAL-CONVENTION
    STATUS        current
    DESCRIPTION
        ""
    SYNTAX        INTEGER
    {
        none(0),
        allocating(1),
        allocated(2),
        failed(3)
    }

CfprApStorageBatteryType ::= TEXTUAL-CONVENTION
    STATUS        current
    DESCRIPTION
        ""
    SYNTAX        INTEGER
    {
        unknown(0),
        battery(1),
        supercap(2)
    }

CfprApStorageBbuStatus ::= TEXTUAL-CONVENTION
    STATUS        current
    DESCRIPTION
        ""
    SYNTAX        INTEGER
    {
        unknown(0),
        optimal(1),
        learnCycleActive(2),
        learnCycleNeeded(3),
        failurePredicted(4),
        premiumFeatureReqd(5),
        microcodeUpdateReqd(6),
        replacementNeeded(7),
        noFlashSpace(8),
        notSupported(9),
        notPresent(10)
    }

CfprApStorageBootableType ::= TEXTUAL-CONVENTION
    STATUS        current
    DESCRIPTION
        ""
    SYNTAX        INTEGER
    {
        unknown(0),
        true(1),
        false(2)
    }

CfprApStorageCacheType ::= TEXTUAL-CONVENTION
    STATUS        current
    DESCRIPTION
        ""
    SYNTAX        INTEGER
    {
        unknown(0),
        noChange(1),
        enable(2),
        disable(3)
    }

CfprApStorageConfigIssues ::= TEXTUAL-CONVENTION
    STATUS        current
    DESCRIPTION
        ""
    SYNTAX        BITS
    {
        destructiveLocalDiskConfig(0),
        incompatibleDiskTypes(1),
        incompatibleNumberOfLocalDisks(2),
        incompatibleRaidLevel(3),
        missingRaidKey(4),
        storagePathConfigurationError(5),
        wwnnAssignment(6),
        zoneCapacity(7),
        flexflashController(8),
        flexflashCard(9),
        flexflashMetadata(10),
        storageFeatureCapabilityMismatch(11)
    }

CfprApStorageConfiguration ::= TEXTUAL-CONVENTION
    STATUS        current
    DESCRIPTION
        ""
    SYNTAX        INTEGER
    {
        unknown(0),
        supported(1),
        notSupported(2)
    }

CfprApStorageConfiguredWriteType ::= TEXTUAL-CONVENTION
    STATUS        current
    DESCRIPTION
        ""
    SYNTAX        INTEGER
    {
        unknown(0),
        writeThrough(1),
        writeBackGoodBbu(2),
        alwaysWriteBack(3)
    }

CfprApStorageConnectionProtocol ::= TEXTUAL-CONVENTION
    STATUS        current
    DESCRIPTION
        ""
    SYNTAX        INTEGER
    {
        unspecified(0),
        sas(1),
        sata(2)
    }

CfprApStorageControllerFaultMonitoring ::= TEXTUAL-CONVENTION
    STATUS        current
    DESCRIPTION
        ""
    SYNTAX        INTEGER
    {
        supported(1),
        notSupported(2)
    }

CfprApStorageControllerId ::= TEXTUAL-CONVENTION
    STATUS        current
    DESCRIPTION
        ""
    SYNTAX        Gauge32 (1..64)

CfprApStorageControllerForm ::= TEXTUAL-CONVENTION
    STATUS        current
    DESCRIPTION
        ""
    SYNTAX        INTEGER
    {
        none(0),
        onBoard(1),
        mezzanine(2),
        pci(3),
        embedded(4)
    }

CfprApStorageControllerStatus ::= TEXTUAL-CONVENTION
    STATUS        current
    DESCRIPTION
        ""
    SYNTAX        INTEGER
    {
        unknown(0),
        optimal(1),
        failed(2),
        unresponsive(3)
    }

CfprApStorageControllerType ::= TEXTUAL-CONVENTION
    STATUS        current
    DESCRIPTION
        ""
    SYNTAX        INTEGER
    {
        unknown(0),
        sas(1),
        sata(2),
        flash(3),
        sd(4)
    }

CfprApStorageDisklessAction ::= TEXTUAL-CONVENTION
    STATUS        current
    DESCRIPTION
        ""
    SYNTAX        INTEGER
    {
        unspecified(0),
        yes(1),
        no(2)
    }

CfprApStorageEpAccess ::= TEXTUAL-CONVENTION
    STATUS        current
    DESCRIPTION
        ""
    SYNTAX        INTEGER
    {
        readonly(1),
        admin(2)
    }

CfprApStorageEtherIfVlanType ::= TEXTUAL-CONVENTION
    STATUS        current
    DESCRIPTION
        ""
    SYNTAX        INTEGER
    {
        regular(0),
        default(1),
        native(2)
    }

CfprApStorageFFCardHealth ::= TEXTUAL-CONVENTION
    STATUS        current
    DESCRIPTION
        ""
    SYNTAX        INTEGER
    {
        ffPhyHealthNa(0),
        ffPhyHealthOk(1),
        ffPhyUnhealthyRaid(2),
        ffPhyUnhealthyOther(3)
    }

CfprApStorageFFCardMode ::= TEXTUAL-CONVENTION
    STATUS        current
    DESCRIPTION
        ""
    SYNTAX        INTEGER
    {
        ffPhyDriveUnpairedPrimary(0),
        ffPhyDrivePrimary(1),
        ffPhyDriveSecondaryAct(2),
        ffPhyDriveSecondaryUnhealthy(3)
    }

CfprApStorageFFCardSizeMismatch ::= TEXTUAL-CONVENTION
    STATUS        current
    DESCRIPTION
        ""
    SYNTAX        INTEGER
    {
        na(0),
        mismatch(1),
        match(2)
    }

CfprApStorageFFCardState ::= TEXTUAL-CONVENTION
    STATUS        current
    DESCRIPTION
        ""
    SYNTAX        INTEGER
    {
        undefined(0),
        configured(1),
        initializing(2),
        active(3),
        ignored(4),
        failed(5),
        unknown(6)
    }

CfprApStorageFFCardSync ::= TEXTUAL-CONVENTION
    STATUS        current
    DESCRIPTION
        ""
    SYNTAX        INTEGER
    {
        na(0),
        manual(1),
        auto(2),
        unknown(3)
    }

CfprApStorageFFCardWriteEnable ::= TEXTUAL-CONVENTION
    STATUS        current
    DESCRIPTION
        ""
    SYNTAX        INTEGER
    {
        no(0),
        yes(1)
    }

CfprApStorageFFControllerHealth ::= TEXTUAL-CONVENTION
    STATUS        current
    DESCRIPTION
        ""
    SYNTAX        INTEGER
    {
        ffchOk(0),
        ffchMetadataFailure(1),
        ffchErrorCardsAccessError(2),
        ffchErrorOldFirmwareRunning(3),
        ffchErrorMediaWriteProtected(4),
        ffchErrorInvalidSize(5),
        ffchErrorCardSizeMismatch(6),
        ffchInconsistentMetadata(7),
        ffchErrorSecondaryUnhealthyCard(8),
        ffchErrorSdCardNotConfigured(9),
        ffchErrorInconsistantMetadataIgnored(10),
        ffchErrorSd253WithUnOrSd247(11),
        ffchErrorRebootedDuringRebuild(12),
        ffchErrorSd247CardDetected(13),
        ffchFlexdErrorSdCardOpModeMismatch(14),
        ffchFlexdErrorSdOpModeMismatchWithUn(15),
        ffchFlexdErrorImSdUnhealthySdUnIgnored(16),
        ffchFlexdErrorImSdHealthySdUnIgnored(17),
        ffchFlexdErrorImSdCardsOpModeMismatch(18),
        ffchFlexdErrorSdCard0UnhealthyOpModeMismatch(19),
        ffchFlexdErrorSdCard0HealthyOpModeMismatch(20),
        ffchFlexdErrorSdCard1UnhealthyOpModeMismatch(21),
        ffchFlexdErrorSdCard1HealthyOpModeMismatch(22),
        ffchFlexdErrorImSd0IgnoredSd1(23),
        ffchFlexdErrorImSd0Sd1Ignored(24)
    }

CfprApStorageFFControllerState ::= TEXTUAL-CONVENTION
    STATUS        current
    DESCRIPTION
        ""
    SYNTAX        INTEGER
    {
        ffcUninitalized(0),
        ffcSoftwareErr(1),
        ffcInit(2),
        ffcConfig(3),
        ffcWaitUser(4),
        ffcUsbDisconnecting(5),
        ffcUsbDisconnected(6),
        ffcUsbConnecting(7),
        ffcUsbConnected(8),
        ffcRebuilding(9),
        ffcFailed(10)
    }

CfprApStorageFFDriveRemovable ::= TEXTUAL-CONVENTION
    STATUS        current
    DESCRIPTION
        ""
    SYNTAX        INTEGER
    {
        na(0),
        yes(1),
        no(2)
    }

CfprApStorageFFDriveState ::= TEXTUAL-CONVENTION
    STATUS        current
    DESCRIPTION
        ""
    SYNTAX        INTEGER
    {
        nonraid(0),
        raid(1)
    }

CfprApStorageFFDriveType ::= TEXTUAL-CONVENTION
    STATUS        current
    DESCRIPTION
        ""
    SYNTAX        INTEGER
    {
        unknown(0),
        scu(1),
        huu(2),
        hv(3),
        drivers(4)
    }

CfprApStorageFFDriveVisible ::= TEXTUAL-CONVENTION
    STATUS        current
    DESCRIPTION
        ""
    SYNTAX        INTEGER
    {
        no(0),
        yes(1)
    }

CfprApStorageFFFormatRunning ::= TEXTUAL-CONVENTION
    STATUS        current
    DESCRIPTION
        ""
    SYNTAX        INTEGER
    {
        na(0),
        yes(1),
        no(2)
    }

CfprApStorageFFHasError ::= TEXTUAL-CONVENTION
    STATUS        current
    DESCRIPTION
        ""
    SYNTAX        INTEGER
    {
        error(0),
        noError(1)
    }

CfprApStorageFFRAIDHealth ::= TEXTUAL-CONVENTION
    STATUS        current
    DESCRIPTION
        ""
    SYNTAX        INTEGER
    {
        ffrHealthNa(0),
        ffrHealthOk(1),
        ffrHealthDegraded(2),
        ffrHealthNotReporting(3)
    }

CfprApStorageFFRAIDState ::= TEXTUAL-CONVENTION
    STATUS        current
    DESCRIPTION
        ""
    SYNTAX        INTEGER
    {
        ffrStateDisabled(0),
        ffrStateEnabledNotPaired(1),
        ffrStateEnabledPairedInvalidSecondary(2),
        ffrStateEnabledPairedInvalidPrimary(3),
        ffrStateEnabledPairedInvalidBoth(4),
        ffrStateEnabledPaired(5)
    }

CfprApStorageFFRWType ::= TEXTUAL-CONVENTION
    STATUS        current
    DESCRIPTION
        ""
    SYNTAX        INTEGER
    {
        readWrite(0),
        readOnly(1)
    }

CfprApStorageFFRaidSyncSupport ::= TEXTUAL-CONVENTION
    STATUS        current
    DESCRIPTION
        ""
    SYNTAX        INTEGER
    {
        no(0),
        yes(1)
    }

CfprApStorageFFSlotENUM ::= TEXTUAL-CONVENTION
    STATUS        current
    DESCRIPTION
        ""
    SYNTAX        INTEGER
    {
        na(0),
        n1(1),
        n2(2)
    }

CfprApStorageFFType ::= TEXTUAL-CONVENTION
    STATUS        current
    DESCRIPTION
        ""
    SYNTAX        INTEGER
    {
        unknown(0),
        astoria(1),
        fx3s(2)
    }

CfprApStorageFcZoningType ::= TEXTUAL-CONVENTION
    STATUS        current
    DESCRIPTION
        ""
    SYNTAX        INTEGER
    {
        none(0),
        sist(1),
        simt(2)
    }

CfprApStorageFileSystemStatus ::= TEXTUAL-CONVENTION
    STATUS        current
    DESCRIPTION
        ""
    SYNTAX        INTEGER
    {
        unknown(0),
        clean(1),
        notClean(2),
        mounted(3),
        unmounted(4)
    }

CfprApStorageFlexFlashControllerId ::= TEXTUAL-CONVENTION
    STATUS        current
    DESCRIPTION
        ""
    SYNTAX        Gauge32 (1..64)

CfprApStorageIOType ::= TEXTUAL-CONVENTION
    STATUS        current
    DESCRIPTION
        ""
    SYNTAX        INTEGER
    {
        unknown(0),
        direct(1),
        cached(2)
    }

CfprApStorageIniGroupOperProtocol ::= TEXTUAL-CONVENTION
    STATUS        current
    DESCRIPTION
        ""
    SYNTAX        INTEGER
    {
        derived(0),
        fc(1),
        iscsi(2)
    }

CfprApStorageIniGroupOwner ::= TEXTUAL-CONVENTION
    STATUS        current
    DESCRIPTION
        ""
    SYNTAX        INTEGER
    {
        unknown(0),
        physical(1),
        policy(2),
        logical(4),
        connPolicy(8)
    }

CfprApStorageIniGroupProtocol ::= TEXTUAL-CONVENTION
    STATUS        current
    DESCRIPTION
        ""
    SYNTAX        INTEGER
    {
        derived(0),
        fc(1),
        iscsi(2)
    }

CfprApStorageKeyType ::= TEXTUAL-CONVENTION
    STATUS        current
    DESCRIPTION
        ""
    SYNTAX        INTEGER
    {
        initiator(1),
        target(2)
    }

CfprApStorageLearnCycleRequested ::= TEXTUAL-CONVENTION
    STATUS        current
    DESCRIPTION
        ""
    SYNTAX        INTEGER
    {
        unknown(0),
        true(1),
        false(2)
    }

CfprApStorageLearnMode ::= TEXTUAL-CONVENTION
    STATUS        current
    DESCRIPTION
        ""
    SYNTAX        INTEGER
    {
        unknown(0),
        auto(1),
        disabled(2),
        warn(3)
    }

CfprApStorageLinkSpeed ::= TEXTUAL-CONVENTION
    STATUS        current
    DESCRIPTION
        ""
    SYNTAX        INTEGER
    {
        unknown(0),
        n15Gbps(1),
        n3Gbps(2),
        n6Gbps(3),
        n12Gbps(4)
    }

CfprApStorageLocalDiskConfigFlexFlashRAIDReportingState ::= TEXTUAL-CONVENTION
    STATUS        current
    DESCRIPTION
        ""
    SYNTAX        INTEGER
    {
        disable(0),
        enable(1)
    }

CfprApStorageLocalDiskConfigFlexFlashState ::= TEXTUAL-CONVENTION
    STATUS        current
    DESCRIPTION
        ""
    SYNTAX        INTEGER
    {
        disable(0),
        enable(1)
    }

CfprApStorageLocalDiskMode ::= TEXTUAL-CONVENTION
    STATUS        current
    DESCRIPTION
        ""
    SYNTAX        INTEGER
    {
        noLocalStorage(1),
        singleDisk(2),
        dualDisk(3),
        raidStriped(4),
        raidMirrored(5),
        bestEffortMirrored(6),
        bestEffortStriped(7),
        anyConfiguration(8),
        noRaid(9),
        raidStripedParity(10),
        raidStripedDualParity(11),
        raidMirroredStriped(12),
        bestEffortStripedParity(13),
        bestEffortStripedDualParity(14),
        bestEffortMirroredStriped(15),
        raidStripedParityStriped(16),
        raidStripedDualParityStriped(17)
    }

CfprApStorageLocalDiskPartitionType ::= TEXTUAL-CONVENTION
    STATUS        current
    DESCRIPTION
        ""
    SYNTAX        INTEGER
    {
        none(1),
        swap(2),
        ext2(3),
        ext3(4),
        ntfs(5),
        fat32(6)
    }

CfprApStorageLunType ::= TEXTUAL-CONVENTION
    STATUS        current
    DESCRIPTION
        ""
    SYNTAX        INTEGER
    {
        unspecified(0),
        simple(1),
        mirror(2),
        stripe(3),
        raid(4),
        stripeParity(5),
        stripeDualParity(6),
        mirrorStripe(7),
        stripeParityStripe(8),
        stripeDualParityStripe(9)
    }

CfprApStorageOperState ::= TEXTUAL-CONVENTION
    STATUS        current
    DESCRIPTION
        ""
    SYNTAX        INTEGER
    {
        ok(0),
        misconfigured(1)
    }

CfprApStorageOperatingModeType ::= TEXTUAL-CONVENTION
    STATUS        current
    DESCRIPTION
        ""
    SYNTAX        INTEGER
    {
        unknown(0),
        mirror(1),
        util(2)
    }

CfprApStorageOperationRequestType ::= TEXTUAL-CONVENTION
    STATUS        current
    DESCRIPTION
        ""
    SYNTAX        INTEGER
    {
        unknown(0),
        format(1),
        reset(2),
        pair(3)
    }

CfprApStorageOperationState ::= TEXTUAL-CONVENTION
    STATUS        current
    DESCRIPTION
        ""
    SYNTAX        INTEGER
    {
        unknown(0),
        inProgress(1),
        completed(2),
        failed(3)
    }

CfprApStorageOperationStateType ::= TEXTUAL-CONVENTION
    STATUS        current
    DESCRIPTION
        ""
    SYNTAX        INTEGER
    {
        partitionNonMirrored(0),
        partitionMirrored(1),
        partitionMirroredSyncing(2),
        partitionMirroredErasing(3),
        partitionMirroredUpdating(4),
        partitionNonMirroredUpdating(5),
        partitionNonMirroredErasing(6),
        partitionMirroredSyncingFail(7),
        partitionMirroredErasingFail(8),
        partitionMirroredUpdatingFail(9),
        partitionNonMirroredUpdatingFail(10),
        partitionNonMirroredErasingFail(11),
        partitionMirroredSyncingSuccess(12),
        partitionMirroredErasingSuccess(13),
        partitionMirroredUpdatingSuccess(14),
        partitionNonMirroredUpdatingSuccess(15),
        partitionNonMirroredErasingSuccess(16),
        unknown(17)
    }

CfprApStorageOperationType ::= TEXTUAL-CONVENTION
    STATUS        current
    DESCRIPTION
        ""
    SYNTAX        INTEGER
    {
        reconstruction(0),
        relearning(1),
        patrolRead(2),
        consistencyCheck(3),
        rebuild(4),
        initialization(5)
    }

CfprApStoragePDriveStatus ::= TEXTUAL-CONVENTION
    STATUS        current
    DESCRIPTION
        ""
    SYNTAX        INTEGER
    {
        unknown(0),
        online(1),
        unconfiguredGood(2),
        globalHotSpare(3),
        dedicatedHotSpare(4),
        jbod(5),
        offline(6),
        rebuilding(7),
        copyback(8),
        failed(9),
        unconfiguredBad(10),
        predictiveFailure(11),
        disabledForRemoval(12),
        foreignConfiguration(13)
    }

CfprApStoragePathHA ::= TEXTUAL-CONVENTION
    STATUS        current
    DESCRIPTION
        ""
    SYNTAX        BITS
    {
        initiator(0),
        target(1),
        fabric(2)
    }

CfprApStoragePowerState ::= TEXTUAL-CONVENTION
    STATUS        current
    DESCRIPTION
        ""
    SYNTAX        INTEGER
    {
        unknown(0),
        active(1),
        powersave(2),
        transitioning(3)
    }

CfprApStorageProtocol ::= TEXTUAL-CONVENTION
    STATUS        current
    DESCRIPTION
        ""
    SYNTAX        INTEGER
    {
        derived(0),
        fc(1),
        iscsi(2)
    }

CfprApStorageRaidBatteryOperabilityQualifier ::= TEXTUAL-CONVENTION
    STATUS        current
    DESCRIPTION
        ""
    SYNTAX        INTEGER
    {
        unknown(0)
    }

CfprApStorageReadType ::= TEXTUAL-CONVENTION
    STATUS        current
    DESCRIPTION
        ""
    SYNTAX        INTEGER
    {
        unknown(0),
        readAhead(1),
        normal(2)
    }

CfprApStorageSystemFsmCurrentFsm ::= TEXTUAL-CONVENTION
    STATUS        current
    DESCRIPTION
        ""
    SYNTAX        INTEGER
    {
        nop(0),
        sync(325)
    }

CfprApStorageSystemFsmStageName ::= TEXTUAL-CONVENTION
    STATUS        current
    DESCRIPTION
        ""
    SYNTAX        INTEGER
    {
        nop(0),
        syncBegin(325),
        syncExecute(326),
        syncFail(784),
        syncSuccess(785)
    }

CfprApStorageSystemFsmTaskItem ::= TEXTUAL-CONVENTION
    STATUS        current
    DESCRIPTION
        ""
    SYNTAX        INTEGER
    {
        nop(0),
        sync(325)
    }

CfprApStorageTargetPath ::= TEXTUAL-CONVENTION
    STATUS        current
    DESCRIPTION
        ""
    SYNTAX        INTEGER
    {
        none(0),
        a(1),
        b(2),
        dual(3)
    }

CfprApStorageTechnology ::= TEXTUAL-CONVENTION
    STATUS        current
    DESCRIPTION
        ""
    SYNTAX        INTEGER
    {
        unspecified(0),
        hdd(1),
        ssd(2)
    }

CfprApStorageVDriveState ::= TEXTUAL-CONVENTION
    STATUS        current
    DESCRIPTION
        ""
    SYNTAX        INTEGER
    {
        unknown(0),
        optimal(1),
        cacheDegraded(2),
        partiallyDegraded(3),
        degraded(4),
        offline(5)
    }

CfprApStorageVsanRefSwitchId ::= TEXTUAL-CONVENTION
    STATUS        current
    DESCRIPTION
        ""
    SYNTAX        INTEGER
    {
        none(0),
        a(1),
        b(2),
        dual(3)
    }

CfprApSwAccessDomainLocale ::= TEXTUAL-CONVENTION
    STATUS        current
    DESCRIPTION
        ""
    SYNTAX        BITS
    {
        server(0),
        chassis(1),
        internal(2),
        external(3)
    }

CfprApSwAccessDomainType ::= TEXTUAL-CONVENTION
    STATUS        current
    DESCRIPTION
        ""
    SYNTAX        BITS
    {
        lan(0),
        san(1),
        ipc(2)
    }

CfprApSwAccessDomainFsmCurrentFsm ::= TEXTUAL-CONVENTION
    STATUS        current
    DESCRIPTION
        ""
    SYNTAX        INTEGER
    {
        nop(0),
        deploy(95)
    }

CfprApSwAccessDomainFsmStageName ::= TEXTUAL-CONVENTION
    STATUS        current
    DESCRIPTION
        ""
    SYNTAX        INTEGER
    {
        nop(0),
        deployBegin(95),
        deployUpdateConnectivity(96),
        deployFail(786),
        deploySuccess(787)
    }

CfprApSwAccessDomainFsmTaskItem ::= TEXTUAL-CONVENTION
    STATUS        current
    DESCRIPTION
        ""
    SYNTAX        INTEGER
    {
        nop(0),
        deploy(95)
    }

CfprApSwAccessEpLocale ::= TEXTUAL-CONVENTION
    STATUS        current
    DESCRIPTION
        ""
    SYNTAX        BITS
    {
        server(0),
        chassis(1),
        internal(2),
        external(3)
    }

CfprApSwAccessEpTransport ::= TEXTUAL-CONVENTION
    STATUS        current
    DESCRIPTION
        ""
    SYNTAX        BITS
    {
        ether(0),
        dce(1),
        fc(2)
    }

CfprApSwAdminState ::= TEXTUAL-CONVENTION
    STATUS        current
    DESCRIPTION
        ""
    SYNTAX        INTEGER
    {
        enabled(1),
        disabled(2)
    }

CfprApSwBorderDomainLocale ::= TEXTUAL-CONVENTION
    STATUS        current
    DESCRIPTION
        ""
    SYNTAX        BITS
    {
        server(0),
        chassis(1),
        internal(2),
        external(3)
    }

CfprApSwBorderEpLocale ::= TEXTUAL-CONVENTION
    STATUS        current
    DESCRIPTION
        ""
    SYNTAX        BITS
    {
        server(0),
        chassis(1),
        internal(2),
        external(3)
    }

CfprApSwBorderPcLocale ::= TEXTUAL-CONVENTION
    STATUS        current
    DESCRIPTION
        ""
    SYNTAX        BITS
    {
        server(0),
        chassis(1),
        internal(2),
        external(3)
    }

CfprApSwBreakoutType ::= TEXTUAL-CONVENTION
    STATUS        current
    DESCRIPTION
        ""
    SYNTAX        INTEGER
    {
        unknown(0),
        n10g4x(1)
    }

CfprApSwCIoEpIfType ::= TEXTUAL-CONVENTION
    STATUS        current
    DESCRIPTION
        ""
    SYNTAX        INTEGER
    {
        unknown(0),
        physical(1),
        aggregation(2),
        virtual(3),
        fabric(4)
    }

CfprApSwCardEnvStatsThresholded ::= TEXTUAL-CONVENTION
    STATUS        current
    DESCRIPTION
        ""
    SYNTAX        BITS
    {
        slotOutlet1(0),
        slotOutlet1Avg(1),
        slotOutlet1Max(2),
        slotOutlet1Min(3),
        slotOutlet2(4),
        slotOutlet2Avg(5),
        slotOutlet2Max(6),
        slotOutlet2Min(7),
        slotOutlet3(8),
        slotOutlet3Avg(9),
        slotOutlet3Max(10),
        slotOutlet3Min(11)
    }

CfprApSwCardEnvStatsHistThresholded ::= TEXTUAL-CONVENTION
    STATUS        current
    DESCRIPTION
        ""
    SYNTAX        BITS
    {
        slotOutlet1(0),
        slotOutlet1Avg(1),
        slotOutlet1Max(2),
        slotOutlet1Min(3),
        slotOutlet2(4),
        slotOutlet2Avg(5),
        slotOutlet2Max(6),
        slotOutlet2Min(7),
        slotOutlet3(8),
        slotOutlet3Avg(9),
        slotOutlet3Max(10),
        slotOutlet3Min(11)
    }

CfprApSwCimcId ::= TEXTUAL-CONVENTION
    STATUS        current
    DESCRIPTION
        ""
    SYNTAX        BITS
    {
        unused(1)
    }

CfprApSwConfMode ::= TEXTUAL-CONVENTION
    STATUS        current
    DESCRIPTION
        ""
    SYNTAX        INTEGER
    {
        none(0),
        inProgress(1),
        verifying(2),
        failed(3)
    }

CfprApSwConfigStatus ::= TEXTUAL-CONVENTION
    STATUS        current
    DESCRIPTION
        ""
    SYNTAX        INTEGER
    {
        none(1),
        noVlanComp(2)
    }

CfprApSwEnvStatsThresholded ::= TEXTUAL-CONVENTION
    STATUS        current
    DESCRIPTION
        ""
    SYNTAX        BITS
    {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31)
    }

CfprApSwEnvStatsHistThresholded ::= TEXTUAL-CONVENTION
    STATUS        current
    DESCRIPTION
        ""
    SYNTAX        BITS
    {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31)
    }

CfprApSwEstcEpLocale ::= TEXTUAL-CONVENTION
    STATUS        current
    DESCRIPTION
        ""
    SYNTAX        BITS
    {
        server(0),
        chassis(1),
        internal(2),
        external(3)
    }

CfprApSwEthEstcEpTransport ::= TEXTUAL-CONVENTION
    STATUS        current
    DESCRIPTION
        ""
    SYNTAX        BITS
    {
        ether(0),
        dce(1),
        fc(2)
    }

CfprApSwEthEstcPcTransport ::= TEXTUAL-CONVENTION
    STATUS        current
    DESCRIPTION
        ""
    SYNTAX        BITS
    {
        ether(0),
        dce(1),
        fc(2)
    }

CfprApSwEthFlowMonSessionTransport ::= TEXTUAL-CONVENTION
    STATUS        current
    DESCRIPTION
        ""
    SYNTAX        BITS
    {
        ether(0),
        dce(1),
        fc(2)
    }

CfprApSwEthFlowMonSessionType ::= TEXTUAL-CONVENTION
    STATUS        current
    DESCRIPTION
        ""
    SYNTAX        BITS
    {
        lan(0),
        san(1),
        ipc(2)
    }

CfprApSwEthLanBorderTransport ::= TEXTUAL-CONVENTION
    STATUS        current
    DESCRIPTION
        ""
    SYNTAX        BITS
    {
        ether(0),
        dce(1),
        fc(2)
    }

CfprApSwEthLanBorderFsmCurrentFsm ::= TEXTUAL-CONVENTION
    STATUS        current
    DESCRIPTION
        ""
    SYNTAX        INTEGER
    {
        nop(0),
        deploy(97)
    }

CfprApSwEthLanBorderFsmStageName ::= TEXTUAL-CONVENTION
    STATUS        current
    DESCRIPTION
        ""
    SYNTAX        INTEGER
    {
        nop(0),
        deployBegin(97),
        deployUpdateVlanGroups(98),
        deployUpdateConnectivity(99),
        deployFail(788),
        deploySuccess(789)
    }

CfprApSwEthLanBorderFsmTaskFlags ::= TEXTUAL-CONVENTION
    STATUS        current
    DESCRIPTION
        ""
    SYNTAX        BITS
    {
        samDmeSwEthLanBorderDeployVlanGroupConfig(11),
        samDmeSwEthLanBorderDeployVlanGroupRetry(12),
        samDmeSwEthLanBorderDeployPortConfig(13)
    }

CfprApSwEthLanBorderFsmTaskItem ::= TEXTUAL-CONVENTION
    STATUS        current
    DESCRIPTION
        ""
    SYNTAX        INTEGER
    {
        nop(0),
        deploy(97)
    }

CfprApSwEthLanEpTransport ::= TEXTUAL-CONVENTION
    STATUS        current
    DESCRIPTION
        ""
    SYNTAX        BITS
    {
        ether(0),
        dce(1),
        fc(2)
    }

CfprApSwEthLanEpUdldAdminState ::= TEXTUAL-CONVENTION
    STATUS        current
    DESCRIPTION
        ""
    SYNTAX        INTEGER
    {
        enabled(1),
        disabled(2)
    }

CfprApSwEthLanEpUdldMode ::= TEXTUAL-CONVENTION
    STATUS        current
    DESCRIPTION
        ""
    SYNTAX        INTEGER
    {
        normal(0),
        aggressive(1)
    }

CfprApSwEthLanFlowMonTransport ::= TEXTUAL-CONVENTION
    STATUS        current
    DESCRIPTION
        ""
    SYNTAX        BITS
    {
        ether(0),
        dce(1),
        fc(2)
    }

CfprApSwEthLanFlowMonExporterTransport ::= TEXTUAL-CONVENTION
    STATUS        current
    DESCRIPTION
        ""
    SYNTAX        BITS
    {
        ether(0),
        dce(1),
        fc(2)
    }

CfprApSwEthLanFlowMonExporterType ::= TEXTUAL-CONVENTION
    STATUS        current
    DESCRIPTION
        ""
    SYNTAX        BITS
    {
        lan(0),
        san(1),
        ipc(2)
    }

CfprApSwEthLanFlowMonFsmCurrentFsm ::= TEXTUAL-CONVENTION
    STATUS        current
    DESCRIPTION
        ""
    SYNTAX        INTEGER
    {
        nop(0),
        deploy(104)
    }

CfprApSwEthLanFlowMonFsmStageName ::= TEXTUAL-CONVENTION
    STATUS        current
    DESCRIPTION
        ""
    SYNTAX        INTEGER
    {
        nop(0),
        deployBegin(104),
        deployUpdateEthFlowMon(105),
        deployFail(790),
        deploySuccess(791)
    }

CfprApSwEthLanFlowMonFsmTaskItem ::= TEXTUAL-CONVENTION
    STATUS        current
    DESCRIPTION
        ""
    SYNTAX        INTEGER
    {
        nop(0),
        deploy(104)
    }

CfprApSwEthLanFlowMonitorTransport ::= TEXTUAL-CONVENTION
    STATUS        current
    DESCRIPTION
        ""
    SYNTAX        BITS
    {
        ether(0),
        dce(1),
        fc(2)
    }

CfprApSwEthLanFlowMonitorType ::= TEXTUAL-CONVENTION
    STATUS        current
    DESCRIPTION
        ""
    SYNTAX        BITS
    {
        lan(0),
        san(1),
        ipc(2)
    }

CfprApSwEthLanFlowRecordDefTransport ::= TEXTUAL-CONVENTION
    STATUS        current
    DESCRIPTION
        ""
    SYNTAX        BITS
    {
        ether(0),
        dce(1),
        fc(2)
    }

CfprApSwEthLanFlowRecordDefType ::= TEXTUAL-CONVENTION
    STATUS        current
    DESCRIPTION
        ""
    SYNTAX        BITS
    {
        lan(0),
        san(1),
        ipc(2)
    }

CfprApSwEthLanMonTransport ::= TEXTUAL-CONVENTION
    STATUS        current
    DESCRIPTION
        ""
    SYNTAX        BITS
    {
        ether(0),
        dce(1),
        fc(2)
    }

CfprApSwEthLanPcTransport ::= TEXTUAL-CONVENTION
    STATUS        current
    DESCRIPTION
        ""
    SYNTAX        BITS
    {
        ether(0),
        dce(1),
        fc(2)
    }

CfprApSwEthMonTransport ::= TEXTUAL-CONVENTION
    STATUS        current
    DESCRIPTION
        ""
    SYNTAX        BITS
    {
        ether(0),
        dce(1),
        fc(2)
    }

CfprApSwEthMonType ::= TEXTUAL-CONVENTION
    STATUS        current
    DESCRIPTION
        ""
    SYNTAX        BITS
    {
        lan(0),
        san(1),
        ipc(2)
    }

CfprApSwEthMonDestEpTransport ::= TEXTUAL-CONVENTION
    STATUS        current
    DESCRIPTION
        ""
    SYNTAX        BITS
    {
        ether(0),
        dce(1),
        fc(2)
    }

CfprApSwEthMonFsmCurrentFsm ::= TEXTUAL-CONVENTION
    STATUS        current
    DESCRIPTION
        ""
    SYNTAX        INTEGER
    {
        nop(0),
        deploy(439)
    }

CfprApSwEthMonFsmStageName ::= TEXTUAL-CONVENTION
    STATUS        current
    DESCRIPTION
        ""
    SYNTAX        INTEGER
    {
        nop(0),
        deployBegin(439),
        deployUpdateEthMon(440),
        deployFail(792),
        deploySuccess(793)
    }

CfprApSwEthMonFsmTaskItem ::= TEXTUAL-CONVENTION
    STATUS        current
    DESCRIPTION
        ""
    SYNTAX        INTEGER
    {
        nop(0),
        deploy(439)
    }

CfprApSwEthMonSrcEpTransport ::= TEXTUAL-CONVENTION
    STATUS        current
    DESCRIPTION
        ""
    SYNTAX        BITS
    {
        ether(0),
        dce(1),
        fc(2)
    }

CfprApSwEthTargetEpAdminState ::= TEXTUAL-CONVENTION
    STATUS        current
    DESCRIPTION
        ""
    SYNTAX        INTEGER
    {
        enabled(1),
        disabled(2)
    }

CfprApSwEthTargetEpTransport ::= TEXTUAL-CONVENTION
    STATUS        current
    DESCRIPTION
        ""
    SYNTAX        BITS
    {
        ether(0),
        dce(1),
        fc(2)
    }

CfprApSwExtUtilityFsmCurrentFsm ::= TEXTUAL-CONVENTION
    STATUS        current
    DESCRIPTION
        ""
    SYNTAX        INTEGER
    {
        nop(0),
        confPortBreakout(114)
    }

CfprApSwExtUtilityFsmStageName ::= TEXTUAL-CONVENTION
    STATUS        current
    DESCRIPTION
        ""
    SYNTAX        INTEGER
    {
        nop(0),
        confPortBreakoutBegin(114),
        confPortBreakoutPortInventorySwA(115),
        confPortBreakoutPortInventorySwB(116),
        confPortBreakoutConfigSwA(117),
        confPortBreakoutConfigSwB(118),
        confPortBreakoutVerifyBreakoutConfig(119),
        confPortBreakoutSuccess(120),
        confPortBreakoutFail(121)
    }

CfprApSwExtUtilityFsmTaskItem ::= TEXTUAL-CONVENTION
    STATUS        current
    DESCRIPTION
        ""
    SYNTAX        INTEGER
    {
        nop(0),
        confPortBreakout(114)
    }

CfprApSwFabricRole ::= TEXTUAL-CONVENTION
    STATUS        current
    DESCRIPTION
        ""
    SYNTAX        INTEGER
    {
        npu(0),
        cpu(1)
    }

CfprApSwFabricZoneNsAllocStatus ::= TEXTUAL-CONVENTION
    STATUS        current
    DESCRIPTION
        ""
    SYNTAX        INTEGER
    {
        available(0),
        full(1)
    }

CfprApSwFcEstcEpTransport ::= TEXTUAL-CONVENTION
    STATUS        current
    DESCRIPTION
        ""
    SYNTAX        BITS
    {
        ether(0),
        dce(1),
        fc(2)
    }

CfprApSwFcMonTransport ::= TEXTUAL-CONVENTION
    STATUS        current
    DESCRIPTION
        ""
    SYNTAX        BITS
    {
        ether(0),
        dce(1),
        fc(2)
    }

CfprApSwFcMonType ::= TEXTUAL-CONVENTION
    STATUS        current
    DESCRIPTION
        ""
    SYNTAX        BITS
    {
        lan(0),
        san(1),
        ipc(2)
    }

CfprApSwFcMonDestEpTransport ::= TEXTUAL-CONVENTION
    STATUS        current
    DESCRIPTION
        ""
    SYNTAX        BITS
    {
        ether(0),
        dce(1),
        fc(2)
    }

CfprApSwFcMonFsmCurrentFsm ::= TEXTUAL-CONVENTION
    STATUS        current
    DESCRIPTION
        ""
    SYNTAX        INTEGER
    {
        nop(0),
        deploy(441)
    }

CfprApSwFcMonFsmStageName ::= TEXTUAL-CONVENTION
    STATUS        current
    DESCRIPTION
        ""
    SYNTAX        INTEGER
    {
        nop(0),
        deployBegin(441),
        deployUpdateFcMon(442),
        deployFail(794),
        deploySuccess(795)
    }

CfprApSwFcMonFsmTaskItem ::= TEXTUAL-CONVENTION
    STATUS        current
    DESCRIPTION
        ""
    SYNTAX        INTEGER
    {
        nop(0),
        deploy(441)
    }

CfprApSwFcMonSrcEpTransport ::= TEXTUAL-CONVENTION
    STATUS        current
    DESCRIPTION
        ""
    SYNTAX        BITS
    {
        ether(0),
        dce(1),
        fc(2)
    }

CfprApSwFcSanBorderTransport ::= TEXTUAL-CONVENTION
    STATUS        current
    DESCRIPTION
        ""
    SYNTAX        BITS
    {
        ether(0),
        dce(1),
        fc(2)
    }

CfprApSwFcSanBorderUplinkTrunking ::= TEXTUAL-CONVENTION
    STATUS        current
    DESCRIPTION
        ""
    SYNTAX        INTEGER
    {
        disabled(0),
        enabled(1)
    }

CfprApSwFcSanBorderFsmCurrentFsm ::= TEXTUAL-CONVENTION
    STATUS        current
    DESCRIPTION
        ""
    SYNTAX        INTEGER
    {
        nop(0),
        deploy(100),
        activateZoneSet(122)
    }

CfprApSwFcSanBorderFsmStageName ::= TEXTUAL-CONVENTION
    STATUS        current
    DESCRIPTION
        ""
    SYNTAX        INTEGER
    {
        nop(0),
        deployBegin(100),
        deployUpdateConnectivity(101),
        activateZoneSetBegin(122),
        activateZoneSetUpdateZones(123),
        activateZoneSetFail(796),
        activateZoneSetSuccess(797),
        deployFail(798),
        deploySuccess(799)
    }

CfprApSwFcSanBorderFsmTaskItem ::= TEXTUAL-CONVENTION
    STATUS        current
    DESCRIPTION
        ""
    SYNTAX        INTEGER
    {
        nop(0),
        deploy(100),
        activateZoneSet(122)
    }

CfprApSwFcSanEpTransport ::= TEXTUAL-CONVENTION
    STATUS        current
    DESCRIPTION
        ""
    SYNTAX        BITS
    {
        ether(0),
        dce(1),
        fc(2)
    }

CfprApSwFcSanMonTransport ::= TEXTUAL-CONVENTION
    STATUS        current
    DESCRIPTION
        ""
    SYNTAX        BITS
    {
        ether(0),
        dce(1),
        fc(2)
    }

CfprApSwFcSanPcTransport ::= TEXTUAL-CONVENTION
    STATUS        current
    DESCRIPTION
        ""
    SYNTAX        BITS
    {
        ether(0),
        dce(1),
        fc(2)
    }

CfprApSwFcServerZoneGroupLc ::= TEXTUAL-CONVENTION
    STATUS        current
    DESCRIPTION
        ""
    SYNTAX        INTEGER
    {
        available(0),
        allocated(1),
        deallocated(2),
        repurposed(3)
    }

CfprApSwFcZoneLc ::= TEXTUAL-CONVENTION
    STATUS        current
    DESCRIPTION
        ""
    SYNTAX        INTEGER
    {
        available(0),
        allocated(1),
        deallocated(2),
        repurposed(3)
    }

CfprApSwFcZoneMemberLc ::= TEXTUAL-CONVENTION
    STATUS        current
    DESCRIPTION
        ""
    SYNTAX        INTEGER
    {
        available(0),
        allocated(1),
        deallocated(2),
        repurposed(3)
    }

CfprApSwFcZoneSetLc ::= TEXTUAL-CONVENTION
    STATUS        current
    DESCRIPTION
        ""
    SYNTAX        INTEGER
    {
        available(0),
        allocated(1),
        deallocated(2),
        repurposed(3)
    }

CfprApSwFcoeEstcEpTransport ::= TEXTUAL-CONVENTION
    STATUS        current
    DESCRIPTION
        ""
    SYNTAX        BITS
    {
        ether(0),
        dce(1),
        fc(2)
    }

CfprApSwFcoeSanEpTransport ::= TEXTUAL-CONVENTION
    STATUS        current
    DESCRIPTION
        ""
    SYNTAX        BITS
    {
        ether(0),
        dce(1),
        fc(2)
    }

CfprApSwFcoeSanEpUdldAdminState ::= TEXTUAL-CONVENTION
    STATUS        current
    DESCRIPTION
        ""
    SYNTAX        INTEGER
    {
        enabled(1),
        disabled(2)
    }

CfprApSwFcoeSanEpUdldMode ::= TEXTUAL-CONVENTION
    STATUS        current
    DESCRIPTION
        ""
    SYNTAX        INTEGER
    {
        normal(0),
        aggressive(1)
    }

CfprApSwFcoeSanPcTransport ::= TEXTUAL-CONVENTION
    STATUS        current
    DESCRIPTION
        ""
    SYNTAX        BITS
    {
        ether(0),
        dce(1),
        fc(2)
    }

CfprApSwFlowMonitorAdminState ::= TEXTUAL-CONVENTION
    STATUS        current
    DESCRIPTION
        ""
    SYNTAX        INTEGER
    {
        enabled(1),
        disabled(2)
    }

CfprApSwLanBorderType ::= TEXTUAL-CONVENTION
    STATUS        current
    DESCRIPTION
        ""
    SYNTAX        BITS
    {
        lan(0),
        san(1),
        ipc(2)
    }

CfprApSwLanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApSwLanEpType ::= TEXTUAL-CONVENTION
    STATUS        current
    DESCRIPTION
        ""
    SYNTAX        BITS
    {
        lan(0),
        san(1),
        ipc(2)
    }

CfprApSwLanMonType ::= TEXTUAL-CONVENTION
    STATUS        current
    DESCRIPTION
        ""
    SYNTAX        BITS
    {
        lan(0),
        san(1),
        ipc(2)
    }

CfprApSwLanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApSwLanPcType ::= TEXTUAL-CONVENTION
    STATUS        current
    DESCRIPTION
        ""
    SYNTAX        BITS
    {
        lan(0),
        san(1),
        ipc(2)
    }

CfprApSwMonAdminState ::= TEXTUAL-CONVENTION
    STATUS        current
    DESCRIPTION
        ""
    SYNTAX        INTEGER
    {
        enabled(1),
        disabled(2)
    }

CfprApSwMonDomainLocale ::= TEXTUAL-CONVENTION
    STATUS        current
    DESCRIPTION
        ""
    SYNTAX        BITS
    {
        server(0),
        chassis(1),
        internal(2),
        external(3)
    }

CfprApSwMonLifeCycle ::= TEXTUAL-CONVENTION
    STATUS        current
    DESCRIPTION
        ""
    SYNTAX        INTEGER
    {
        normal(1),
        new(2),
        deleted(3)
    }

CfprApSwMonSrcEpLocale ::= TEXTUAL-CONVENTION
    STATUS        current
    DESCRIPTION
        ""
    SYNTAX        BITS
    {
        server(0),
        chassis(1),
        internal(2),
        external(3)
    }

CfprApSwNFConfigStatus ::= TEXTUAL-CONVENTION
    STATUS        current
    DESCRIPTION
        ""
    SYNTAX        INTEGER
    {
        ok(1),
        incomplete(2)
    }

CfprApSwNetflowExporterProtocol ::= TEXTUAL-CONVENTION
    STATUS        current
    DESCRIPTION
        ""
    SYNTAX        INTEGER
    {
        netflow(1)
    }

CfprApSwNetflowMonSessionProtocol ::= TEXTUAL-CONVENTION
    STATUS        current
    DESCRIPTION
        ""
    SYNTAX        INTEGER
    {
        netflow(1)
    }

CfprApSwNetflowMonitorProtocol ::= TEXTUAL-CONVENTION
    STATUS        current
    DESCRIPTION
        ""
    SYNTAX        INTEGER
    {
        netflow(1)
    }

CfprApSwNetflowRecordDefProtocol ::= TEXTUAL-CONVENTION
    STATUS        current
    DESCRIPTION
        ""
    SYNTAX        INTEGER
    {
        netflow(1)
    }

CfprApSwPIoEpIfType ::= TEXTUAL-CONVENTION
    STATUS        current
    DESCRIPTION
        ""
    SYNTAX        INTEGER
    {
        unknown(0),
        physical(1),
        aggregation(2),
        virtual(3),
        fabric(4)
    }

CfprApSwPIoEpLc ::= TEXTUAL-CONVENTION
    STATUS        current
    DESCRIPTION
        ""
    SYNTAX        INTEGER
    {
        available(0),
        allocated(1),
        deallocated(2),
        repurposed(3),
        pending(4)
    }

CfprApSwPeerStatus ::= TEXTUAL-CONVENTION
    STATUS        current
    DESCRIPTION
        ""
    SYNTAX        INTEGER
    {
        existing(1),
        nonexisting(2)
    }

CfprApSwPhysFsmCurrentFsm ::= TEXTUAL-CONVENTION
    STATUS        current
    DESCRIPTION
        ""
    SYNTAX        INTEGER
    {
        nop(0),
        confPhysical(106)
    }

CfprApSwPhysFsmStageName ::= TEXTUAL-CONVENTION
    STATUS        current
    DESCRIPTION
        ""
    SYNTAX        INTEGER
    {
        nop(0),
        confPhysicalBegin(106),
        confPhysicalPortInventorySwA(107),
        confPhysicalPortInventorySwB(108),
        confPhysicalConfigSwA(109),
        confPhysicalConfigSwB(110),
        confPhysicalVerifyPhysConfig(111),
        confPhysicalSuccess(112),
        confPhysicalFail(113)
    }

CfprApSwPhysFsmTaskItem ::= TEXTUAL-CONVENTION
    STATUS        current
    DESCRIPTION
        ""
    SYNTAX        INTEGER
    {
        nop(0),
        confPhysical(106)
    }

CfprApSwPktCaptureLifeCycle ::= TEXTUAL-CONVENTION
    STATUS        current
    DESCRIPTION
        ""
    SYNTAX        INTEGER
    {
        normal(1),
        new(2),
        deleted(3)
    }

CfprApSwPortBreakoutPortId ::= TEXTUAL-CONVENTION
    STATUS        current
    DESCRIPTION
        ""
    SYNTAX        Gauge32 (1..4)

CfprApSwPortBreakoutSlotId ::= TEXTUAL-CONVENTION
    STATUS        current
    DESCRIPTION
        ""
    SYNTAX        Gauge32 (2..3)

CfprApSwSanBorderType ::= TEXTUAL-CONVENTION
    STATUS        current
    DESCRIPTION
        ""
    SYNTAX        BITS
    {
        lan(0),
        san(1),
        ipc(2)
    }

CfprApSwSanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApSwSanEpType ::= TEXTUAL-CONVENTION
    STATUS        current
    DESCRIPTION
        ""
    SYNTAX        BITS
    {
        lan(0),
        san(1),
        ipc(2)
    }

CfprApSwSanMonType ::= TEXTUAL-CONVENTION
    STATUS        current
    DESCRIPTION
        ""
    SYNTAX        BITS
    {
        lan(0),
        san(1),
        ipc(2)
    }

CfprApSwSanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprApSwSanPcType ::= TEXTUAL-CONVENTION
    STATUS        current
    DESCRIPTION
        ""
    SYNTAX        BITS
    {
        lan(0),
        san(1),
        ipc(2)
    }

CfprApSwSspEthLanMonTransport ::= TEXTUAL-CONVENTION
    STATUS        current
    DESCRIPTION
        ""
    SYNTAX        BITS
    {
        ether(0),
        dce(1),
        fc(2)
    }

CfprApSwSspEthMonTransport ::= TEXTUAL-CONVENTION
    STATUS        current
    DESCRIPTION
        ""
    SYNTAX        BITS
    {
        ether(0),
        dce(1),
        fc(2)
    }

CfprApSwSspEthMonType ::= TEXTUAL-CONVENTION
    STATUS        current
    DESCRIPTION
        ""
    SYNTAX        BITS
    {
        lan(0),
        san(1),
        ipc(2)
    }

CfprApSwSspEthMonFsmCurrentFsm ::= TEXTUAL-CONVENTION
    STATUS        current
    DESCRIPTION
        ""
    SYNTAX        INTEGER
    {
        nop(0),
        deploy(443)
    }

CfprApSwSspEthMonFsmStageName ::= TEXTUAL-CONVENTION
    STATUS        current
    DESCRIPTION
        ""
    SYNTAX        INTEGER
    {
        nop(0),
        deployBegin(443),
        deployUpdateSspEthMon(444),
        deployFail(800),
        deploySuccess(801)
    }

CfprApSwSspEthMonFsmTaskItem ::= TEXTUAL-CONVENTION
    STATUS        current
    DESCRIPTION
        ""
    SYNTAX        INTEGER
    {
        nop(0),
        deploy(443)
    }

CfprApSwSspEthMonSrcPhyEpFsmCurrentFsm ::= TEXTUAL-CONVENTION
    STATUS        current
    DESCRIPTION
        ""
    SYNTAX        INTEGER
    {
        nop(0),
        delete(445)
    }

CfprApSwSspEthMonSrcPhyEpFsmStageName ::= TEXTUAL-CONVENTION
    STATUS        current
    DESCRIPTION
        ""
    SYNTAX        INTEGER
    {
        nop(0),
        deleteBegin(445),
        deleteDeletePcapFile(446),
        deleteFail(802),
        deleteSuccess(803)
    }

CfprApSwSspEthMonSrcPhyEpFsmTaskItem ::= TEXTUAL-CONVENTION
    STATUS        current
    DESCRIPTION
        ""
    SYNTAX        INTEGER
    {
        nop(0),
        delete(445)
    }

CfprApSwSspLanMonType ::= TEXTUAL-CONVENTION
    STATUS        current
    DESCRIPTION
        ""
    SYNTAX        BITS
    {
        lan(0),
        san(1),
        ipc(2)
    }

CfprApSwSspMonAdminState ::= TEXTUAL-CONVENTION
    STATUS        current
    DESCRIPTION
        ""
    SYNTAX        INTEGER
    {
        enabled(1),
        disabled(2)
    }

CfprApSwSspMonDelPcap ::= TEXTUAL-CONVENTION
    STATUS        current
    DESCRIPTION
        ""
    SYNTAX        INTEGER
    {
        enabled(1),
        disabled(2)
    }

CfprApSwSspMonDomainLocale ::= TEXTUAL-CONVENTION
    STATUS        current
    DESCRIPTION
        ""
    SYNTAX        BITS
    {
        server(0),
        chassis(1),
        internal(2),
        external(3)
    }

CfprApSwSubGroupAggrPortId ::= TEXTUAL-CONVENTION
    STATUS        current
    DESCRIPTION
        ""
    SYNTAX        Gauge32 (1..48)

CfprApSwSubGroupSlotId ::= TEXTUAL-CONVENTION
    STATUS        current
    DESCRIPTION
        ""
    SYNTAX        Gauge32 (1..4)

CfprApSwSystemStatsThresholded ::= TEXTUAL-CONVENTION
    STATUS        current
    DESCRIPTION
        ""
    SYNTAX        BITS
    {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CfprApSwSystemStatsHistThresholded ::= TEXTUAL-CONVENTION
    STATUS        current
    DESCRIPTION
        ""
    SYNTAX        BITS
    {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CfprApSwTargetEpType ::= TEXTUAL-CONVENTION
    STATUS        current
    DESCRIPTION
        ""
    SYNTAX        BITS
    {
        lan(0),
        san(1),
        ipc(2)
    }

CfprApSwUlanPurpose ::= TEXTUAL-CONVENTION
    STATUS        current
    DESCRIPTION
        ""
    SYNTAX        INTEGER
    {
        management(1),
        boot(2),
        reserved1(3),
        reserved2(4)
    }

CfprApSwUtilityDomainLocale ::= TEXTUAL-CONVENTION
    STATUS        current
    DESCRIPTION
        ""
    SYNTAX        BITS
    {
        server(0),
        chassis(1),
        internal(2),
        external(3)
    }

CfprApSwUtilityDomainType ::= TEXTUAL-CONVENTION
    STATUS        current
    DESCRIPTION
        ""
    SYNTAX        BITS
    {
        lan(0),
        san(1),
        ipc(2)
    }

CfprApSwUtilityDomainFsmCurrentFsm ::= TEXTUAL-CONVENTION
    STATUS        current
    DESCRIPTION
        ""
    SYNTAX        INTEGER
    {
        nop(0),
        deploy(102)
    }

CfprApSwUtilityDomainFsmStageName ::= TEXTUAL-CONVENTION
    STATUS        current
    DESCRIPTION
        ""
    SYNTAX        INTEGER
    {
        nop(0),
        deployBegin(102),
        deployUpdateConnectivity(103),
        deployFail(804),
        deploySuccess(805)
    }

CfprApSwUtilityDomainFsmTaskItem ::= TEXTUAL-CONVENTION
    STATUS        current
    DESCRIPTION
        ""
    SYNTAX        INTEGER
    {
        nop(0),
        deploy(102)
    }

CfprApSwVlanLc ::= TEXTUAL-CONVENTION
    STATUS        current
    DESCRIPTION
        ""
    SYNTAX        INTEGER
    {
        available(0),
        allocated(1),
        deallocated(2),
        repurposed(3),
        pending(4),
        provisioned(5)
    }

CfprApSwVlanCompType ::= TEXTUAL-CONVENTION
    STATUS        current
    DESCRIPTION
        ""
    SYNTAX        INTEGER
    {
        included(1),
        excluded(2)
    }

CfprApSwVlanConfigStatusType ::= TEXTUAL-CONVENTION
    STATUS        current
    DESCRIPTION
        ""
    SYNTAX        INTEGER
    {
        applied(1),
        unApplied(2)
    }

CfprApSwVlanGroupType ::= TEXTUAL-CONVENTION
    STATUS        current
    DESCRIPTION
        ""
    SYNTAX        INTEGER
    {
        compressed(1),
        uncompressed(2)
    }

CfprApSwVlanPortNsAllocStatus ::= TEXTUAL-CONVENTION
    STATUS        current
    DESCRIPTION
        ""
    SYNTAX        INTEGER
    {
        available(0),
        exceeded(1)
    }

CfprApSysdebugAutoCoreFileExportTargetProto ::= TEXTUAL-CONVENTION
    STATUS        current
    DESCRIPTION
        ""
    SYNTAX        INTEGER
    {
        none(0),
        ftp(1),
        tftp(2),
        scp(3),
        http(4),
        sftp(5),
        nfsCopy(6)
    }

CfprApSysdebugAutoCoreFileExportTargetFsmCurrentFsm ::= TEXTUAL-CONVENTION
    STATUS        current
    DESCRIPTION
        ""
    SYNTAX        INTEGER
    {
        nop(0),
        configure(363)
    }

CfprApSysdebugAutoCoreFileExportTargetFsmStageName ::= TEXTUAL-CONVENTION
    STATUS        current
    DESCRIPTION
        ""
    SYNTAX        INTEGER
    {
        nop(0),
        configureBegin(363),
        configureLocal(364),
        configurePeer(365),
        configureFail(808),
        configureSuccess(809)
    }

CfprApSysdebugAutoCoreFileExportTargetFsmTaskItem ::= TEXTUAL-CONVENTION
    STATUS        current
    DESCRIPTION
        ""
    SYNTAX        INTEGER
    {
        nop(0),
        configure(363)
    }

CfprApSysdebugBackupBehaviorInterval ::= TEXTUAL-CONVENTION
    STATUS        current
    DESCRIPTION
        ""
    SYNTAX        INTEGER
    {
        never(0),
        n1hour(3600),
        n2hours(7200),
        n4hours(14400),
        n8hours(28800),
        n24hours(86400),
        n1week(604800),
        n1month(2592000)
    }

CfprApSysdebugBackupBehaviorProto ::= TEXTUAL-CONVENTION
    STATUS        current
    DESCRIPTION
        ""
    SYNTAX        INTEGER
    {
        none(0),
        ftp(1),
        tftp(2),
        scp(3),
        http(4),
        sftp(5),
        nfsCopy(6)
    }

CfprApSysdebugBackupFormat ::= TEXTUAL-CONVENTION
    STATUS        current
    DESCRIPTION
        ""
    SYNTAX        INTEGER
    {
        ascii(1),
        binary(2)
    }

CfprApSysdebugCoreExportStatus ::= TEXTUAL-CONVENTION
    STATUS        current
    DESCRIPTION
        ""
    SYNTAX        INTEGER
    {
        success(1),
        failure(2)
    }

CfprApSysdebugCoreFileAdminState ::= TEXTUAL-CONVENTION
    STATUS        current
    DESCRIPTION
        ""
    SYNTAX        INTEGER
    {
        init(0),
        prepareDownload(1),
        downloaded(2)
    }

CfprApSysdebugCoreFileOperState ::= TEXTUAL-CONVENTION
    STATUS        current
    DESCRIPTION
        ""
    SYNTAX        INTEGER
    {
        unavailable(0),
        available(1),
        availableOnSubordinate(2),
        inProgress(3),
        failed(4)
    }

CfprApSysdebugCoreFsmCurrentFsm ::= TEXTUAL-CONVENTION
    STATUS        current
    DESCRIPTION
        ""
    SYNTAX        INTEGER
    {
        nop(0),
        download(376)
    }

CfprApSysdebugCoreFsmStageName ::= TEXTUAL-CONVENTION
    STATUS        current
    DESCRIPTION
        ""
    SYNTAX        INTEGER
    {
        nop(0),
        downloadBegin(376),
        downloadCopySub(377),
        downloadCopyPrimary(378),
        downloadDeleteSub(379),
        downloadDeletePrimary(380),
        downloadFail(810),
        downloadSuccess(811)
    }

CfprApSysdebugCoreFsmTaskItem ::= TEXTUAL-CONVENTION
    STATUS        current
    DESCRIPTION
        ""
    SYNTAX        INTEGER
    {
        nop(0),
        download(376)
    }

CfprApSysdebugEpLogAdminState ::= TEXTUAL-CONVENTION
    STATUS        current
    DESCRIPTION
        ""
    SYNTAX        INTEGER
    {
        policy(0),
        backup(1),
        clear(2)
    }

CfprApSysdebugEpLogBackupAction ::= TEXTUAL-CONVENTION
    STATUS        current
    DESCRIPTION
        ""
    SYNTAX        BITS
    {
        logFull(0),
        onClear(1),
        timer(2),
        onAssocChange(3)
    }

CfprApSysdebugEpLogCapacity ::= TEXTUAL-CONVENTION
    STATUS        current
    DESCRIPTION
        ""
    SYNTAX        INTEGER
    {
        unknown(0),
        available(1),
        low(2),
        veryLow(3),
        full(4)
    }

CfprApSysdebugEpLogType ::= TEXTUAL-CONVENTION
    STATUS        current
    DESCRIPTION
        ""
    SYNTAX        INTEGER
    {
        sel(1),
        obfl(2),
        syslog(3)
    }

CfprApSysdebugExportStatus ::= TEXTUAL-CONVENTION
    STATUS        current
    DESCRIPTION
        ""
    SYNTAX        INTEGER
    {
        success(1),
        failure(2)
    }

CfprApSysdebugLogControlDomainEnum ::= TEXTUAL-CONVENTION
    STATUS        current
    DESCRIPTION
        ""
    SYNTAX        INTEGER
    {
        sysmgmt(0)
    }

CfprApSysdebugLogControlEpFsmCurrentFsm ::= TEXTUAL-CONVENTION
    STATUS        current
    DESCRIPTION
        ""
    SYNTAX        INTEGER
    {
        nop(0),
        logControlPersist(381)
    }

CfprApSysdebugLogControlEpFsmStageName ::= TEXTUAL-CONVENTION
    STATUS        current
    DESCRIPTION
        ""
    SYNTAX        INTEGER
    {
        nop(0),
        logControlPersistBegin(381),
        logControlPersistLocal(382),
        logControlPersistPeer(383),
        logControlPersistFail(812),
        logControlPersistSuccess(813)
    }

CfprApSysdebugLogControlEpFsmTaskItem ::= TEXTUAL-CONVENTION
    STATUS        current
    DESCRIPTION
        ""
    SYNTAX        INTEGER
    {
        nop(0),
        logControlPersist(381)
    }

CfprApSysdebugLogControlLevel ::= TEXTUAL-CONVENTION
    STATUS        current
    DESCRIPTION
        ""
    SYNTAX        INTEGER
    {
        debug0(0),
        debug1(1),
        debug2(2),
        debug3(3),
        debug4(4),
        info(5),
        warn(6),
        minor(7),
        major(8),
        crit(9)
    }

CfprApSysdebugLogExportPolicyProto ::= TEXTUAL-CONVENTION
    STATUS        current
    DESCRIPTION
        ""
    SYNTAX        INTEGER
    {
        none(0),
        ftp(1),
        tftp(2),
        scp(3),
        http(4),
        sftp(5),
        nfsCopy(6)
    }

CfprApSysdebugLogExportPolicyFsmCurrentFsm ::= TEXTUAL-CONVENTION
    STATUS        current
    DESCRIPTION
        ""
    SYNTAX        INTEGER
    {
        nop(0),
        configure(360)
    }

CfprApSysdebugLogExportPolicyFsmStageName ::= TEXTUAL-CONVENTION
    STATUS        current
    DESCRIPTION
        ""
    SYNTAX        INTEGER
    {
        nop(0),
        configureBegin(360),
        configureLocal(361),
        configurePeer(362),
        configureFail(814),
        configureSuccess(815)
    }

CfprApSysdebugLogExportPolicyFsmTaskItem ::= TEXTUAL-CONVENTION
    STATUS        current
    DESCRIPTION
        ""
    SYNTAX        INTEGER
    {
        nop(0),
        configure(360)
    }

CfprApSysdebugMEpLogOperState ::= TEXTUAL-CONVENTION
    STATUS        current
    DESCRIPTION
        ""
    SYNTAX        INTEGER
    {
        ok(0),
        permissionDeniedError(1),
        remoteCommunicationError(2),
        bmcCommunicationError(3),
        internalUcsmError(4)
    }

CfprApSysdebugManualCoreFileExportTargetAdminState ::= TEXTUAL-CONVENTION
    STATUS        current
    DESCRIPTION
        ""
    SYNTAX        INTEGER
    {
        enabled(1),
        disabled(2)
    }

CfprApSysdebugManualCoreFileExportTargetProto ::= TEXTUAL-CONVENTION
    STATUS        current
    DESCRIPTION
        ""
    SYNTAX        INTEGER
    {
        none(0),
        ftp(1),
        tftp(2),
        scp(3),
        http(4),
        sftp(5),
        nfsCopy(6)
    }

CfprApSysdebugManualCoreFileExportTargetFsmCurrentFsm ::= TEXTUAL-CONVENTION
    STATUS        current
    DESCRIPTION
        ""
    SYNTAX        INTEGER
    {
        nop(0),
        export(358)
    }

CfprApSysdebugManualCoreFileExportTargetFsmStageName ::= TEXTUAL-CONVENTION
    STATUS        current
    DESCRIPTION
        ""
    SYNTAX        INTEGER
    {
        nop(0),
        exportBegin(358),
        exportExecute(359),
        exportFail(816),
        exportSuccess(817)
    }

CfprApSysdebugManualCoreFileExportTargetFsmTaskItem ::= TEXTUAL-CONVENTION
    STATUS        current
    DESCRIPTION
        ""
    SYNTAX        INTEGER
    {
        nop(0),
        export(358)
    }

CfprApSysdebugTSCmdOptMajorType ::= TEXTUAL-CONVENTION
    STATUS        current
    DESCRIPTION
        ""
    SYNTAX        INTEGER
    {
        chassis(0),
        fex(1),
        server(2),
        ucsm(3),
        ucsmMgmt(4)
    }

CfprApSysdebugTechSupportAdminState ::= TEXTUAL-CONVENTION
    STATUS        current
    DESCRIPTION
        ""
    SYNTAX        INTEGER
    {
        init(0),
        start(1),
        created(2),
        prepareDownload(3),
        delete(4)
    }

CfprApSysdebugTechSupportFsmCurrentFsm ::= TEXTUAL-CONVENTION
    STATUS        current
    DESCRIPTION
        ""
    SYNTAX        INTEGER
    {
        nop(0),
        initiate(366),
        deleteTechSupFile(368),
        download(371)
    }

CfprApSysdebugTechSupportFsmStageName ::= TEXTUAL-CONVENTION
    STATUS        current
    DESCRIPTION
        ""
    SYNTAX        INTEGER
    {
        nop(0),
        initiateBegin(366),
        initiateLocal(367),
        deleteTechSupFileBegin(368),
        deleteTechSupFileLocal(369),
        deleteTechSupFilePeer(370),
        downloadBegin(371),
        downloadCopySub(372),
        downloadCopyPrimary(373),
        downloadDeleteSub(374),
        downloadDeletePrimary(375),
        deleteTechSupFileFail(818),
        deleteTechSupFileSuccess(819),
        downloadFail(820),
        downloadSuccess(821),
        initiateFail(822),
        initiateSuccess(823)
    }

CfprApSysdebugTechSupportFsmTaskItem ::= TEXTUAL-CONVENTION
    STATUS        current
    DESCRIPTION
        ""
    SYNTAX        INTEGER
    {
        nop(0),
        initiate(366),
        deleteTechSupFile(368),
        download(371)
    }

CfprApSysdebugTechSupportOperState ::= TEXTUAL-CONVENTION
    STATUS        current
    DESCRIPTION
        ""
    SYNTAX        INTEGER
    {
        unavailable(0),
        available(1),
        availableOnSubordinate(2),
        inProgress(3),
        failed(4)
    }

CfprApSysfileExporterPostAction ::= TEXTUAL-CONVENTION
    STATUS        current
    DESCRIPTION
        ""
    SYNTAX        INTEGER
    {
        none(0),
        remove(1)
    }

CfprApSysfileMutationAction ::= TEXTUAL-CONVENTION
    STATUS        current
    DESCRIPTION
        ""
    SYNTAX        INTEGER
    {
        none(0),
        remove(1)
    }

CfprApSysfileMutationFsmCurrentFsm ::= TEXTUAL-CONVENTION
    STATUS        current
    DESCRIPTION
        ""
    SYNTAX        INTEGER
    {
        nop(0),
        single(327),
        global(329)
    }

CfprApSysfileMutationFsmStageName ::= TEXTUAL-CONVENTION
    STATUS        current
    DESCRIPTION
        ""
    SYNTAX        INTEGER
    {
        nop(0),
        singleBegin(327),
        singleExecute(328),
        globalBegin(329),
        globalLocal(330),
        globalPeer(331),
        globalFail(824),
        globalSuccess(825),
        singleFail(826),
        singleSuccess(827)
    }

CfprApSysfileMutationFsmTaskItem ::= TEXTUAL-CONVENTION
    STATUS        current
    DESCRIPTION
        ""
    SYNTAX        INTEGER
    {
        nop(0),
        single(327),
        global(329)
    }

CfprApTopInfoPolicyState ::= TEXTUAL-CONVENTION
    STATUS        current
    DESCRIPTION
        ""
    SYNTAX        INTEGER
    {
        disabled(0),
        enabled(1)
    }

CfprApTopMode ::= TEXTUAL-CONVENTION
    STATUS        current
    DESCRIPTION
        ""
    SYNTAX        INTEGER
    {
        unspecified(0),
        standAlone(1),
        cluster(2)
    }

CfprApTrigAckOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CfprApTrigAckPrevOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CfprApTrigAckChangeDetails ::= TEXTUAL-CONVENTION
    STATUS        current
    DESCRIPTION
        ""
    SYNTAX        BITS
    {
        binding(0),
        hostVirtEthIf(1),
        hostNonvirtEthIf(2),
        hostEthIfProfile(3),
        hostEthIfQos(4),
        hostEthIfNwCtrl(5),
        hostVirtFcIf(6),
        hostNonvirtFcIf(7),
        hostVirtFcIfPersBind(8),
        hostNonvirtFcIfPersBind(9),
        hostFcIfProfile(10),
        hostFcIfQos(11),
        hostFcoeIf(12),
        vif(13),
        vlan(14),
        vsan(15),
        ip(16),
        bootOrder(17),
        bootVirtVnic(18),
        bootNonvirtVnic(19),
        bootLocalStorage(20),
        bootVirtPxe(21),
        bootNonvirtPxe(22),
        bladeIdentity(24),
        agentPolicy(25),
        biosFw(26),
        storageControllerFw(27),
        adaptorHostFw(28),
        adaptorNwFw(29),
        mgmtControllerFw(30),
        localDiskPolicy(31),
        pin(32),
        sol(33),
        epAuth(34),
        biosProfile(35),
        checkpoint(36),
        implicitReboot(37),
        implicitHostFcIfProfileRedeploy(38),
        boardControllerFw(39),
        hostEthIfQosHostControl(40),
        localDiskFw(41),
        implicitHostEthIfProfileRedeploy(42),
        storagePath(43),
        bmcUpdateBiosFw(44),
        hostIfPcie(45),
        flexflashConfig(46),
        bootmodeConfig(48),
        securebootConfig(49),
        vmediaConfig(50),
        ssposUpdateFw(51)
    }

CfprApTrigAckChanges ::= TEXTUAL-CONVENTION
    STATUS        current
    DESCRIPTION
        ""
    SYNTAX        BITS
    {
        serverIdentity(0),
        storage(1),
        networking(2),
        vnicVhbaPlacement(3),
        bootOrder(4),
        serverAssignment(5),
        operationalPolicies(6)
    }

CfprApTrigAckDisr ::= TEXTUAL-CONVENTION
    STATUS        current
    DESCRIPTION
        ""
    SYNTAX        BITS
    {
        upTime(0),
        acPowerCycle(1)
    }

CfprApTrigAckMode ::= TEXTUAL-CONVENTION
    STATUS        current
    DESCRIPTION
        ""
    SYNTAX        INTEGER
    {
        immediate(0),
        userAck(1),
        timerAutomatic(2)
    }

CfprApTrigAdminState ::= TEXTUAL-CONVENTION
    STATUS        current
    DESCRIPTION
        ""
    SYNTAX        INTEGER
    {
        triggerImmediate(0),
        trigger(1),
        triggered(2),
        untriggered(3),
        userAck(4),
        userDiscard(5)
    }

CfprApTrigDay ::= TEXTUAL-CONVENTION
    STATUS        current
    DESCRIPTION
        ""
    SYNTAX        INTEGER
    {
        everyDay(0),
        monday(1),
        tuesday(2),
        wednesday(3),
        thursday(4),
        friday(5),
        saturday(6),
        sunday(7),
        oddDay(8),
        evenDay(9)
    }

CfprApTrigOperState ::= TEXTUAL-CONVENTION
    STATUS        current
    DESCRIPTION
        ""
    SYNTAX        INTEGER
    {
        pending(0),
        inProgress(1),
        failed(2),
        triggered(3),
        capReached(4)
    }

CfprApTrigTokenOperState ::= TEXTUAL-CONVENTION
    STATUS        current
    DESCRIPTION
        ""
    SYNTAX        INTEGER
    {
        valid(0),
        expired(1)
    }

CfprApTrigTrigOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CfprApTrigTriggeredState ::= TEXTUAL-CONVENTION
    STATUS        current
    DESCRIPTION
        ""
    SYNTAX        INTEGER
    {
        pending(0),
        inProgress(1),
        failed(2),
        triggered(3)
    }

CfprApUuidpoolPoolAssignmentOrder ::= TEXTUAL-CONVENTION
    STATUS        current
    DESCRIPTION
        ""
    SYNTAX        INTEGER
    {
        default(0),
        sequential(1)
    }

CfprApVmAdaptorOwner ::= TEXTUAL-CONVENTION
    STATUS        current
    DESCRIPTION
        ""
    SYNTAX        INTEGER
    {
        unknown(0),
        physical(1),
        policy(2),
        logical(4),
        connPolicy(8)
    }

CfprApVmComputeEpClInstType ::= TEXTUAL-CONVENTION
    STATUS        current
    DESCRIPTION
        ""
    SYNTAX        INTEGER
    {
        vm(0),
        hv(1),
        computeEp(2)
    }

CfprApVmHbaType ::= TEXTUAL-CONVENTION
    STATUS        current
    DESCRIPTION
        ""
    SYNTAX        INTEGER
    {
        unknown(0),
        ether(1),
        fc(4),
        scsi(8),
        ipc(16)
    }

CfprApVmHvClInstType ::= TEXTUAL-CONVENTION
    STATUS        current
    DESCRIPTION
        ""
    SYNTAX        INTEGER
    {
        vm(0),
        hv(1),
        computeEp(2)
    }

CfprApVmHvType ::= TEXTUAL-CONVENTION
    STATUS        current
    DESCRIPTION
        ""
    SYNTAX        INTEGER
    {
        unspecified(0),
        esx(1),
        kvm(2),
        hyperv(3),
        xen(4)
    }

CfprApVmInstType ::= TEXTUAL-CONVENTION
    STATUS        current
    DESCRIPTION
        ""
    SYNTAX        INTEGER
    {
        vm(0),
        hv(1),
        computeEp(2)
    }

CfprApVmMgmtPlane ::= TEXTUAL-CONVENTION
    STATUS        current
    DESCRIPTION
        ""
    SYNTAX        INTEGER
    {
        unmanaged(0),
        vcenter(1),
        rhevM(2),
        scvmm(3)
    }

CfprApVmNicType ::= TEXTUAL-CONVENTION
    STATUS        current
    DESCRIPTION
        ""
    SYNTAX        INTEGER
    {
        unknown(0),
        ether(1),
        fc(4),
        scsi(8),
        ipc(16)
    }

CfprApVmOsHvVendor ::= TEXTUAL-CONVENTION
    STATUS        current
    DESCRIPTION
        ""
    SYNTAX        INTEGER
    {
        unspecified(0),
        vmware(1),
        redhat(2),
        microsoft(3),
        novell(4),
        oracle(5),
        citrix(6)
    }

CfprApVmStatus ::= TEXTUAL-CONVENTION
    STATUS        current
    DESCRIPTION
        ""
    SYNTAX        INTEGER
    {
        unknown(0),
        online(1),
        offline(2)
    }

CfprApVmSwitchAdminState ::= TEXTUAL-CONVENTION
    STATUS        current
    DESCRIPTION
        ""
    SYNTAX        INTEGER
    {
        disable(0),
        enable(1)
    }

CfprApVmSwitchVendor ::= TEXTUAL-CONVENTION
    STATUS        current
    DESCRIPTION
        ""
    SYNTAX        INTEGER
    {
        undetermined(0),
        vmware(1),
        microsoft(2)
    }

CfprApVnicAEtherIfType ::= TEXTUAL-CONVENTION
    STATUS        current
    DESCRIPTION
        ""
    SYNTAX        INTEGER
    {
        unknown(0),
        ether(1),
        fc(4),
        scsi(8),
        ipc(16)
    }

CfprApVnicAFcIfType ::= TEXTUAL-CONVENTION
    STATUS        current
    DESCRIPTION
        ""
    SYNTAX        INTEGER
    {
        unknown(0),
        ether(1),
        fc(4),
        scsi(8),
        ipc(16)
    }

CfprApVnicAIpcIfType ::= TEXTUAL-CONVENTION
    STATUS        current
    DESCRIPTION
        ""
    SYNTAX        INTEGER
    {
        unknown(0),
        ether(1),
        fc(4),
        scsi(8),
        ipc(16)
    }

CfprApVnicAScsiIfType ::= TEXTUAL-CONVENTION
    STATUS        current
    DESCRIPTION
        ""
    SYNTAX        INTEGER
    {
        unknown(0),
        ether(1),
        fc(4),
        scsi(8),
        ipc(16)
    }

CfprApVnicAppRole ::= TEXTUAL-CONVENTION
    STATUS        current
    DESCRIPTION
        ""
    SYNTAX        INTEGER
    {
        none(0),
        mainCp(1),
        appCp(2),
        appIntMgmt(3),
        appExtMgmt(4),
        asaDp(5),
        appDp(6),
        offloadDp(7)
    }

CfprApVnicConfigIssues ::= TEXTUAL-CONVENTION
    STATUS        current
    DESCRIPTION
        ""
    SYNTAX        BITS
    {
        pinningVlanMismatch(0),
        vnicVlanAssignmentError(1),
        missingPrimaryVlan(2),
        pinnedTargetMisconfig(3),
        unresolvedVlanName(4),
        inaccessibleVlan(5),
        unresolvedVsanName(6),
        unresolvedRemoteVlanName(7),
        unresolvedRemoteVsanName(8),
        adaptorFcoeCapability(9),
        adaptorProtectedEthCapability(10),
        adaptorRequirement(11),
        connectionPlacement(12),
        dynamicVfVnic(13),
        fcoeCapacity(14),
        insufficientVhbaCapacity(15),
        insufficientVnicCapacity(16),
        invalidWwn(17),
        macDerivationVirtualizedPort(18),
        vfcVnicPvlanConflict(19),
        vifResourcesOverprovisioned(20),
        vnicNotHaReady(21),
        vnicVconProvisioningChange(22),
        wwpnAssignment(23),
        wwpnDerivationVirtualizedPort(24),
        unableToUpdateUcsm(25),
        unassociatedVlan(26),
        serviceProfileVirtualizationConflict(27),
        vnicVirtualizationConflict(28),
        virtualizationNotSupported(29),
        ungroupedDomain(30),
        missingIpv4InbandMgmtAddr(31),
        missingIpv6InbandMgmtAddr(32),
        missingIpv4Addr(33),
        vnicVirtualizationNetflowConflict(34),
        softPinningVlanMismatch(35),
        unsupportedRoceVmq(36),
        unsupportedRoceNetflow(37),
        unsupportedRoce(38),
        unsupportedVxlan(39),
        unsupportedNvgre(40),
        unsupportedNvgreDynamicVnic(41),
        unsupportedNvgreUsnic(42),
        unsupportedVxlanDynamicVnic(43),
        unsupportedVxlanUsnic(44),
        unsupportedNvgreVmq(45),
        unsupportedVxlanVmq(46),
        unsupportedVxlanNetflow(47),
        unsupportedNvgreNetflow(48)
    }

CfprApVnicConnectionOwner ::= TEXTUAL-CONVENTION
    STATUS        current
    DESCRIPTION
        ""
    SYNTAX        INTEGER
    {
        unknown(0),
        physical(1),
        policy(2),
        logical(4),
        connPolicy(8)
    }

CfprApVnicConnectionType ::= TEXTUAL-CONVENTION
    STATUS        current
    DESCRIPTION
        ""
    SYNTAX        INTEGER
    {
        unknown(0),
        ether(1),
        fc(4),
        scsi(8),
        ipc(16)
    }

CfprApVnicDefBehType ::= TEXTUAL-CONVENTION
    STATUS        current
    DESCRIPTION
        ""
    SYNTAX        INTEGER
    {
        vnic(1),
        vhba(2)
    }

CfprApVnicDefaultAction ::= TEXTUAL-CONVENTION
    STATUS        current
    DESCRIPTION
        ""
    SYNTAX        INTEGER
    {
        none(0),
        hwInherit(1)
    }

CfprApVnicDynamicConReqProtection ::= TEXTUAL-CONVENTION
    STATUS        current
    DESCRIPTION
        ""
    SYNTAX        INTEGER
    {
        none(0),
        protectedPrefA(1),
        protectedPrefB(2),
        protected(3)
    }

CfprApVnicEtherType ::= TEXTUAL-CONVENTION
    STATUS        current
    DESCRIPTION
        ""
    SYNTAX        INTEGER
    {
        unknown(0),
        ether(1),
        fc(4),
        scsi(8),
        ipc(16)
    }

CfprApVnicEtherBaseSwitchId ::= TEXTUAL-CONVENTION
    STATUS        current
    DESCRIPTION
        ""
    SYNTAX        INTEGER
    {
        none(0),
        a(1),
        b(2),
        aB(5),
        bA(6)
    }

CfprApVnicExternalMgmtIPMode ::= TEXTUAL-CONVENTION
    STATUS        current
    DESCRIPTION
        ""
    SYNTAX        INTEGER
    {
        none(1),
        static(2),
        pooled(3)
    }

CfprApVnicFcBasePersBind ::= TEXTUAL-CONVENTION
    STATUS        current
    DESCRIPTION
        ""
    SYNTAX        INTEGER
    {
        disabled(0),
        enabled(4)
    }

CfprApVnicFcBaseType ::= TEXTUAL-CONVENTION
    STATUS        current
    DESCRIPTION
        ""
    SYNTAX        INTEGER
    {
        unknown(0),
        ether(1),
        fc(4),
        scsi(8),
        ipc(16)
    }

CfprApVnicFcNodeOwner ::= TEXTUAL-CONVENTION
    STATUS        current
    DESCRIPTION
        ""
    SYNTAX        INTEGER
    {
        unknown(0),
        physical(1),
        policy(2),
        logical(4),
        connPolicy(8)
    }

CfprApVnicHostNwIOPerfPref ::= TEXTUAL-CONVENTION
    STATUS        current
    DESCRIPTION
        ""
    SYNTAX        INTEGER
    {
        none(0),
        highPerfReqd(1)
    }

CfprApVnicIPv4DnsPref ::= TEXTUAL-CONVENTION
    STATUS        current
    DESCRIPTION
        ""
    SYNTAX        INTEGER
    {
        preferred(0),
        alternate(1)
    }

CfprApVnicIScsiConfigIssues ::= TEXTUAL-CONVENTION
    STATUS        current
    DESCRIPTION
        ""
    SYNTAX        BITS
    {
        initiatorName(0),
        iqnPoolName(1),
        targetName(2),
        authProfileSame(3),
        invalidTargetName(4),
        noLuns(5),
        iscsiCardinality(6),
        autoTargetAuth(7),
        autoTargetInit(8),
        noVlanIp(9),
        staticTargetMix(10),
        ipAddrDhcp(11),
        unclassified(12),
        internalCfgError(13),
        missingVlan(14),
        vnicName(15),
        allowedVlan(16),
        iscsiConfig(17),
        iscsiInitiatorIpAddress(18),
        invalidMac(19),
        nativeVlan(20),
        initTargetPasswd(21),
        initIdentity(22)
    }

CfprApVnicIScsiIfDefType ::= TEXTUAL-CONVENTION
    STATUS        current
    DESCRIPTION
        ""
    SYNTAX        INTEGER
    {
        static(0),
        dynamicNw(1),
        option17(2),
        option43(4)
    }

CfprApVnicIScsiNodeOwner ::= TEXTUAL-CONVENTION
    STATUS        current
    DESCRIPTION
        ""
    SYNTAX        INTEGER
    {
        unknown(0),
        physical(1),
        policy(2),
        logical(4),
        connPolicy(8)
    }

CfprApVnicIfOperState ::= TEXTUAL-CONVENTION
    STATUS        current
    DESCRIPTION
        ""
    SYNTAX        INTEGER
    {
        indeterminate(0),
        up(1),
        down(2),
        failed(4)
    }

CfprApVnicInstantiation ::= TEXTUAL-CONVENTION
    STATUS        current
    DESCRIPTION
        ""
    SYNTAX        INTEGER
    {
        manual(0),
        default(1),
        dynamic(2),
        dynamicVf(3)
    }

CfprApVnicIpcType ::= TEXTUAL-CONVENTION
    STATUS        current
    DESCRIPTION
        ""
    SYNTAX        INTEGER
    {
        unknown(0),
        ether(1),
        fc(4),
        scsi(8),
        ipc(16)
    }

CfprApVnicL2IfSwitchId ::= TEXTUAL-CONVENTION
    STATUS        current
    DESCRIPTION
        ""
    SYNTAX        INTEGER
    {
        none(0),
        a(1),
        b(2),
        aB(5),
        bA(6)
    }

CfprApVnicLanConnTemplSwitchId ::= TEXTUAL-CONVENTION
    STATUS        current
    DESCRIPTION
        ""
    SYNTAX        INTEGER
    {
        none(0),
        a(1),
        b(2),
        aB(5),
        bA(6)
    }

CfprApVnicLunId ::= TEXTUAL-CONVENTION
    STATUS        current
    DESCRIPTION
        ""
    SYNTAX        Gauge32 (0..65535)

CfprApVnicMezzMappingScheme ::= TEXTUAL-CONVENTION
    STATUS        current
    DESCRIPTION
        ""
    SYNTAX        INTEGER
    {
        physicalCapFirst(1),
        capLoadDistribute(2)
    }

CfprApVnicOrderScheme ::= TEXTUAL-CONVENTION
    STATUS        current
    DESCRIPTION
        ""
    SYNTAX        INTEGER
    {
        zeroFuncAll(0),
        multiFuncAll(1),
        staticZeroFunc(2)
    }

CfprApVnicPlacement ::= TEXTUAL-CONVENTION
    STATUS        current
    DESCRIPTION
        ""
    SYNTAX        INTEGER
    {
        allVnic(0),
        staticAllFirst(1),
        dynamicAllLast(2)
    }

CfprApVnicProfileConfigQualifier ::= TEXTUAL-CONVENTION
    STATUS        current
    DESCRIPTION
        ""
    SYNTAX        INTEGER
    {
        normal(0),
        invalidName(1)
    }

CfprApVnicSanConnTemplTarget ::= TEXTUAL-CONVENTION
    STATUS        current
    DESCRIPTION
        ""
    SYNTAX        BITS
    {
        vm(0),
        adaptor(1)
    }

CfprApVnicScsiType ::= TEXTUAL-CONVENTION
    STATUS        current
    DESCRIPTION
        ""
    SYNTAX        INTEGER
    {
        unknown(0),
        ether(1),
        fc(4),
        scsi(8),
        ipc(16)
    }

CfprApVnicTemplateTarget ::= TEXTUAL-CONVENTION
    STATUS        current
    DESCRIPTION
        ""
    SYNTAX        BITS
    {
        vm(0),
        adaptor(1)
    }

CfprApVnicTemplateType ::= TEXTUAL-CONVENTION
    STATUS        current
    DESCRIPTION
        ""
    SYNTAX        INTEGER
    {
        initialTemplate(1),
        updatingTemplate(2)
    }

CfprApVnicVhbaBehPolicyType ::= TEXTUAL-CONVENTION
    STATUS        current
    DESCRIPTION
        ""
    SYNTAX        INTEGER
    {
        vnic(1),
        vhba(2)
    }

CfprApVnicVirtualizationPreferenceType ::= TEXTUAL-CONVENTION
    STATUS        current
    DESCRIPTION
        ""
    SYNTAX        INTEGER
    {
        none(0),
        sriov(2),
        sriovVmfex(3),
        sriovUsnic(4),
        vmq(5)
    }

CfprApVnicVnicBootDev ::= TEXTUAL-CONVENTION
    STATUS        current
    DESCRIPTION
        ""
    SYNTAX        INTEGER
    {
        disabled(0),
        enabled(1)
    }

CfprApVnicVnicOperHostPort ::= TEXTUAL-CONVENTION
    STATUS        current
    DESCRIPTION
        ""
    SYNTAX        INTEGER
    {
        any(0),
        n1(1),
        n2(2),
        none(10)
    }

CfprApVnicVnicBehPolicyType ::= TEXTUAL-CONVENTION
    STATUS        current
    DESCRIPTION
        ""
    SYNTAX        INTEGER
    {
        vnic(1),
        vhba(2)
    }

CfprApVnicPortProfileType ::= TEXTUAL-CONVENTION
    STATUS        current
    DESCRIPTION
        ""
    SYNTAX        INTEGER
    {
        regular(0),
        slaOnly(1)
    }

END
