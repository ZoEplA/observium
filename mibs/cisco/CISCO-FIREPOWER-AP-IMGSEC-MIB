-- *********************************************************************
-- CISCO-FIREPOWER-AP-IMGSEC-MIB.my
-- 
-- MIB representation of the Cisco Firepower
-- IMGSEC management information model package
-- 
-- Created August 2017 by Charles Bullis
-- 
-- Copyright (c) 2005-2017 Cisco Systems, Inc. All rights reserved.
-- 
-- *********************************************************************

CISCO-FIREPOWER-AP-IMGSEC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApImgsecKeyType,
    CfprApPolicyPolicyOwner
        FROM CISCO-FIREPOWER-AP-TC-MIB;

cfprApImgsecObjects MODULE-IDENTITY
    LAST-UPDATED    "201708230000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        IMGSEC management information model package"
    ::= { ciscoFirepowerApMIBObjects 38 }

cfprApImgsecKeyTable OBJECT-TYPE
    SYNTAX           SEQUENCE OF CfprApImgsecKeyEntry
    MAX-ACCESS       not-accessible
    STATUS           current
    DESCRIPTION
        "Cisco Firepower imgsec:Key managed object table"
    ::= { cfprApImgsecObjects 1 }

cfprApImgsecKeyEntry OBJECT-TYPE
    SYNTAX           CfprApImgsecKeyEntry
    MAX-ACCESS       not-accessible
    STATUS           current
    DESCRIPTION
        "Entry for the cfprApImgsecKeyTable table."
    INDEX { cfprApImgsecKeyInstanceId }
    ::= { cfprApImgsecKeyTable 1 }

CfprApImgsecKeyEntry ::= SEQUENCE {
    cfprApImgsecKeyInstanceId                                        CfprApManagedObjectId,
    cfprApImgsecKeyDn                                                CfprApManagedObjectDn,
    cfprApImgsecKeyRn                                                SnmpAdminString,
    cfprApImgsecKeyType                                              CfprApImgsecKeyType,
    cfprApImgsecKeyValue                                             SnmpAdminString
}

cfprApImgsecKeyInstanceId OBJECT-TYPE
    SYNTAX       CfprApManagedObjectId
    MAX-ACCESS   not-accessible
    STATUS       current
    DESCRIPTION
        "Instance identifier of the managed object."
    ::= { cfprApImgsecKeyEntry 1 }

cfprApImgsecKeyDn OBJECT-TYPE
    SYNTAX       CfprApManagedObjectDn
    MAX-ACCESS   read-only
    STATUS       current
    DESCRIPTION
        "Cisco Firepower imgsec:Key:dn managed object property"
    ::= { cfprApImgsecKeyEntry 2 }

cfprApImgsecKeyRn OBJECT-TYPE
    SYNTAX       SnmpAdminString
    MAX-ACCESS   read-only
    STATUS       current
    DESCRIPTION
        "Cisco Firepower imgsec:Key:rn managed object property"
    ::= { cfprApImgsecKeyEntry 3 }

cfprApImgsecKeyType OBJECT-TYPE
    SYNTAX       CfprApImgsecKeyType
    MAX-ACCESS   read-only
    STATUS       current
    DESCRIPTION
        "Cisco Firepower imgsec:Key:type managed object property"
    ::= { cfprApImgsecKeyEntry 4 }

cfprApImgsecKeyValue OBJECT-TYPE
    SYNTAX       SnmpAdminString
    MAX-ACCESS   read-only
    STATUS       current
    DESCRIPTION
        "Cisco Firepower imgsec:Key:value managed object property"
    ::= { cfprApImgsecKeyEntry 5 }

cfprApImgsecPolicyTable OBJECT-TYPE
    SYNTAX           SEQUENCE OF CfprApImgsecPolicyEntry
    MAX-ACCESS       not-accessible
    STATUS           current
    DESCRIPTION
        "Cisco Firepower imgsec:Policy managed object table"
    ::= { cfprApImgsecObjects 2 }

cfprApImgsecPolicyEntry OBJECT-TYPE
    SYNTAX           CfprApImgsecPolicyEntry
    MAX-ACCESS       not-accessible
    STATUS           current
    DESCRIPTION
        "Entry for the cfprApImgsecPolicyTable table."
    INDEX { cfprApImgsecPolicyInstanceId }
    ::= { cfprApImgsecPolicyTable 1 }

CfprApImgsecPolicyEntry ::= SEQUENCE {
    cfprApImgsecPolicyInstanceId                                     CfprApManagedObjectId,
    cfprApImgsecPolicyDn                                             CfprApManagedObjectDn,
    cfprApImgsecPolicyRn                                             SnmpAdminString,
    cfprApImgsecPolicyDescr                                          SnmpAdminString,
    cfprApImgsecPolicyIntId                                          SnmpAdminString,
    cfprApImgsecPolicyName                                           SnmpAdminString,
    cfprApImgsecPolicyPolicyLevel                                    Gauge32,
    cfprApImgsecPolicyPolicyOwner                                    CfprApPolicyPolicyOwner
}

cfprApImgsecPolicyInstanceId OBJECT-TYPE
    SYNTAX       CfprApManagedObjectId
    MAX-ACCESS   not-accessible
    STATUS       current
    DESCRIPTION
        "Instance identifier of the managed object."
    ::= { cfprApImgsecPolicyEntry 1 }

cfprApImgsecPolicyDn OBJECT-TYPE
    SYNTAX       CfprApManagedObjectDn
    MAX-ACCESS   read-only
    STATUS       current
    DESCRIPTION
        "Cisco Firepower imgsec:Policy:dn managed object property"
    ::= { cfprApImgsecPolicyEntry 2 }

cfprApImgsecPolicyRn OBJECT-TYPE
    SYNTAX       SnmpAdminString
    MAX-ACCESS   read-only
    STATUS       current
    DESCRIPTION
        "Cisco Firepower imgsec:Policy:rn managed object property"
    ::= { cfprApImgsecPolicyEntry 3 }

cfprApImgsecPolicyDescr OBJECT-TYPE
    SYNTAX       SnmpAdminString
    MAX-ACCESS   read-only
    STATUS       current
    DESCRIPTION
        "Cisco Firepower imgsec:Policy:descr managed object property"
    ::= { cfprApImgsecPolicyEntry 4 }

cfprApImgsecPolicyIntId OBJECT-TYPE
    SYNTAX       SnmpAdminString
    MAX-ACCESS   read-only
    STATUS       current
    DESCRIPTION
        "Cisco Firepower imgsec:Policy:intId managed object property"
    ::= { cfprApImgsecPolicyEntry 5 }

cfprApImgsecPolicyName OBJECT-TYPE
    SYNTAX       SnmpAdminString
    MAX-ACCESS   read-only
    STATUS       current
    DESCRIPTION
        "Cisco Firepower imgsec:Policy:name managed object property"
    ::= { cfprApImgsecPolicyEntry 6 }

cfprApImgsecPolicyPolicyLevel OBJECT-TYPE
    SYNTAX       Gauge32
    MAX-ACCESS   read-only
    STATUS       current
    DESCRIPTION
        "Cisco Firepower imgsec:Policy:policyLevel managed
        object property"
    ::= { cfprApImgsecPolicyEntry 7 }

cfprApImgsecPolicyPolicyOwner OBJECT-TYPE
    SYNTAX       CfprApPolicyPolicyOwner
    MAX-ACCESS   read-only
    STATUS       current
    DESCRIPTION
        "Cisco Firepower imgsec:Policy:policyOwner managed
        object property"
    ::= { cfprApImgsecPolicyEntry 8 }

END
