-- *********************************************************************
-- CISCO-FIREPOWER-AP-BIOS-MIB.my
-- 
-- MIB representation of the Cisco Firepower
-- BIOS management information model package
-- 
-- Created August 2017 by Charles Bullis
-- 
-- Copyright (c) 2005-2017 Cisco Systems, Inc. All rights reserved.
-- 
-- *********************************************************************

CISCO-FIREPOWER-AP-BIOS-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApBiosBootDevErrorCode,
    CfprApBiosBootDevGrpType,
    CfprApBiosBootDevOrder,
    CfprApBiosDefaultAction,
    CfprApBiosSupportedAction,
    CfprApBiosVfACPI10SupportVpACPI10Support,
    CfprApBiosVfAllUSBDevicesVpAllUSBDevices,
    CfprApBiosVfAltitudeVpAltitude,
    CfprApBiosVfAssertNMIOnPERRVpAssertNMIOnPERR,
    CfprApBiosVfAssertNMIOnSERRVpAssertNMIOnSERR,
    CfprApBiosVfBootOptionRetryVpBootOptionRetry,
    CfprApBiosVfCPUPerformanceVpCPUPerformance,
    CfprApBiosVfConsoleRedirectionVpBaudRate,
    CfprApBiosVfConsoleRedirectionVpConsoleRedirection,
    CfprApBiosVfConsoleRedirectionVpFlowControl,
    CfprApBiosVfConsoleRedirectionVpLegacyOSRedirection,
    CfprApBiosVfConsoleRedirectionVpPuttyKeyPad,
    CfprApBiosVfConsoleRedirectionVpTerminalType,
    CfprApBiosVfCoreMultiProcessingVpCoreMultiProcessing,
    CfprApBiosVfDRAMClockThrottlingVpDRAMClockThrottling,
    CfprApBiosVfDirectCacheAccessVpDirectCacheAccess,
    CfprApBiosVfDramRefreshRateVpDramRefreshRate,
    CfprApBiosVfEnhancedIntelSpeedStepTechVpEnhancedIntelSpeedStepTech,
    CfprApBiosVfExecuteDisableBitVpExecuteDisableBit,
    CfprApBiosVfFRB2TimerVpFRB2Timer,
    CfprApBiosVfFrequencyFloorOverrideVpFrequencyFloorOverride,
    CfprApBiosVfFrontPanelLockoutVpFrontPanelLockout,
    CfprApBiosVfIntelEntrySASRAIDModuleVpSASRAID,
    CfprApBiosVfIntelEntrySASRAIDModuleVpSASRAIDModule,
    CfprApBiosVfIntelHyperThreadingTechVpIntelHyperThreadingTech,
    CfprApBiosVfIntelTurboBoostTechVpIntelTurboBoostTech,
    CfprApBiosVfIntelVTForDirectedIOVpIntelVTDATSSupport,
    CfprApBiosVfIntelVTForDirectedIOVpIntelVTDCoherencySupport,
    CfprApBiosVfIntelVTForDirectedIOVpIntelVTDInterruptRemapping,
    CfprApBiosVfIntelVTForDirectedIOVpIntelVTDPassThroughDMASupport,
    CfprApBiosVfIntelVTForDirectedIOVpIntelVTForDirectedIO,
    CfprApBiosVfIntelVirtualizationTechnologyVpIntelVirtTechnology,
    CfprApBiosVfInterleaveConfigurationVpChannelInterleaving,
    CfprApBiosVfInterleaveConfigurationVpMemoryInterleaving,
    CfprApBiosVfInterleaveConfigurationVpRankInterleaving,
    CfprApBiosVfLocalX2ApicVpLocalX2Apic,
    CfprApBiosVfLvDIMMSupportVpLvDDRMode,
    CfprApBiosVfMaxVariableMTRRSettingVpProcessorMtrr,
    CfprApBiosVfMaximumMemoryBelow4GBVpMaximumMemoryBelow4GB,
    CfprApBiosVfMemoryMappedIOAbove4GBVpMemoryMappedIOAbove4GB,
    CfprApBiosVfMirroringModeVpMirroringMode,
    CfprApBiosVfNUMAOptimizedVpNUMAOptimized,
    CfprApBiosVfOSBootWatchdogTimerPolicyVpOSBootWatchdogTimerPolicy,
    CfprApBiosVfOSBootWatchdogTimerTimeoutVpOSBootWatchdogTimerTimeout,
    CfprApBiosVfOSBootWatchdogTimerVpOSBootWatchdogTimer,
    CfprApBiosVfOnboardSATAControllerVpOnboardSATAController,
    CfprApBiosVfOnboardSATAControllerVpSATAMode,
    CfprApBiosVfOnboardStorageVpOnboardSCUStorageSupport,
    CfprApBiosVfOptionROMEnableVpState,
    CfprApBiosVfOptionROMLoadVpLoad,
    CfprApBiosVfPCISlotLinkSpeedVpPCIeSlot10LinkSpeed,
    CfprApBiosVfPCISlotLinkSpeedVpPCIeSlot1LinkSpeed,
    CfprApBiosVfPCISlotLinkSpeedVpPCIeSlot2LinkSpeed,
    CfprApBiosVfPCISlotLinkSpeedVpPCIeSlot3LinkSpeed,
    CfprApBiosVfPCISlotLinkSpeedVpPCIeSlot4LinkSpeed,
    CfprApBiosVfPCISlotLinkSpeedVpPCIeSlot5LinkSpeed,
    CfprApBiosVfPCISlotLinkSpeedVpPCIeSlot6LinkSpeed,
    CfprApBiosVfPCISlotLinkSpeedVpPCIeSlot7LinkSpeed,
    CfprApBiosVfPCISlotLinkSpeedVpPCIeSlot8LinkSpeed,
    CfprApBiosVfPCISlotLinkSpeedVpPCIeSlot9LinkSpeed,
    CfprApBiosVfPCISlotOptionROMEnableVpPCIeSlotHBAOptionROM,
    CfprApBiosVfPCISlotOptionROMEnableVpPCIeSlotMLOMOptionROM,
    CfprApBiosVfPCISlotOptionROMEnableVpPCIeSlotN1OptionROM,
    CfprApBiosVfPCISlotOptionROMEnableVpPCIeSlotN2OptionROM,
    CfprApBiosVfPCISlotOptionROMEnableVpPCIeSlotSASOptionROM,
    CfprApBiosVfPCISlotOptionROMEnableVpSlot10State,
    CfprApBiosVfPCISlotOptionROMEnableVpSlot1State,
    CfprApBiosVfPCISlotOptionROMEnableVpSlot2State,
    CfprApBiosVfPCISlotOptionROMEnableVpSlot3State,
    CfprApBiosVfPCISlotOptionROMEnableVpSlot4State,
    CfprApBiosVfPCISlotOptionROMEnableVpSlot5State,
    CfprApBiosVfPCISlotOptionROMEnableVpSlot6State,
    CfprApBiosVfPCISlotOptionROMEnableVpSlot7State,
    CfprApBiosVfPCISlotOptionROMEnableVpSlot8State,
    CfprApBiosVfPCISlotOptionROMEnableVpSlot9State,
    CfprApBiosVfPCISlotOptionROMEnableVpSlotMezzState,
    CfprApBiosVfPOSTErrorPauseVpPOSTErrorPause,
    CfprApBiosVfPSTATECoordinationVpPSTATECoordination,
    CfprApBiosVfPackageCStateLimitVpPackageCStateLimit,
    CfprApBiosVfProcessorC1EVpProcessorC1E,
    CfprApBiosVfProcessorC3ReportVpProcessorC3Report,
    CfprApBiosVfProcessorC6ReportVpProcessorC6Report,
    CfprApBiosVfProcessorC7ReportVpProcessorC7Report,
    CfprApBiosVfProcessorCStateVpProcessorCState,
    CfprApBiosVfProcessorEnergyConfigurationVpEnergyPerformance,
    CfprApBiosVfProcessorEnergyConfigurationVpPowerTechnology,
    CfprApBiosVfProcessorPrefetchConfigVpAdjacentCacheLinePrefetcher,
    CfprApBiosVfProcessorPrefetchConfigVpDCUIPPrefetcher,
    CfprApBiosVfProcessorPrefetchConfigVpDCUStreamerPrefetch,
    CfprApBiosVfProcessorPrefetchConfigVpHardwarePrefetcher,
    CfprApBiosVfQPILinkFrequencySelectVpQPILinkFrequencySelect,
    CfprApBiosVfQuietBootVpQuietBoot,
    CfprApBiosVfResumeOnACPowerLossVpResumeOnACPowerLoss,
    CfprApBiosVfScrubPoliciesVpDemandScrub,
    CfprApBiosVfScrubPoliciesVpPatrolScrub,
    CfprApBiosVfSelectMemoryRASConfigurationVpSelectMemoryRASConf,
    CfprApBiosVfSerialPortAEnableVpSerialPortAEnable,
    CfprApBiosVfSparingModeVpSparingMode,
    CfprApBiosVfSriovConfigVpSriov,
    CfprApBiosVfTPMSupportVpTPMSupport,
    CfprApBiosVfUCSMBootModeControlVpUEFIBootMode,
    CfprApBiosVfUCSMBootOrderRuleControlVpUCSMBootOrderRule,
    CfprApBiosVfUEFIOSUseLegacyVideoVpUEFIOSUseLegacyVideo,
    CfprApBiosVfUSBBootConfigVpLegacyUSBSupport,
    CfprApBiosVfUSBBootConfigVpMakeDeviceNonBootable,
    CfprApBiosVfUSBConfigurationVpLegacyUSBSupport,
    CfprApBiosVfUSBConfigurationVpXHCIMode,
    CfprApBiosVfUSBFrontPanelAccessLockVpUSBFrontPanelLock,
    CfprApBiosVfUSBPortConfigurationVpPort6064Emulation,
    CfprApBiosVfUSBPortConfigurationVpUSBPortFront,
    CfprApBiosVfUSBPortConfigurationVpUSBPortInternal,
    CfprApBiosVfUSBPortConfigurationVpUSBPortKVM,
    CfprApBiosVfUSBPortConfigurationVpUSBPortRear,
    CfprApBiosVfUSBPortConfigurationVpUSBPortSDCard,
    CfprApBiosVfUSBPortConfigurationVpUSBPortVMedia,
    CfprApBiosVfUSBSysIdlePowerOptimizingSettingVpUSBIdlePowerOptimize,
    CfprApBiosVfVGAPriorityVpVGAPriority,
    CfprApPolicyPolicyOwner
        FROM CISCO-FIREPOWER-AP-TC-MIB;

cfprApBiosObjects MODULE-IDENTITY
    LAST-UPDATED    "201708230000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        BIOS management information model package"
    ::= { ciscoFirepowerApMIBObjects 5 }

cfprApBiosBOTTable OBJECT-TYPE
    SYNTAX           SEQUENCE OF CfprApBiosBOTEntry
    MAX-ACCESS       not-accessible
    STATUS           current
    DESCRIPTION
        "Cisco Firepower bios:BOT managed object table"
    ::= { cfprApBiosObjects 1 }

cfprApBiosBOTEntry OBJECT-TYPE
    SYNTAX           CfprApBiosBOTEntry
    MAX-ACCESS       not-accessible
    STATUS           current
    DESCRIPTION
        "Entry for the cfprApBiosBOTTable table."
    INDEX { cfprApBiosBOTInstanceId }
    ::= { cfprApBiosBOTTable 1 }

CfprApBiosBOTEntry ::= SEQUENCE {
    cfprApBiosBOTInstanceId                                          CfprApManagedObjectId,
    cfprApBiosBOTDn                                                  CfprApManagedObjectDn,
    cfprApBiosBOTRn                                                  SnmpAdminString,
    cfprApBiosBOTLastUpdate                                          DateAndTime
}

cfprApBiosBOTInstanceId OBJECT-TYPE
    SYNTAX       CfprApManagedObjectId
    MAX-ACCESS   not-accessible
    STATUS       current
    DESCRIPTION
        "Instance identifier of the managed object."
    ::= { cfprApBiosBOTEntry 1 }

cfprApBiosBOTDn OBJECT-TYPE
    SYNTAX       CfprApManagedObjectDn
    MAX-ACCESS   read-only
    STATUS       current
    DESCRIPTION
        "Cisco Firepower bios:BOT:dn managed object property"
    ::= { cfprApBiosBOTEntry 2 }

cfprApBiosBOTRn OBJECT-TYPE
    SYNTAX       SnmpAdminString
    MAX-ACCESS   read-only
    STATUS       current
    DESCRIPTION
        "Cisco Firepower bios:BOT:rn managed object property"
    ::= { cfprApBiosBOTEntry 3 }

cfprApBiosBOTLastUpdate OBJECT-TYPE
    SYNTAX       DateAndTime
    MAX-ACCESS   read-only
    STATUS       current
    DESCRIPTION
        "Cisco Firepower bios:BOT:lastUpdate managed object property"
    ::= { cfprApBiosBOTEntry 4 }

cfprApBiosBootDevTable OBJECT-TYPE
    SYNTAX           SEQUENCE OF CfprApBiosBootDevEntry
    MAX-ACCESS       not-accessible
    STATUS           current
    DESCRIPTION
        "Cisco Firepower bios:BootDev managed object table"
    ::= { cfprApBiosObjects 2 }

cfprApBiosBootDevEntry OBJECT-TYPE
    SYNTAX           CfprApBiosBootDevEntry
    MAX-ACCESS       not-accessible
    STATUS           current
    DESCRIPTION
        "Entry for the cfprApBiosBootDevTable table."
    INDEX { cfprApBiosBootDevInstanceId }
    ::= { cfprApBiosBootDevTable 1 }

CfprApBiosBootDevEntry ::= SEQUENCE {
    cfprApBiosBootDevInstanceId                                      CfprApManagedObjectId,
    cfprApBiosBootDevDn                                              CfprApManagedObjectDn,
    cfprApBiosBootDevRn                                              SnmpAdminString,
    cfprApBiosBootDevDescr                                           SnmpAdminString,
    cfprApBiosBootDevDeviceName                                      SnmpAdminString,
    cfprApBiosBootDevErrValue                                        CfprApBiosBootDevErrorCode,
    cfprApBiosBootDevOrder                                           CfprApBiosBootDevOrder
}

cfprApBiosBootDevInstanceId OBJECT-TYPE
    SYNTAX       CfprApManagedObjectId
    MAX-ACCESS   not-accessible
    STATUS       current
    DESCRIPTION
        "Instance identifier of the managed object."
    ::= { cfprApBiosBootDevEntry 1 }

cfprApBiosBootDevDn OBJECT-TYPE
    SYNTAX       CfprApManagedObjectDn
    MAX-ACCESS   read-only
    STATUS       current
    DESCRIPTION
        "Cisco Firepower bios:BootDev:dn managed object property"
    ::= { cfprApBiosBootDevEntry 2 }

cfprApBiosBootDevRn OBJECT-TYPE
    SYNTAX       SnmpAdminString
    MAX-ACCESS   read-only
    STATUS       current
    DESCRIPTION
        "Cisco Firepower bios:BootDev:rn managed object property"
    ::= { cfprApBiosBootDevEntry 3 }

cfprApBiosBootDevDescr OBJECT-TYPE
    SYNTAX       SnmpAdminString
    MAX-ACCESS   read-only
    STATUS       current
    DESCRIPTION
        "Cisco Firepower bios:BootDev:descr managed object property"
    ::= { cfprApBiosBootDevEntry 4 }

cfprApBiosBootDevDeviceName OBJECT-TYPE
    SYNTAX       SnmpAdminString
    MAX-ACCESS   read-only
    STATUS       current
    DESCRIPTION
        "Cisco Firepower bios:BootDev:deviceName managed object property"
    ::= { cfprApBiosBootDevEntry 5 }

cfprApBiosBootDevErrValue OBJECT-TYPE
    SYNTAX       CfprApBiosBootDevErrorCode
    MAX-ACCESS   read-only
    STATUS       current
    DESCRIPTION
        "Cisco Firepower bios:BootDev:errValue managed object property"
    ::= { cfprApBiosBootDevEntry 6 }

cfprApBiosBootDevOrder OBJECT-TYPE
    SYNTAX       CfprApBiosBootDevOrder
    MAX-ACCESS   read-only
    STATUS       current
    DESCRIPTION
        "Cisco Firepower bios:BootDev:order managed object property"
    ::= { cfprApBiosBootDevEntry 7 }

cfprApBiosBootDevGrpTable OBJECT-TYPE
    SYNTAX           SEQUENCE OF CfprApBiosBootDevGrpEntry
    MAX-ACCESS       not-accessible
    STATUS           current
    DESCRIPTION
        "Cisco Firepower bios:BootDevGrp managed object table"
    ::= { cfprApBiosObjects 3 }

cfprApBiosBootDevGrpEntry OBJECT-TYPE
    SYNTAX           CfprApBiosBootDevGrpEntry
    MAX-ACCESS       not-accessible
    STATUS           current
    DESCRIPTION
        "Entry for the cfprApBiosBootDevGrpTable table."
    INDEX { cfprApBiosBootDevGrpInstanceId }
    ::= { cfprApBiosBootDevGrpTable 1 }

CfprApBiosBootDevGrpEntry ::= SEQUENCE {
    cfprApBiosBootDevGrpInstanceId                                   CfprApManagedObjectId,
    cfprApBiosBootDevGrpDn                                           CfprApManagedObjectDn,
    cfprApBiosBootDevGrpRn                                           SnmpAdminString,
    cfprApBiosBootDevGrpDescr                                        SnmpAdminString,
    cfprApBiosBootDevGrpDeviceName                                   SnmpAdminString,
    cfprApBiosBootDevGrpErrVal                                       CfprApBiosBootDevErrorCode,
    cfprApBiosBootDevGrpOrder                                        CfprApBiosBootDevOrder,
    cfprApBiosBootDevGrpType                                         CfprApBiosBootDevGrpType
}

cfprApBiosBootDevGrpInstanceId OBJECT-TYPE
    SYNTAX       CfprApManagedObjectId
    MAX-ACCESS   not-accessible
    STATUS       current
    DESCRIPTION
        "Instance identifier of the managed object."
    ::= { cfprApBiosBootDevGrpEntry 1 }

cfprApBiosBootDevGrpDn OBJECT-TYPE
    SYNTAX       CfprApManagedObjectDn
    MAX-ACCESS   read-only
    STATUS       current
    DESCRIPTION
        "Cisco Firepower bios:BootDevGrp:dn managed object property"
    ::= { cfprApBiosBootDevGrpEntry 2 }

cfprApBiosBootDevGrpRn OBJECT-TYPE
    SYNTAX       SnmpAdminString
    MAX-ACCESS   read-only
    STATUS       current
    DESCRIPTION
        "Cisco Firepower bios:BootDevGrp:rn managed object property"
    ::= { cfprApBiosBootDevGrpEntry 3 }

cfprApBiosBootDevGrpDescr OBJECT-TYPE
    SYNTAX       SnmpAdminString
    MAX-ACCESS   read-only
    STATUS       current
    DESCRIPTION
        "Cisco Firepower bios:BootDevGrp:descr managed object property"
    ::= { cfprApBiosBootDevGrpEntry 4 }

cfprApBiosBootDevGrpDeviceName OBJECT-TYPE
    SYNTAX       SnmpAdminString
    MAX-ACCESS   read-only
    STATUS       current
    DESCRIPTION
        "Cisco Firepower bios:BootDevGrp:deviceName managed
        object property"
    ::= { cfprApBiosBootDevGrpEntry 5 }

cfprApBiosBootDevGrpErrVal OBJECT-TYPE
    SYNTAX       CfprApBiosBootDevErrorCode
    MAX-ACCESS   read-only
    STATUS       current
    DESCRIPTION
        "Cisco Firepower bios:BootDevGrp:errVal managed object property"
    ::= { cfprApBiosBootDevGrpEntry 6 }

cfprApBiosBootDevGrpOrder OBJECT-TYPE
    SYNTAX       CfprApBiosBootDevOrder
    MAX-ACCESS   read-only
    STATUS       current
    DESCRIPTION
        "Cisco Firepower bios:BootDevGrp:order managed object property"
    ::= { cfprApBiosBootDevGrpEntry 7 }

cfprApBiosBootDevGrpType OBJECT-TYPE
    SYNTAX       CfprApBiosBootDevGrpType
    MAX-ACCESS   read-only
    STATUS       current
    DESCRIPTION
        "Cisco Firepower bios:BootDevGrp:type managed object property"
    ::= { cfprApBiosBootDevGrpEntry 8 }

cfprApBiosFeatureRefTable OBJECT-TYPE
    SYNTAX           SEQUENCE OF CfprApBiosFeatureRefEntry
    MAX-ACCESS       not-accessible
    STATUS           current
    DESCRIPTION
        "Cisco Firepower bios:FeatureRef managed object table"
    ::= { cfprApBiosObjects 4 }

cfprApBiosFeatureRefEntry OBJECT-TYPE
    SYNTAX           CfprApBiosFeatureRefEntry
    MAX-ACCESS       not-accessible
    STATUS           current
    DESCRIPTION
        "Entry for the cfprApBiosFeatureRefTable table."
    INDEX { cfprApBiosFeatureRefInstanceId }
    ::= { cfprApBiosFeatureRefTable 1 }

CfprApBiosFeatureRefEntry ::= SEQUENCE {
    cfprApBiosFeatureRefInstanceId                                   CfprApManagedObjectId,
    cfprApBiosFeatureRefDn                                           CfprApManagedObjectDn,
    cfprApBiosFeatureRefRn                                           SnmpAdminString,
    cfprApBiosFeatureRefFtrMoClassName                               SnmpAdminString,
    cfprApBiosFeatureRefIsSupported                                  CfprApBiosSupportedAction,
    cfprApBiosFeatureRefName                                         SnmpAdminString
}

cfprApBiosFeatureRefInstanceId OBJECT-TYPE
    SYNTAX       CfprApManagedObjectId
    MAX-ACCESS   not-accessible
    STATUS       current
    DESCRIPTION
        "Instance identifier of the managed object."
    ::= { cfprApBiosFeatureRefEntry 1 }

cfprApBiosFeatureRefDn OBJECT-TYPE
    SYNTAX       CfprApManagedObjectDn
    MAX-ACCESS   read-only
    STATUS       current
    DESCRIPTION
        "Cisco Firepower bios:FeatureRef:dn managed object property"
    ::= { cfprApBiosFeatureRefEntry 2 }

cfprApBiosFeatureRefRn OBJECT-TYPE
    SYNTAX       SnmpAdminString
    MAX-ACCESS   read-only
    STATUS       current
    DESCRIPTION
        "Cisco Firepower bios:FeatureRef:rn managed object property"
    ::= { cfprApBiosFeatureRefEntry 3 }

cfprApBiosFeatureRefFtrMoClassName OBJECT-TYPE
    SYNTAX       SnmpAdminString
    MAX-ACCESS   read-only
    STATUS       current
    DESCRIPTION
        "Cisco Firepower bios:FeatureRef:ftrMoClassName
        managed object property"
    ::= { cfprApBiosFeatureRefEntry 4 }

cfprApBiosFeatureRefIsSupported OBJECT-TYPE
    SYNTAX       CfprApBiosSupportedAction
    MAX-ACCESS   read-only
    STATUS       current
    DESCRIPTION
        "Cisco Firepower bios:FeatureRef:isSupported managed
        object property"
    ::= { cfprApBiosFeatureRefEntry 5 }

cfprApBiosFeatureRefName OBJECT-TYPE
    SYNTAX       SnmpAdminString
    MAX-ACCESS   read-only
    STATUS       current
    DESCRIPTION
        "Cisco Firepower bios:FeatureRef:name managed object property"
    ::= { cfprApBiosFeatureRefEntry 6 }

cfprApBiosParameterRefTable OBJECT-TYPE
    SYNTAX           SEQUENCE OF CfprApBiosParameterRefEntry
    MAX-ACCESS       not-accessible
    STATUS           current
    DESCRIPTION
        "Cisco Firepower bios:ParameterRef managed object table"
    ::= { cfprApBiosObjects 5 }

cfprApBiosParameterRefEntry OBJECT-TYPE
    SYNTAX           CfprApBiosParameterRefEntry
    MAX-ACCESS       not-accessible
    STATUS           current
    DESCRIPTION
        "Entry for the cfprApBiosParameterRefTable table."
    INDEX { cfprApBiosParameterRefInstanceId }
    ::= { cfprApBiosParameterRefTable 1 }

CfprApBiosParameterRefEntry ::= SEQUENCE {
    cfprApBiosParameterRefInstanceId                                 CfprApManagedObjectId,
    cfprApBiosParameterRefDn                                         CfprApManagedObjectDn,
    cfprApBiosParameterRefRn                                         SnmpAdminString,
    cfprApBiosParameterRefIsSupported                                CfprApBiosSupportedAction,
    cfprApBiosParameterRefName                                       SnmpAdminString,
    cfprApBiosParameterRefPropertyName                               SnmpAdminString
}

cfprApBiosParameterRefInstanceId OBJECT-TYPE
    SYNTAX       CfprApManagedObjectId
    MAX-ACCESS   not-accessible
    STATUS       current
    DESCRIPTION
        "Instance identifier of the managed object."
    ::= { cfprApBiosParameterRefEntry 1 }

cfprApBiosParameterRefDn OBJECT-TYPE
    SYNTAX       CfprApManagedObjectDn
    MAX-ACCESS   read-only
    STATUS       current
    DESCRIPTION
        "Cisco Firepower bios:ParameterRef:dn managed object property"
    ::= { cfprApBiosParameterRefEntry 2 }

cfprApBiosParameterRefRn OBJECT-TYPE
    SYNTAX       SnmpAdminString
    MAX-ACCESS   read-only
    STATUS       current
    DESCRIPTION
        "Cisco Firepower bios:ParameterRef:rn managed object property"
    ::= { cfprApBiosParameterRefEntry 3 }

cfprApBiosParameterRefIsSupported OBJECT-TYPE
    SYNTAX       CfprApBiosSupportedAction
    MAX-ACCESS   read-only
    STATUS       current
    DESCRIPTION
        "Cisco Firepower bios:ParameterRef:isSupported
        managed object property"
    ::= { cfprApBiosParameterRefEntry 4 }

cfprApBiosParameterRefName OBJECT-TYPE
    SYNTAX       SnmpAdminString
    MAX-ACCESS   read-only
    STATUS       current
    DESCRIPTION
        "Cisco Firepower bios:ParameterRef:name managed object property"
    ::= { cfprApBiosParameterRefEntry 5 }

cfprApBiosParameterRefPropertyName OBJECT-TYPE
    SYNTAX       SnmpAdminString
    MAX-ACCESS   read-only
    STATUS       current
    DESCRIPTION
        "Cisco Firepower bios:ParameterRef:propertyName
        managed object property"
    ::= { cfprApBiosParameterRefEntry 6 }

cfprApBiosRefTable OBJECT-TYPE
    SYNTAX           SEQUENCE OF CfprApBiosRefEntry
    MAX-ACCESS       not-accessible
    STATUS           current
    DESCRIPTION
        "Cisco Firepower bios:Ref managed object table"
    ::= { cfprApBiosObjects 6 }

cfprApBiosRefEntry OBJECT-TYPE
    SYNTAX           CfprApBiosRefEntry
    MAX-ACCESS       not-accessible
    STATUS           current
    DESCRIPTION
        "Entry for the cfprApBiosRefTable table."
    INDEX { cfprApBiosRefInstanceId }
    ::= { cfprApBiosRefTable 1 }

CfprApBiosRefEntry ::= SEQUENCE {
    cfprApBiosRefInstanceId                                          CfprApManagedObjectId,
    cfprApBiosRefDn                                                  CfprApManagedObjectDn,
    cfprApBiosRefRn                                                  SnmpAdminString,
    cfprApBiosRefIsSupported                                         CfprApBiosSupportedAction
}

cfprApBiosRefInstanceId OBJECT-TYPE
    SYNTAX       CfprApManagedObjectId
    MAX-ACCESS   not-accessible
    STATUS       current
    DESCRIPTION
        "Instance identifier of the managed object."
    ::= { cfprApBiosRefEntry 1 }

cfprApBiosRefDn OBJECT-TYPE
    SYNTAX       CfprApManagedObjectDn
    MAX-ACCESS   read-only
    STATUS       current
    DESCRIPTION
        "Cisco Firepower bios:Ref:dn managed object property"
    ::= { cfprApBiosRefEntry 2 }

cfprApBiosRefRn OBJECT-TYPE
    SYNTAX       SnmpAdminString
    MAX-ACCESS   read-only
    STATUS       current
    DESCRIPTION
        "Cisco Firepower bios:Ref:rn managed object property"
    ::= { cfprApBiosRefEntry 3 }

cfprApBiosRefIsSupported OBJECT-TYPE
    SYNTAX       CfprApBiosSupportedAction
    MAX-ACCESS   read-only
    STATUS       current
    DESCRIPTION
        "Cisco Firepower bios:Ref:isSupported managed object property"
    ::= { cfprApBiosRefEntry 4 }

cfprApBiosSettingRefTable OBJECT-TYPE
    SYNTAX           SEQUENCE OF CfprApBiosSettingRefEntry
    MAX-ACCESS       not-accessible
    STATUS           current
    DESCRIPTION
        "Cisco Firepower bios:SettingRef managed object table"
    ::= { cfprApBiosObjects 7 }

cfprApBiosSettingRefEntry OBJECT-TYPE
    SYNTAX           CfprApBiosSettingRefEntry
    MAX-ACCESS       not-accessible
    STATUS           current
    DESCRIPTION
        "Entry for the cfprApBiosSettingRefTable table."
    INDEX { cfprApBiosSettingRefInstanceId }
    ::= { cfprApBiosSettingRefTable 1 }

CfprApBiosSettingRefEntry ::= SEQUENCE {
    cfprApBiosSettingRefInstanceId                                   CfprApManagedObjectId,
    cfprApBiosSettingRefDn                                           CfprApManagedObjectDn,
    cfprApBiosSettingRefRn                                           SnmpAdminString,
    cfprApBiosSettingRefConstantName                                 SnmpAdminString,
    cfprApBiosSettingRefIsDefault                                    CfprApBiosDefaultAction,
    cfprApBiosSettingRefIsSupported                                  CfprApBiosSupportedAction,
    cfprApBiosSettingRefName                                         SnmpAdminString
}

cfprApBiosSettingRefInstanceId OBJECT-TYPE
    SYNTAX       CfprApManagedObjectId
    MAX-ACCESS   not-accessible
    STATUS       current
    DESCRIPTION
        "Instance identifier of the managed object."
    ::= { cfprApBiosSettingRefEntry 1 }

cfprApBiosSettingRefDn OBJECT-TYPE
    SYNTAX       CfprApManagedObjectDn
    MAX-ACCESS   read-only
    STATUS       current
    DESCRIPTION
        "Cisco Firepower bios:SettingRef:dn managed object property"
    ::= { cfprApBiosSettingRefEntry 2 }

cfprApBiosSettingRefRn OBJECT-TYPE
    SYNTAX       SnmpAdminString
    MAX-ACCESS   read-only
    STATUS       current
    DESCRIPTION
        "Cisco Firepower bios:SettingRef:rn managed object property"
    ::= { cfprApBiosSettingRefEntry 3 }

cfprApBiosSettingRefConstantName OBJECT-TYPE
    SYNTAX       SnmpAdminString
    MAX-ACCESS   read-only
    STATUS       current
    DESCRIPTION
        "Cisco Firepower bios:SettingRef:constantName managed
        object property"
    ::= { cfprApBiosSettingRefEntry 4 }

cfprApBiosSettingRefIsDefault OBJECT-TYPE
    SYNTAX       CfprApBiosDefaultAction
    MAX-ACCESS   read-only
    STATUS       current
    DESCRIPTION
        "Cisco Firepower bios:SettingRef:isDefault managed
        object property"
    ::= { cfprApBiosSettingRefEntry 5 }

cfprApBiosSettingRefIsSupported OBJECT-TYPE
    SYNTAX       CfprApBiosSupportedAction
    MAX-ACCESS   read-only
    STATUS       current
    DESCRIPTION
        "Cisco Firepower bios:SettingRef:isSupported managed
        object property"
    ::= { cfprApBiosSettingRefEntry 6 }

cfprApBiosSettingRefName OBJECT-TYPE
    SYNTAX       SnmpAdminString
    MAX-ACCESS   read-only
    STATUS       current
    DESCRIPTION
        "Cisco Firepower bios:SettingRef:name managed object property"
    ::= { cfprApBiosSettingRefEntry 7 }

cfprApBiosSettingsTable OBJECT-TYPE
    SYNTAX           SEQUENCE OF CfprApBiosSettingsEntry
    MAX-ACCESS       not-accessible
    STATUS           current
    DESCRIPTION
        "Cisco Firepower bios:Settings managed object table"
    ::= { cfprApBiosObjects 8 }

cfprApBiosSettingsEntry OBJECT-TYPE
    SYNTAX           CfprApBiosSettingsEntry
    MAX-ACCESS       not-accessible
    STATUS           current
    DESCRIPTION
        "Entry for the cfprApBiosSettingsTable table."
    INDEX { cfprApBiosSettingsInstanceId }
    ::= { cfprApBiosSettingsTable 1 }

CfprApBiosSettingsEntry ::= SEQUENCE {
    cfprApBiosSettingsInstanceId                                     CfprApManagedObjectId,
    cfprApBiosSettingsDn                                             CfprApManagedObjectDn,
    cfprApBiosSettingsRn                                             SnmpAdminString
}

cfprApBiosSettingsInstanceId OBJECT-TYPE
    SYNTAX       CfprApManagedObjectId
    MAX-ACCESS   not-accessible
    STATUS       current
    DESCRIPTION
        "Instance identifier of the managed object."
    ::= { cfprApBiosSettingsEntry 1 }

cfprApBiosSettingsDn OBJECT-TYPE
    SYNTAX       CfprApManagedObjectDn
    MAX-ACCESS   read-only
    STATUS       current
    DESCRIPTION
        "Cisco Firepower bios:Settings:dn managed object property"
    ::= { cfprApBiosSettingsEntry 2 }

cfprApBiosSettingsRn OBJECT-TYPE
    SYNTAX       SnmpAdminString
    MAX-ACCESS   read-only
    STATUS       current
    DESCRIPTION
        "Cisco Firepower bios:Settings:rn managed object property"
    ::= { cfprApBiosSettingsEntry 3 }

cfprApBiosUnitTable OBJECT-TYPE
    SYNTAX           SEQUENCE OF CfprApBiosUnitEntry
    MAX-ACCESS       not-accessible
    STATUS           current
    DESCRIPTION
        "Cisco Firepower bios:Unit managed object table"
    ::= { cfprApBiosObjects 9 }

cfprApBiosUnitEntry OBJECT-TYPE
    SYNTAX           CfprApBiosUnitEntry
    MAX-ACCESS       not-accessible
    STATUS           current
    DESCRIPTION
        "Entry for the cfprApBiosUnitTable table."
    INDEX { cfprApBiosUnitInstanceId }
    ::= { cfprApBiosUnitTable 1 }

CfprApBiosUnitEntry ::= SEQUENCE {
    cfprApBiosUnitInstanceId                                         CfprApManagedObjectId,
    cfprApBiosUnitDn                                                 CfprApManagedObjectDn,
    cfprApBiosUnitRn                                                 SnmpAdminString,
    cfprApBiosUnitInitSeq                                            SnmpAdminString,
    cfprApBiosUnitInitTs                                             DateAndTime,
    cfprApBiosUnitModel                                              SnmpAdminString,
    cfprApBiosUnitRevision                                           SnmpAdminString,
    cfprApBiosUnitSerial                                             SnmpAdminString,
    cfprApBiosUnitVendor                                             SnmpAdminString
}

cfprApBiosUnitInstanceId OBJECT-TYPE
    SYNTAX       CfprApManagedObjectId
    MAX-ACCESS   not-accessible
    STATUS       current
    DESCRIPTION
        "Instance identifier of the managed object."
    ::= { cfprApBiosUnitEntry 1 }

cfprApBiosUnitDn OBJECT-TYPE
    SYNTAX       CfprApManagedObjectDn
    MAX-ACCESS   read-only
    STATUS       current
    DESCRIPTION
        "Cisco Firepower bios:Unit:dn managed object property"
    ::= { cfprApBiosUnitEntry 2 }

cfprApBiosUnitRn OBJECT-TYPE
    SYNTAX       SnmpAdminString
    MAX-ACCESS   read-only
    STATUS       current
    DESCRIPTION
        "Cisco Firepower bios:Unit:rn managed object property"
    ::= { cfprApBiosUnitEntry 3 }

cfprApBiosUnitInitSeq OBJECT-TYPE
    SYNTAX       SnmpAdminString
    MAX-ACCESS   read-only
    STATUS       current
    DESCRIPTION
        "Cisco Firepower bios:Unit:initSeq managed object property"
    ::= { cfprApBiosUnitEntry 4 }

cfprApBiosUnitInitTs OBJECT-TYPE
    SYNTAX       DateAndTime
    MAX-ACCESS   read-only
    STATUS       current
    DESCRIPTION
        "Cisco Firepower bios:Unit:initTs managed object property"
    ::= { cfprApBiosUnitEntry 5 }

cfprApBiosUnitModel OBJECT-TYPE
    SYNTAX       SnmpAdminString
    MAX-ACCESS   read-only
    STATUS       current
    DESCRIPTION
        "Cisco Firepower bios:Unit:model managed object property"
    ::= { cfprApBiosUnitEntry 6 }

cfprApBiosUnitRevision OBJECT-TYPE
    SYNTAX       SnmpAdminString
    MAX-ACCESS   read-only
    STATUS       current
    DESCRIPTION
        "Cisco Firepower bios:Unit:revision managed object property"
    ::= { cfprApBiosUnitEntry 7 }

cfprApBiosUnitSerial OBJECT-TYPE
    SYNTAX       SnmpAdminString
    MAX-ACCESS   read-only
    STATUS       current
    DESCRIPTION
        "Cisco Firepower bios:Unit:serial managed object property"
    ::= { cfprApBiosUnitEntry 8 }

cfprApBiosUnitVendor OBJECT-TYPE
    SYNTAX       SnmpAdminString
    MAX-ACCESS   read-only
    STATUS       current
    DESCRIPTION
        "Cisco Firepower bios:Unit:vendor managed object property"
    ::= { cfprApBiosUnitEntry 9 }

cfprApBiosVIdentityParamsTable OBJECT-TYPE
    SYNTAX           SEQUENCE OF CfprApBiosVIdentityParamsEntry
    MAX-ACCESS       not-accessible
    STATUS           current
    DESCRIPTION
        "Cisco Firepower bios:VIdentityParams managed object table"
    ::= { cfprApBiosObjects 10 }

cfprApBiosVIdentityParamsEntry OBJECT-TYPE
    SYNTAX           CfprApBiosVIdentityParamsEntry
    MAX-ACCESS       not-accessible
    STATUS           current
    DESCRIPTION
        "Entry for the cfprApBiosVIdentityParamsTable table."
    INDEX { cfprApBiosVIdentityParamsInstanceId }
    ::= { cfprApBiosVIdentityParamsTable 1 }

CfprApBiosVIdentityParamsEntry ::= SEQUENCE {
    cfprApBiosVIdentityParamsInstanceId                              CfprApManagedObjectId,
    cfprApBiosVIdentityParamsDn                                      CfprApManagedObjectDn,
    cfprApBiosVIdentityParamsRn                                      SnmpAdminString,
    cfprApBiosVIdentityParamsLsServerName                            SnmpAdminString,
    cfprApBiosVIdentityParamsLsServerTmplName                        SnmpAdminString,
    cfprApBiosVIdentityParamsSysName                                 SnmpAdminString
}

cfprApBiosVIdentityParamsInstanceId OBJECT-TYPE
    SYNTAX       CfprApManagedObjectId
    MAX-ACCESS   not-accessible
    STATUS       current
    DESCRIPTION
        "Instance identifier of the managed object."
    ::= { cfprApBiosVIdentityParamsEntry 1 }

cfprApBiosVIdentityParamsDn OBJECT-TYPE
    SYNTAX       CfprApManagedObjectDn
    MAX-ACCESS   read-only
    STATUS       current
    DESCRIPTION
        "Cisco Firepower bios:VIdentityParams:dn managed object property"
    ::= { cfprApBiosVIdentityParamsEntry 2 }

cfprApBiosVIdentityParamsRn OBJECT-TYPE
    SYNTAX       SnmpAdminString
    MAX-ACCESS   read-only
    STATUS       current
    DESCRIPTION
        "Cisco Firepower bios:VIdentityParams:rn managed object property"
    ::= { cfprApBiosVIdentityParamsEntry 3 }

cfprApBiosVIdentityParamsLsServerName OBJECT-TYPE
    SYNTAX       SnmpAdminString
    MAX-ACCESS   read-only
    STATUS       current
    DESCRIPTION
        "Cisco Firepower bios:VIdentityParams:lsServerName
        managed object property"
    ::= { cfprApBiosVIdentityParamsEntry 4 }

cfprApBiosVIdentityParamsLsServerTmplName OBJECT-TYPE
    SYNTAX       SnmpAdminString
    MAX-ACCESS   read-only
    STATUS       current
    DESCRIPTION
        "Cisco Firepower bios:VIdentityParams:lsServerTmplName
        managed object property"
    ::= { cfprApBiosVIdentityParamsEntry 5 }

cfprApBiosVIdentityParamsSysName OBJECT-TYPE
    SYNTAX       SnmpAdminString
    MAX-ACCESS   read-only
    STATUS       current
    DESCRIPTION
        "Cisco Firepower bios:VIdentityParams:sysName managed
        object property"
    ::= { cfprApBiosVIdentityParamsEntry 6 }

cfprApBiosVProfileTable OBJECT-TYPE
    SYNTAX           SEQUENCE OF CfprApBiosVProfileEntry
    MAX-ACCESS       not-accessible
    STATUS           current
    DESCRIPTION
        "Cisco Firepower bios:VProfile managed object table"
    ::= { cfprApBiosObjects 11 }

cfprApBiosVProfileEntry OBJECT-TYPE
    SYNTAX           CfprApBiosVProfileEntry
    MAX-ACCESS       not-accessible
    STATUS           current
    DESCRIPTION
        "Entry for the cfprApBiosVProfileTable table."
    INDEX { cfprApBiosVProfileInstanceId }
    ::= { cfprApBiosVProfileTable 1 }

CfprApBiosVProfileEntry ::= SEQUENCE {
    cfprApBiosVProfileInstanceId                                     CfprApManagedObjectId,
    cfprApBiosVProfileDn                                             CfprApManagedObjectDn,
    cfprApBiosVProfileRn                                             SnmpAdminString,
    cfprApBiosVProfileDescr                                          SnmpAdminString,
    cfprApBiosVProfileIntId                                          SnmpAdminString,
    cfprApBiosVProfileName                                           SnmpAdminString,
    cfprApBiosVProfilePolicyLevel                                    Gauge32,
    cfprApBiosVProfilePolicyOwner                                    CfprApPolicyPolicyOwner,
    cfprApBiosVProfileRebootOnUpdate                                 TruthValue
}

cfprApBiosVProfileInstanceId OBJECT-TYPE
    SYNTAX       CfprApManagedObjectId
    MAX-ACCESS   not-accessible
    STATUS       current
    DESCRIPTION
        "Instance identifier of the managed object."
    ::= { cfprApBiosVProfileEntry 1 }

cfprApBiosVProfileDn OBJECT-TYPE
    SYNTAX       CfprApManagedObjectDn
    MAX-ACCESS   read-only
    STATUS       current
    DESCRIPTION
        "Cisco Firepower bios:VProfile:dn managed object property"
    ::= { cfprApBiosVProfileEntry 2 }

cfprApBiosVProfileRn OBJECT-TYPE
    SYNTAX       SnmpAdminString
    MAX-ACCESS   read-only
    STATUS       current
    DESCRIPTION
        "Cisco Firepower bios:VProfile:rn managed object property"
    ::= { cfprApBiosVProfileEntry 3 }

cfprApBiosVProfileDescr OBJECT-TYPE
    SYNTAX       SnmpAdminString
    MAX-ACCESS   read-only
    STATUS       current
    DESCRIPTION
        "Cisco Firepower bios:VProfile:descr managed object property"
    ::= { cfprApBiosVProfileEntry 4 }

cfprApBiosVProfileIntId OBJECT-TYPE
    SYNTAX       SnmpAdminString
    MAX-ACCESS   read-only
    STATUS       current
    DESCRIPTION
        "Cisco Firepower bios:VProfile:intId managed object property"
    ::= { cfprApBiosVProfileEntry 5 }

cfprApBiosVProfileName OBJECT-TYPE
    SYNTAX       SnmpAdminString
    MAX-ACCESS   read-only
    STATUS       current
    DESCRIPTION
        "Cisco Firepower bios:VProfile:name managed object property"
    ::= { cfprApBiosVProfileEntry 6 }

cfprApBiosVProfilePolicyLevel OBJECT-TYPE
    SYNTAX       Gauge32
    MAX-ACCESS   read-only
    STATUS       current
    DESCRIPTION
        "Cisco Firepower bios:VProfile:policyLevel managed
        object property"
    ::= { cfprApBiosVProfileEntry 7 }

cfprApBiosVProfilePolicyOwner OBJECT-TYPE
    SYNTAX       CfprApPolicyPolicyOwner
    MAX-ACCESS   read-only
    STATUS       current
    DESCRIPTION
        "Cisco Firepower bios:VProfile:policyOwner managed
        object property"
    ::= { cfprApBiosVProfileEntry 8 }

cfprApBiosVProfileRebootOnUpdate OBJECT-TYPE
    SYNTAX       TruthValue
    MAX-ACCESS   read-only
    STATUS       current
    DESCRIPTION
        "Cisco Firepower bios:VProfile:rebootOnUpdate managed
        object property"
    ::= { cfprApBiosVProfileEntry 9 }

cfprApBiosVfACPI10SupportTable OBJECT-TYPE
    SYNTAX           SEQUENCE OF CfprApBiosVfACPI10SupportEntry
    MAX-ACCESS       not-accessible
    STATUS           current
    DESCRIPTION
        "Cisco Firepower bios:VfACPI10Support managed object table"
    ::= { cfprApBiosObjects 12 }

cfprApBiosVfACPI10SupportEntry OBJECT-TYPE
    SYNTAX           CfprApBiosVfACPI10SupportEntry
    MAX-ACCESS       not-accessible
    STATUS           current
    DESCRIPTION
        "Entry for the cfprApBiosVfACPI10SupportTable table."
    INDEX { cfprApBiosVfACPI10SupportInstanceId }
    ::= { cfprApBiosVfACPI10SupportTable 1 }

CfprApBiosVfACPI10SupportEntry ::= SEQUENCE {
    cfprApBiosVfACPI10SupportInstanceId                              CfprApManagedObjectId,
    cfprApBiosVfACPI10SupportDn                                      CfprApManagedObjectDn,
    cfprApBiosVfACPI10SupportRn                                      SnmpAdminString,
    cfprApBiosVfACPI10SupportVpACPI10Support                         CfprApBiosVfACPI10SupportVpACPI10Support
}

cfprApBiosVfACPI10SupportInstanceId OBJECT-TYPE
    SYNTAX       CfprApManagedObjectId
    MAX-ACCESS   not-accessible
    STATUS       current
    DESCRIPTION
        "Instance identifier of the managed object."
    ::= { cfprApBiosVfACPI10SupportEntry 1 }

cfprApBiosVfACPI10SupportDn OBJECT-TYPE
    SYNTAX       CfprApManagedObjectDn
    MAX-ACCESS   read-only
    STATUS       current
    DESCRIPTION
        "Cisco Firepower bios:VfACPI10Support:dn managed object property"
    ::= { cfprApBiosVfACPI10SupportEntry 2 }

cfprApBiosVfACPI10SupportRn OBJECT-TYPE
    SYNTAX       SnmpAdminString
    MAX-ACCESS   read-only
    STATUS       current
    DESCRIPTION
        "Cisco Firepower bios:VfACPI10Support:rn managed object property"
    ::= { cfprApBiosVfACPI10SupportEntry 3 }

cfprApBiosVfACPI10SupportVpACPI10Support OBJECT-TYPE
    SYNTAX       CfprApBiosVfACPI10SupportVpACPI10Support
    MAX-ACCESS   read-only
    STATUS       current
    DESCRIPTION
        "Cisco Firepower bios:VfACPI10Support:vpACPI10Support
        managed object property"
    ::= { cfprApBiosVfACPI10SupportEntry 4 }

cfprApBiosVfAllUSBDevicesTable OBJECT-TYPE
    SYNTAX           SEQUENCE OF CfprApBiosVfAllUSBDevicesEntry
    MAX-ACCESS       not-accessible
    STATUS           current
    DESCRIPTION
        "Cisco Firepower bios:VfAllUSBDevices managed object table"
    ::= { cfprApBiosObjects 13 }

cfprApBiosVfAllUSBDevicesEntry OBJECT-TYPE
    SYNTAX           CfprApBiosVfAllUSBDevicesEntry
    MAX-ACCESS       not-accessible
    STATUS           current
    DESCRIPTION
        "Entry for the cfprApBiosVfAllUSBDevicesTable table."
    INDEX { cfprApBiosVfAllUSBDevicesInstanceId }
    ::= { cfprApBiosVfAllUSBDevicesTable 1 }

CfprApBiosVfAllUSBDevicesEntry ::= SEQUENCE {
    cfprApBiosVfAllUSBDevicesInstanceId                              CfprApManagedObjectId,
    cfprApBiosVfAllUSBDevicesDn                                      CfprApManagedObjectDn,
    cfprApBiosVfAllUSBDevicesRn                                      SnmpAdminString,
    cfprApBiosVfAllUSBDevicesVpAllUSBDevices                         CfprApBiosVfAllUSBDevicesVpAllUSBDevices
}

cfprApBiosVfAllUSBDevicesInstanceId OBJECT-TYPE
    SYNTAX       CfprApManagedObjectId
    MAX-ACCESS   not-accessible
    STATUS       current
    DESCRIPTION
        "Instance identifier of the managed object."
    ::= { cfprApBiosVfAllUSBDevicesEntry 1 }

cfprApBiosVfAllUSBDevicesDn OBJECT-TYPE
    SYNTAX       CfprApManagedObjectDn
    MAX-ACCESS   read-only
    STATUS       current
    DESCRIPTION
        "Cisco Firepower bios:VfAllUSBDevices:dn managed object property"
    ::= { cfprApBiosVfAllUSBDevicesEntry 2 }

cfprApBiosVfAllUSBDevicesRn OBJECT-TYPE
    SYNTAX       SnmpAdminString
    MAX-ACCESS   read-only
    STATUS       current
    DESCRIPTION
        "Cisco Firepower bios:VfAllUSBDevices:rn managed object property"
    ::= { cfprApBiosVfAllUSBDevicesEntry 3 }

cfprApBiosVfAllUSBDevicesVpAllUSBDevices OBJECT-TYPE
    SYNTAX       CfprApBiosVfAllUSBDevicesVpAllUSBDevices
    MAX-ACCESS   read-only
    STATUS       current
    DESCRIPTION
        "Cisco Firepower bios:VfAllUSBDevices:vpAllUSBDevices
        managed object property"
    ::= { cfprApBiosVfAllUSBDevicesEntry 4 }

cfprApBiosVfAltitudeTable OBJECT-TYPE
    SYNTAX           SEQUENCE OF CfprApBiosVfAltitudeEntry
    MAX-ACCESS       not-accessible
    STATUS           current
    DESCRIPTION
        "Cisco Firepower bios:VfAltitude managed object table"
    ::= { cfprApBiosObjects 14 }

cfprApBiosVfAltitudeEntry OBJECT-TYPE
    SYNTAX           CfprApBiosVfAltitudeEntry
    MAX-ACCESS       not-accessible
    STATUS           current
    DESCRIPTION
        "Entry for the cfprApBiosVfAltitudeTable table."
    INDEX { cfprApBiosVfAltitudeInstanceId }
    ::= { cfprApBiosVfAltitudeTable 1 }

CfprApBiosVfAltitudeEntry ::= SEQUENCE {
    cfprApBiosVfAltitudeInstanceId                                   CfprApManagedObjectId,
    cfprApBiosVfAltitudeDn                                           CfprApManagedObjectDn,
    cfprApBiosVfAltitudeRn                                           SnmpAdminString,
    cfprApBiosVfAltitudeVpAltitude                                   CfprApBiosVfAltitudeVpAltitude
}

cfprApBiosVfAltitudeInstanceId OBJECT-TYPE
    SYNTAX       CfprApManagedObjectId
    MAX-ACCESS   not-accessible
    STATUS       current
    DESCRIPTION
        "Instance identifier of the managed object."
    ::= { cfprApBiosVfAltitudeEntry 1 }

cfprApBiosVfAltitudeDn OBJECT-TYPE
    SYNTAX       CfprApManagedObjectDn
    MAX-ACCESS   read-only
    STATUS       current
    DESCRIPTION
        "Cisco Firepower bios:VfAltitude:dn managed object property"
    ::= { cfprApBiosVfAltitudeEntry 2 }

cfprApBiosVfAltitudeRn OBJECT-TYPE
    SYNTAX       SnmpAdminString
    MAX-ACCESS   read-only
    STATUS       current
    DESCRIPTION
        "Cisco Firepower bios:VfAltitude:rn managed object property"
    ::= { cfprApBiosVfAltitudeEntry 3 }

cfprApBiosVfAltitudeVpAltitude OBJECT-TYPE
    SYNTAX       CfprApBiosVfAltitudeVpAltitude
    MAX-ACCESS   read-only
    STATUS       current
    DESCRIPTION
        "Cisco Firepower bios:VfAltitude:vpAltitude managed
        object property"
    ::= { cfprApBiosVfAltitudeEntry 4 }

cfprApBiosVfAssertNMIOnPERRTable OBJECT-TYPE
    SYNTAX           SEQUENCE OF CfprApBiosVfAssertNMIOnPERREntry
    MAX-ACCESS       not-accessible
    STATUS           current
    DESCRIPTION
        "Cisco Firepower bios:VfAssertNMIOnPERR managed object table"
    ::= { cfprApBiosObjects 15 }

cfprApBiosVfAssertNMIOnPERREntry OBJECT-TYPE
    SYNTAX           CfprApBiosVfAssertNMIOnPERREntry
    MAX-ACCESS       not-accessible
    STATUS           current
    DESCRIPTION
        "Entry for the cfprApBiosVfAssertNMIOnPERRTable table."
    INDEX { cfprApBiosVfAssertNMIOnPERRInstanceId }
    ::= { cfprApBiosVfAssertNMIOnPERRTable 1 }

CfprApBiosVfAssertNMIOnPERREntry ::= SEQUENCE {
    cfprApBiosVfAssertNMIOnPERRInstanceId                            CfprApManagedObjectId,
    cfprApBiosVfAssertNMIOnPERRDn                                    CfprApManagedObjectDn,
    cfprApBiosVfAssertNMIOnPERRRn                                    SnmpAdminString,
    cfprApBiosVfAssertNMIOnPERRVpAssertNMIOnPERR                     CfprApBiosVfAssertNMIOnPERRVpAssertNMIOnPERR
}

cfprApBiosVfAssertNMIOnPERRInstanceId OBJECT-TYPE
    SYNTAX       CfprApManagedObjectId
    MAX-ACCESS   not-accessible
    STATUS       current
    DESCRIPTION
        "Instance identifier of the managed object."
    ::= { cfprApBiosVfAssertNMIOnPERREntry 1 }

cfprApBiosVfAssertNMIOnPERRDn OBJECT-TYPE
    SYNTAX       CfprApManagedObjectDn
    MAX-ACCESS   read-only
    STATUS       current
    DESCRIPTION
        "Cisco Firepower bios:VfAssertNMIOnPERR:dn managed
        object property"
    ::= { cfprApBiosVfAssertNMIOnPERREntry 2 }

cfprApBiosVfAssertNMIOnPERRRn OBJECT-TYPE
    SYNTAX       SnmpAdminString
    MAX-ACCESS   read-only
    STATUS       current
    DESCRIPTION
        "Cisco Firepower bios:VfAssertNMIOnPERR:rn managed
        object property"
    ::= { cfprApBiosVfAssertNMIOnPERREntry 3 }

cfprApBiosVfAssertNMIOnPERRVpAssertNMIOnPERR OBJECT-TYPE
    SYNTAX       CfprApBiosVfAssertNMIOnPERRVpAssertNMIOnPERR
    MAX-ACCESS   read-only
    STATUS       current
    DESCRIPTION
        "Cisco Firepower bios:VfAssertNMIOnPERR:vpAssertNMIOnPERR
        managed object property"
    ::= { cfprApBiosVfAssertNMIOnPERREntry 4 }

cfprApBiosVfAssertNMIOnSERRTable OBJECT-TYPE
    SYNTAX           SEQUENCE OF CfprApBiosVfAssertNMIOnSERREntry
    MAX-ACCESS       not-accessible
    STATUS           current
    DESCRIPTION
        "Cisco Firepower bios:VfAssertNMIOnSERR managed object table"
    ::= { cfprApBiosObjects 16 }

cfprApBiosVfAssertNMIOnSERREntry OBJECT-TYPE
    SYNTAX           CfprApBiosVfAssertNMIOnSERREntry
    MAX-ACCESS       not-accessible
    STATUS           current
    DESCRIPTION
        "Entry for the cfprApBiosVfAssertNMIOnSERRTable table."
    INDEX { cfprApBiosVfAssertNMIOnSERRInstanceId }
    ::= { cfprApBiosVfAssertNMIOnSERRTable 1 }

CfprApBiosVfAssertNMIOnSERREntry ::= SEQUENCE {
    cfprApBiosVfAssertNMIOnSERRInstanceId                            CfprApManagedObjectId,
    cfprApBiosVfAssertNMIOnSERRDn                                    CfprApManagedObjectDn,
    cfprApBiosVfAssertNMIOnSERRRn                                    SnmpAdminString,
    cfprApBiosVfAssertNMIOnSERRVpAssertNMIOnSERR                     CfprApBiosVfAssertNMIOnSERRVpAssertNMIOnSERR
}

cfprApBiosVfAssertNMIOnSERRInstanceId OBJECT-TYPE
    SYNTAX       CfprApManagedObjectId
    MAX-ACCESS   not-accessible
    STATUS       current
    DESCRIPTION
        "Instance identifier of the managed object."
    ::= { cfprApBiosVfAssertNMIOnSERREntry 1 }

cfprApBiosVfAssertNMIOnSERRDn OBJECT-TYPE
    SYNTAX       CfprApManagedObjectDn
    MAX-ACCESS   read-only
    STATUS       current
    DESCRIPTION
        "Cisco Firepower bios:VfAssertNMIOnSERR:dn managed
        object property"
    ::= { cfprApBiosVfAssertNMIOnSERREntry 2 }

cfprApBiosVfAssertNMIOnSERRRn OBJECT-TYPE
    SYNTAX       SnmpAdminString
    MAX-ACCESS   read-only
    STATUS       current
    DESCRIPTION
        "Cisco Firepower bios:VfAssertNMIOnSERR:rn managed
        object property"
    ::= { cfprApBiosVfAssertNMIOnSERREntry 3 }

cfprApBiosVfAssertNMIOnSERRVpAssertNMIOnSERR OBJECT-TYPE
    SYNTAX       CfprApBiosVfAssertNMIOnSERRVpAssertNMIOnSERR
    MAX-ACCESS   read-only
    STATUS       current
    DESCRIPTION
        "Cisco Firepower bios:VfAssertNMIOnSERR:vpAssertNMIOnSERR
        managed object property"
    ::= { cfprApBiosVfAssertNMIOnSERREntry 4 }

cfprApBiosVfBootOptionRetryTable OBJECT-TYPE
    SYNTAX           SEQUENCE OF CfprApBiosVfBootOptionRetryEntry
    MAX-ACCESS       not-accessible
    STATUS           current
    DESCRIPTION
        "Cisco Firepower bios:VfBootOptionRetry managed object table"
    ::= { cfprApBiosObjects 17 }

cfprApBiosVfBootOptionRetryEntry OBJECT-TYPE
    SYNTAX           CfprApBiosVfBootOptionRetryEntry
    MAX-ACCESS       not-accessible
    STATUS           current
    DESCRIPTION
        "Entry for the cfprApBiosVfBootOptionRetryTable table."
    INDEX { cfprApBiosVfBootOptionRetryInstanceId }
    ::= { cfprApBiosVfBootOptionRetryTable 1 }

CfprApBiosVfBootOptionRetryEntry ::= SEQUENCE {
    cfprApBiosVfBootOptionRetryInstanceId                            CfprApManagedObjectId,
    cfprApBiosVfBootOptionRetryDn                                    CfprApManagedObjectDn,
    cfprApBiosVfBootOptionRetryRn                                    SnmpAdminString,
    cfprApBiosVfBootOptionRetryVpBootOptionRetry                     CfprApBiosVfBootOptionRetryVpBootOptionRetry
}

cfprApBiosVfBootOptionRetryInstanceId OBJECT-TYPE
    SYNTAX       CfprApManagedObjectId
    MAX-ACCESS   not-accessible
    STATUS       current
    DESCRIPTION
        "Instance identifier of the managed object."
    ::= { cfprApBiosVfBootOptionRetryEntry 1 }

cfprApBiosVfBootOptionRetryDn OBJECT-TYPE
    SYNTAX       CfprApManagedObjectDn
    MAX-ACCESS   read-only
    STATUS       current
    DESCRIPTION
        "Cisco Firepower bios:VfBootOptionRetry:dn managed
        object property"
    ::= { cfprApBiosVfBootOptionRetryEntry 2 }

cfprApBiosVfBootOptionRetryRn OBJECT-TYPE
    SYNTAX       SnmpAdminString
    MAX-ACCESS   read-only
    STATUS       current
    DESCRIPTION
        "Cisco Firepower bios:VfBootOptionRetry:rn managed
        object property"
    ::= { cfprApBiosVfBootOptionRetryEntry 3 }

cfprApBiosVfBootOptionRetryVpBootOptionRetry OBJECT-TYPE
    SYNTAX       CfprApBiosVfBootOptionRetryVpBootOptionRetry
    MAX-ACCESS   read-only
    STATUS       current
    DESCRIPTION
        "Cisco Firepower bios:VfBootOptionRetry:vpBootOptionRetry
        managed object property"
    ::= { cfprApBiosVfBootOptionRetryEntry 4 }

cfprApBiosVfCPUPerformanceTable OBJECT-TYPE
    SYNTAX           SEQUENCE OF CfprApBiosVfCPUPerformanceEntry
    MAX-ACCESS       not-accessible
    STATUS           current
    DESCRIPTION
        "Cisco Firepower bios:VfCPUPerformance managed object table"
    ::= { cfprApBiosObjects 18 }

cfprApBiosVfCPUPerformanceEntry OBJECT-TYPE
    SYNTAX           CfprApBiosVfCPUPerformanceEntry
    MAX-ACCESS       not-accessible
    STATUS           current
    DESCRIPTION
        "Entry for the cfprApBiosVfCPUPerformanceTable table."
    INDEX { cfprApBiosVfCPUPerformanceInstanceId }
    ::= { cfprApBiosVfCPUPerformanceTable 1 }

CfprApBiosVfCPUPerformanceEntry ::= SEQUENCE {
    cfprApBiosVfCPUPerformanceInstanceId                             CfprApManagedObjectId,
    cfprApBiosVfCPUPerformanceDn                                     CfprApManagedObjectDn,
    cfprApBiosVfCPUPerformanceRn                                     SnmpAdminString,
    cfprApBiosVfCPUPerformanceVpCPUPerformance                       CfprApBiosVfCPUPerformanceVpCPUPerformance
}

cfprApBiosVfCPUPerformanceInstanceId OBJECT-TYPE
    SYNTAX       CfprApManagedObjectId
    MAX-ACCESS   not-accessible
    STATUS       current
    DESCRIPTION
        "Instance identifier of the managed object."
    ::= { cfprApBiosVfCPUPerformanceEntry 1 }

cfprApBiosVfCPUPerformanceDn OBJECT-TYPE
    SYNTAX       CfprApManagedObjectDn
    MAX-ACCESS   read-only
    STATUS       current
    DESCRIPTION
        "Cisco Firepower bios:VfCPUPerformance:dn managed object property"
    ::= { cfprApBiosVfCPUPerformanceEntry 2 }

cfprApBiosVfCPUPerformanceRn OBJECT-TYPE
    SYNTAX       SnmpAdminString
    MAX-ACCESS   read-only
    STATUS       current
    DESCRIPTION
        "Cisco Firepower bios:VfCPUPerformance:rn managed object property"
    ::= { cfprApBiosVfCPUPerformanceEntry 3 }

cfprApBiosVfCPUPerformanceVpCPUPerformance OBJECT-TYPE
    SYNTAX       CfprApBiosVfCPUPerformanceVpCPUPerformance
    MAX-ACCESS   read-only
    STATUS       current
    DESCRIPTION
        "Cisco Firepower bios:VfCPUPerformance:vpCPUPerformance
        managed object property"
    ::= { cfprApBiosVfCPUPerformanceEntry 4 }

cfprApBiosVfConsoleRedirectionTable OBJECT-TYPE
    SYNTAX           SEQUENCE OF CfprApBiosVfConsoleRedirectionEntry
    MAX-ACCESS       not-accessible
    STATUS           current
    DESCRIPTION
        "Cisco Firepower bios:VfConsoleRedirection managed object table"
    ::= { cfprApBiosObjects 19 }

cfprApBiosVfConsoleRedirectionEntry OBJECT-TYPE
    SYNTAX           CfprApBiosVfConsoleRedirectionEntry
    MAX-ACCESS       not-accessible
    STATUS           current
    DESCRIPTION
        "Entry for the cfprApBiosVfConsoleRedirectionTable table."
    INDEX { cfprApBiosVfConsoleRedirectionInstanceId }
    ::= { cfprApBiosVfConsoleRedirectionTable 1 }

CfprApBiosVfConsoleRedirectionEntry ::= SEQUENCE {
    cfprApBiosVfConsoleRedirectionInstanceId                         CfprApManagedObjectId,
    cfprApBiosVfConsoleRedirectionDn                                 CfprApManagedObjectDn,
    cfprApBiosVfConsoleRedirectionRn                                 SnmpAdminString,
    cfprApBiosVfConsoleRedirectionVpBaudRate                         CfprApBiosVfConsoleRedirectionVpBaudRate,
    cfprApBiosVfConsoleRedirectionVpConsoleRedirection               CfprApBiosVfConsoleRedirectionVpConsoleRedirection,
    cfprApBiosVfConsoleRedirectionVpFlowControl                      CfprApBiosVfConsoleRedirectionVpFlowControl,
    cfprApBiosVfConsoleRedirectionVpLegacyOSRedirection              CfprApBiosVfConsoleRedirectionVpLegacyOSRedirection,
    cfprApBiosVfConsoleRedirectionVpPuttyKeyPad                      CfprApBiosVfConsoleRedirectionVpPuttyKeyPad,
    cfprApBiosVfConsoleRedirectionVpTerminalType                     CfprApBiosVfConsoleRedirectionVpTerminalType
}

cfprApBiosVfConsoleRedirectionInstanceId OBJECT-TYPE
    SYNTAX       CfprApManagedObjectId
    MAX-ACCESS   not-accessible
    STATUS       current
    DESCRIPTION
        "Instance identifier of the managed object."
    ::= { cfprApBiosVfConsoleRedirectionEntry 1 }

cfprApBiosVfConsoleRedirectionDn OBJECT-TYPE
    SYNTAX       CfprApManagedObjectDn
    MAX-ACCESS   read-only
    STATUS       current
    DESCRIPTION
        "Cisco Firepower bios:VfConsoleRedirection:dn managed
        object property"
    ::= { cfprApBiosVfConsoleRedirectionEntry 2 }

cfprApBiosVfConsoleRedirectionRn OBJECT-TYPE
    SYNTAX       SnmpAdminString
    MAX-ACCESS   read-only
    STATUS       current
    DESCRIPTION
        "Cisco Firepower bios:VfConsoleRedirection:rn managed
        object property"
    ::= { cfprApBiosVfConsoleRedirectionEntry 3 }

cfprApBiosVfConsoleRedirectionVpBaudRate OBJECT-TYPE
    SYNTAX       CfprApBiosVfConsoleRedirectionVpBaudRate
    MAX-ACCESS   read-only
    STATUS       current
    DESCRIPTION
        "Cisco Firepower bios:VfConsoleRedirection:vpBaudRate
        managed object property"
    ::= { cfprApBiosVfConsoleRedirectionEntry 4 }

cfprApBiosVfConsoleRedirectionVpConsoleRedirection OBJECT-TYPE
    SYNTAX       CfprApBiosVfConsoleRedirectionVpConsoleRedirection
    MAX-ACCESS   read-only
    STATUS       current
    DESCRIPTION
        "Cisco Firepower bios:VfConsoleRedirection:vpConsoleRedirection
        managed object property"
    ::= { cfprApBiosVfConsoleRedirectionEntry 5 }

cfprApBiosVfConsoleRedirectionVpFlowControl OBJECT-TYPE
    SYNTAX       CfprApBiosVfConsoleRedirectionVpFlowControl
    MAX-ACCESS   read-only
    STATUS       current
    DESCRIPTION
        "Cisco Firepower bios:VfConsoleRedirection:vpFlowControl
        managed object property"
    ::= { cfprApBiosVfConsoleRedirectionEntry 6 }

cfprApBiosVfConsoleRedirectionVpLegacyOSRedirection OBJECT-TYPE
    SYNTAX       CfprApBiosVfConsoleRedirectionVpLegacyOSRedirection
    MAX-ACCESS   read-only
    STATUS       current
    DESCRIPTION
        "Cisco Firepower bios:VfConsoleRedirection:vpLegacyOSRedirection
        managed object property"
    ::= { cfprApBiosVfConsoleRedirectionEntry 7 }

cfprApBiosVfConsoleRedirectionVpPuttyKeyPad OBJECT-TYPE
    SYNTAX       CfprApBiosVfConsoleRedirectionVpPuttyKeyPad
    MAX-ACCESS   read-only
    STATUS       current
    DESCRIPTION
        "Cisco Firepower bios:VfConsoleRedirection:vpPuttyKeyPad
        managed object property"
    ::= { cfprApBiosVfConsoleRedirectionEntry 8 }

cfprApBiosVfConsoleRedirectionVpTerminalType OBJECT-TYPE
    SYNTAX       CfprApBiosVfConsoleRedirectionVpTerminalType
    MAX-ACCESS   read-only
    STATUS       current
    DESCRIPTION
        "Cisco Firepower bios:VfConsoleRedirection:vpTerminalType
        managed object property"
    ::= { cfprApBiosVfConsoleRedirectionEntry 9 }

cfprApBiosVfCoreMultiProcessingTable OBJECT-TYPE
    SYNTAX           SEQUENCE OF CfprApBiosVfCoreMultiProcessingEntry
    MAX-ACCESS       not-accessible
    STATUS           current
    DESCRIPTION
        "Cisco Firepower bios:VfCoreMultiProcessing managed object table"
    ::= { cfprApBiosObjects 20 }

cfprApBiosVfCoreMultiProcessingEntry OBJECT-TYPE
    SYNTAX           CfprApBiosVfCoreMultiProcessingEntry
    MAX-ACCESS       not-accessible
    STATUS           current
    DESCRIPTION
        "Entry for the cfprApBiosVfCoreMultiProcessingTable table."
    INDEX { cfprApBiosVfCoreMultiProcessingInstanceId }
    ::= { cfprApBiosVfCoreMultiProcessingTable 1 }

CfprApBiosVfCoreMultiProcessingEntry ::= SEQUENCE {
    cfprApBiosVfCoreMultiProcessingInstanceId                        CfprApManagedObjectId,
    cfprApBiosVfCoreMultiProcessingDn                                CfprApManagedObjectDn,
    cfprApBiosVfCoreMultiProcessingRn                                SnmpAdminString,
    cfprApBiosVfCoreMultiProcessingVpCoreMultiProcessing             CfprApBiosVfCoreMultiProcessingVpCoreMultiProcessing
}

cfprApBiosVfCoreMultiProcessingInstanceId OBJECT-TYPE
    SYNTAX       CfprApManagedObjectId
    MAX-ACCESS   not-accessible
    STATUS       current
    DESCRIPTION
        "Instance identifier of the managed object."
    ::= { cfprApBiosVfCoreMultiProcessingEntry 1 }

cfprApBiosVfCoreMultiProcessingDn OBJECT-TYPE
    SYNTAX       CfprApManagedObjectDn
    MAX-ACCESS   read-only
    STATUS       current
    DESCRIPTION
        "Cisco Firepower bios:VfCoreMultiProcessing:dn
        managed object property"
    ::= { cfprApBiosVfCoreMultiProcessingEntry 2 }

cfprApBiosVfCoreMultiProcessingRn OBJECT-TYPE
    SYNTAX       SnmpAdminString
    MAX-ACCESS   read-only
    STATUS       current
    DESCRIPTION
        "Cisco Firepower bios:VfCoreMultiProcessing:rn
        managed object property"
    ::= { cfprApBiosVfCoreMultiProcessingEntry 3 }

cfprApBiosVfCoreMultiProcessingVpCoreMultiProcessing OBJECT-TYPE
    SYNTAX       CfprApBiosVfCoreMultiProcessingVpCoreMultiProcessing
    MAX-ACCESS   read-only
    STATUS       current
    DESCRIPTION
        "Cisco Firepower bios:VfCoreMultiProcessing:vpCoreMultiProcessing
        managed object property"
    ::= { cfprApBiosVfCoreMultiProcessingEntry 4 }

cfprApBiosVfDRAMClockThrottlingTable OBJECT-TYPE
    SYNTAX           SEQUENCE OF CfprApBiosVfDRAMClockThrottlingEntry
    MAX-ACCESS       not-accessible
    STATUS           current
    DESCRIPTION
        "Cisco Firepower bios:VfDRAMClockThrottling managed object table"
    ::= { cfprApBiosObjects 21 }

cfprApBiosVfDRAMClockThrottlingEntry OBJECT-TYPE
    SYNTAX           CfprApBiosVfDRAMClockThrottlingEntry
    MAX-ACCESS       not-accessible
    STATUS           current
    DESCRIPTION
        "Entry for the cfprApBiosVfDRAMClockThrottlingTable table."
    INDEX { cfprApBiosVfDRAMClockThrottlingInstanceId }
    ::= { cfprApBiosVfDRAMClockThrottlingTable 1 }

CfprApBiosVfDRAMClockThrottlingEntry ::= SEQUENCE {
    cfprApBiosVfDRAMClockThrottlingInstanceId                        CfprApManagedObjectId,
    cfprApBiosVfDRAMClockThrottlingDn                                CfprApManagedObjectDn,
    cfprApBiosVfDRAMClockThrottlingRn                                SnmpAdminString,
    cfprApBiosVfDRAMClockThrottlingVpDRAMClockThrottling             CfprApBiosVfDRAMClockThrottlingVpDRAMClockThrottling
}

cfprApBiosVfDRAMClockThrottlingInstanceId OBJECT-TYPE
    SYNTAX       CfprApManagedObjectId
    MAX-ACCESS   not-accessible
    STATUS       current
    DESCRIPTION
        "Instance identifier of the managed object."
    ::= { cfprApBiosVfDRAMClockThrottlingEntry 1 }

cfprApBiosVfDRAMClockThrottlingDn OBJECT-TYPE
    SYNTAX       CfprApManagedObjectDn
    MAX-ACCESS   read-only
    STATUS       current
    DESCRIPTION
        "Cisco Firepower bios:VfDRAMClockThrottling:dn
        managed object property"
    ::= { cfprApBiosVfDRAMClockThrottlingEntry 2 }

cfprApBiosVfDRAMClockThrottlingRn OBJECT-TYPE
    SYNTAX       SnmpAdminString
    MAX-ACCESS   read-only
    STATUS       current
    DESCRIPTION
        "Cisco Firepower bios:VfDRAMClockThrottling:rn
        managed object property"
    ::= { cfprApBiosVfDRAMClockThrottlingEntry 3 }

cfprApBiosVfDRAMClockThrottlingVpDRAMClockThrottling OBJECT-TYPE
    SYNTAX       CfprApBiosVfDRAMClockThrottlingVpDRAMClockThrottling
    MAX-ACCESS   read-only
    STATUS       current
    DESCRIPTION
        "Cisco Firepower bios:VfDRAMClockThrottling:vpDRAMClockThrottling
        managed object property"
    ::= { cfprApBiosVfDRAMClockThrottlingEntry 4 }

cfprApBiosVfDirectCacheAccessTable OBJECT-TYPE
    SYNTAX           SEQUENCE OF CfprApBiosVfDirectCacheAccessEntry
    MAX-ACCESS       not-accessible
    STATUS           current
    DESCRIPTION
        "Cisco Firepower bios:VfDirectCacheAccess managed object table"
    ::= { cfprApBiosObjects 22 }

cfprApBiosVfDirectCacheAccessEntry OBJECT-TYPE
    SYNTAX           CfprApBiosVfDirectCacheAccessEntry
    MAX-ACCESS       not-accessible
    STATUS           current
    DESCRIPTION
        "Entry for the cfprApBiosVfDirectCacheAccessTable table."
    INDEX { cfprApBiosVfDirectCacheAccessInstanceId }
    ::= { cfprApBiosVfDirectCacheAccessTable 1 }

CfprApBiosVfDirectCacheAccessEntry ::= SEQUENCE {
    cfprApBiosVfDirectCacheAccessInstanceId                          CfprApManagedObjectId,
    cfprApBiosVfDirectCacheAccessDn                                  CfprApManagedObjectDn,
    cfprApBiosVfDirectCacheAccessRn                                  SnmpAdminString,
    cfprApBiosVfDirectCacheAccessVpDirectCacheAccess                 CfprApBiosVfDirectCacheAccessVpDirectCacheAccess
}

cfprApBiosVfDirectCacheAccessInstanceId OBJECT-TYPE
    SYNTAX       CfprApManagedObjectId
    MAX-ACCESS   not-accessible
    STATUS       current
    DESCRIPTION
        "Instance identifier of the managed object."
    ::= { cfprApBiosVfDirectCacheAccessEntry 1 }

cfprApBiosVfDirectCacheAccessDn OBJECT-TYPE
    SYNTAX       CfprApManagedObjectDn
    MAX-ACCESS   read-only
    STATUS       current
    DESCRIPTION
        "Cisco Firepower bios:VfDirectCacheAccess:dn managed
        object property"
    ::= { cfprApBiosVfDirectCacheAccessEntry 2 }

cfprApBiosVfDirectCacheAccessRn OBJECT-TYPE
    SYNTAX       SnmpAdminString
    MAX-ACCESS   read-only
    STATUS       current
    DESCRIPTION
        "Cisco Firepower bios:VfDirectCacheAccess:rn managed
        object property"
    ::= { cfprApBiosVfDirectCacheAccessEntry 3 }

cfprApBiosVfDirectCacheAccessVpDirectCacheAccess OBJECT-TYPE
    SYNTAX       CfprApBiosVfDirectCacheAccessVpDirectCacheAccess
    MAX-ACCESS   read-only
    STATUS       current
    DESCRIPTION
        "Cisco Firepower bios:VfDirectCacheAccess:vpDirectCacheAccess
        managed object property"
    ::= { cfprApBiosVfDirectCacheAccessEntry 4 }

cfprApBiosVfDramRefreshRateTable OBJECT-TYPE
    SYNTAX           SEQUENCE OF CfprApBiosVfDramRefreshRateEntry
    MAX-ACCESS       not-accessible
    STATUS           current
    DESCRIPTION
        "Cisco Firepower bios:VfDramRefreshRate managed object table"
    ::= { cfprApBiosObjects 23 }

cfprApBiosVfDramRefreshRateEntry OBJECT-TYPE
    SYNTAX           CfprApBiosVfDramRefreshRateEntry
    MAX-ACCESS       not-accessible
    STATUS           current
    DESCRIPTION
        "Entry for the cfprApBiosVfDramRefreshRateTable table."
    INDEX { cfprApBiosVfDramRefreshRateInstanceId }
    ::= { cfprApBiosVfDramRefreshRateTable 1 }

CfprApBiosVfDramRefreshRateEntry ::= SEQUENCE {
    cfprApBiosVfDramRefreshRateInstanceId                            CfprApManagedObjectId,
    cfprApBiosVfDramRefreshRateDn                                    CfprApManagedObjectDn,
    cfprApBiosVfDramRefreshRateRn                                    SnmpAdminString,
    cfprApBiosVfDramRefreshRateVpDramRefreshRate                     CfprApBiosVfDramRefreshRateVpDramRefreshRate
}

cfprApBiosVfDramRefreshRateInstanceId OBJECT-TYPE
    SYNTAX       CfprApManagedObjectId
    MAX-ACCESS   not-accessible
    STATUS       current
    DESCRIPTION
        "Instance identifier of the managed object."
    ::= { cfprApBiosVfDramRefreshRateEntry 1 }

cfprApBiosVfDramRefreshRateDn OBJECT-TYPE
    SYNTAX       CfprApManagedObjectDn
    MAX-ACCESS   read-only
    STATUS       current
    DESCRIPTION
        "Cisco Firepower bios:VfDramRefreshRate:dn managed
        object property"
    ::= { cfprApBiosVfDramRefreshRateEntry 2 }

cfprApBiosVfDramRefreshRateRn OBJECT-TYPE
    SYNTAX       SnmpAdminString
    MAX-ACCESS   read-only
    STATUS       current
    DESCRIPTION
        "Cisco Firepower bios:VfDramRefreshRate:rn managed
        object property"
    ::= { cfprApBiosVfDramRefreshRateEntry 3 }

cfprApBiosVfDramRefreshRateVpDramRefreshRate OBJECT-TYPE
    SYNTAX       CfprApBiosVfDramRefreshRateVpDramRefreshRate
    MAX-ACCESS   read-only
    STATUS       current
    DESCRIPTION
        "Cisco Firepower bios:VfDramRefreshRate:vpDramRefreshRate
        managed object property"
    ::= { cfprApBiosVfDramRefreshRateEntry 4 }

cfprApBiosVfEnhancedIntelSpeedStepTechTable OBJECT-TYPE
    SYNTAX           SEQUENCE OF CfprApBiosVfEnhancedIntelSpeedStepTechEntry
    MAX-ACCESS       not-accessible
    STATUS           current
    DESCRIPTION
        "Cisco Firepower bios:VfEnhancedIntelSpeedStepTech
        managed object table"
    ::= { cfprApBiosObjects 24 }

cfprApBiosVfEnhancedIntelSpeedStepTechEntry OBJECT-TYPE
    SYNTAX           CfprApBiosVfEnhancedIntelSpeedStepTechEntry
    MAX-ACCESS       not-accessible
    STATUS           current
    DESCRIPTION
        "Entry for the cfprApBiosVfEnhancedIntelSpeedStepTechTable table."
    INDEX { cfprApBiosVfEnhancedIntelSpeedStepTechInstanceId }
    ::= { cfprApBiosVfEnhancedIntelSpeedStepTechTable 1 }

CfprApBiosVfEnhancedIntelSpeedStepTechEntry ::= SEQUENCE {
    cfprApBiosVfEnhancedIntelSpeedStepTechInstanceId                 CfprApManagedObjectId,
    cfprApBiosVfEnhancedIntelSpeedStepTechDn                         CfprApManagedObjectDn,
    cfprApBiosVfEnhancedIntelSpeedStepTechRn                         SnmpAdminString,
    cfprApBiosVfEnhancedIntelSpeedStepTechVpEnhancedIntelSpeedStepTech CfprApBiosVfEnhancedIntelSpeedStepTechVpEnhancedIntelSpeedStepTech
}

cfprApBiosVfEnhancedIntelSpeedStepTechInstanceId OBJECT-TYPE
    SYNTAX       CfprApManagedObjectId
    MAX-ACCESS   not-accessible
    STATUS       current
    DESCRIPTION
        "Instance identifier of the managed object."
    ::= { cfprApBiosVfEnhancedIntelSpeedStepTechEntry 1 }

cfprApBiosVfEnhancedIntelSpeedStepTechDn OBJECT-TYPE
    SYNTAX       CfprApManagedObjectDn
    MAX-ACCESS   read-only
    STATUS       current
    DESCRIPTION
        "Cisco Firepower bios:VfEnhancedIntelSpeedStepTech:dn
        managed object property"
    ::= { cfprApBiosVfEnhancedIntelSpeedStepTechEntry 2 }

cfprApBiosVfEnhancedIntelSpeedStepTechRn OBJECT-TYPE
    SYNTAX       SnmpAdminString
    MAX-ACCESS   read-only
    STATUS       current
    DESCRIPTION
        "Cisco Firepower bios:VfEnhancedIntelSpeedStepTech:rn
        managed object property"
    ::= { cfprApBiosVfEnhancedIntelSpeedStepTechEntry 3 }

cfprApBiosVfEnhancedIntelSpeedStepTechVpEnhancedIntelSpeedStepTech OBJECT-TYPE
    SYNTAX       CfprApBiosVfEnhancedIntelSpeedStepTechVpEnhancedIntelSpeedStepTech
    MAX-ACCESS   read-only
    STATUS       current
    DESCRIPTION
        "Cisco Firepower bios:VfEnhancedIntelSpeedStepTech:vpEnhancedIntel
        SpeedStepTech managed object property"
    ::= { cfprApBiosVfEnhancedIntelSpeedStepTechEntry 4 }

cfprApBiosVfExecuteDisableBitTable OBJECT-TYPE
    SYNTAX           SEQUENCE OF CfprApBiosVfExecuteDisableBitEntry
    MAX-ACCESS       not-accessible
    STATUS           current
    DESCRIPTION
        "Cisco Firepower bios:VfExecuteDisableBit managed object table"
    ::= { cfprApBiosObjects 25 }

cfprApBiosVfExecuteDisableBitEntry OBJECT-TYPE
    SYNTAX           CfprApBiosVfExecuteDisableBitEntry
    MAX-ACCESS       not-accessible
    STATUS           current
    DESCRIPTION
        "Entry for the cfprApBiosVfExecuteDisableBitTable table."
    INDEX { cfprApBiosVfExecuteDisableBitInstanceId }
    ::= { cfprApBiosVfExecuteDisableBitTable 1 }

CfprApBiosVfExecuteDisableBitEntry ::= SEQUENCE {
    cfprApBiosVfExecuteDisableBitInstanceId                          CfprApManagedObjectId,
    cfprApBiosVfExecuteDisableBitDn                                  CfprApManagedObjectDn,
    cfprApBiosVfExecuteDisableBitRn                                  SnmpAdminString,
    cfprApBiosVfExecuteDisableBitVpExecuteDisableBit                 CfprApBiosVfExecuteDisableBitVpExecuteDisableBit
}

cfprApBiosVfExecuteDisableBitInstanceId OBJECT-TYPE
    SYNTAX       CfprApManagedObjectId
    MAX-ACCESS   not-accessible
    STATUS       current
    DESCRIPTION
        "Instance identifier of the managed object."
    ::= { cfprApBiosVfExecuteDisableBitEntry 1 }

cfprApBiosVfExecuteDisableBitDn OBJECT-TYPE
    SYNTAX       CfprApManagedObjectDn
    MAX-ACCESS   read-only
    STATUS       current
    DESCRIPTION
        "Cisco Firepower bios:VfExecuteDisableBit:dn managed
        object property"
    ::= { cfprApBiosVfExecuteDisableBitEntry 2 }

cfprApBiosVfExecuteDisableBitRn OBJECT-TYPE
    SYNTAX       SnmpAdminString
    MAX-ACCESS   read-only
    STATUS       current
    DESCRIPTION
        "Cisco Firepower bios:VfExecuteDisableBit:rn managed
        object property"
    ::= { cfprApBiosVfExecuteDisableBitEntry 3 }

cfprApBiosVfExecuteDisableBitVpExecuteDisableBit OBJECT-TYPE
    SYNTAX       CfprApBiosVfExecuteDisableBitVpExecuteDisableBit
    MAX-ACCESS   read-only
    STATUS       current
    DESCRIPTION
        "Cisco Firepower bios:VfExecuteDisableBit:vpExecuteDisableBit
        managed object property"
    ::= { cfprApBiosVfExecuteDisableBitEntry 4 }

cfprApBiosVfFRB2TimerTable OBJECT-TYPE
    SYNTAX           SEQUENCE OF CfprApBiosVfFRB2TimerEntry
    MAX-ACCESS       not-accessible
    STATUS           current
    DESCRIPTION
        "Cisco Firepower bios:VfFRB2Timer managed object table"
    ::= { cfprApBiosObjects 26 }

cfprApBiosVfFRB2TimerEntry OBJECT-TYPE
    SYNTAX           CfprApBiosVfFRB2TimerEntry
    MAX-ACCESS       not-accessible
    STATUS           current
    DESCRIPTION
        "Entry for the cfprApBiosVfFRB2TimerTable table."
    INDEX { cfprApBiosVfFRB2TimerInstanceId }
    ::= { cfprApBiosVfFRB2TimerTable 1 }

CfprApBiosVfFRB2TimerEntry ::= SEQUENCE {
    cfprApBiosVfFRB2TimerInstanceId                                  CfprApManagedObjectId,
    cfprApBiosVfFRB2TimerDn                                          CfprApManagedObjectDn,
    cfprApBiosVfFRB2TimerRn                                          SnmpAdminString,
    cfprApBiosVfFRB2TimerVpFRB2Timer                                 CfprApBiosVfFRB2TimerVpFRB2Timer
}

cfprApBiosVfFRB2TimerInstanceId OBJECT-TYPE
    SYNTAX       CfprApManagedObjectId
    MAX-ACCESS   not-accessible
    STATUS       current
    DESCRIPTION
        "Instance identifier of the managed object."
    ::= { cfprApBiosVfFRB2TimerEntry 1 }

cfprApBiosVfFRB2TimerDn OBJECT-TYPE
    SYNTAX       CfprApManagedObjectDn
    MAX-ACCESS   read-only
    STATUS       current
    DESCRIPTION
        "Cisco Firepower bios:VfFRB2Timer:dn managed object property"
    ::= { cfprApBiosVfFRB2TimerEntry 2 }

cfprApBiosVfFRB2TimerRn OBJECT-TYPE
    SYNTAX       SnmpAdminString
    MAX-ACCESS   read-only
    STATUS       current
    DESCRIPTION
        "Cisco Firepower bios:VfFRB2Timer:rn managed object property"
    ::= { cfprApBiosVfFRB2TimerEntry 3 }

cfprApBiosVfFRB2TimerVpFRB2Timer OBJECT-TYPE
    SYNTAX       CfprApBiosVfFRB2TimerVpFRB2Timer
    MAX-ACCESS   read-only
    STATUS       current
    DESCRIPTION
        "Cisco Firepower bios:VfFRB2Timer:vpFRB2Timer managed
        object property"
    ::= { cfprApBiosVfFRB2TimerEntry 4 }

cfprApBiosVfFrequencyFloorOverrideTable OBJECT-TYPE
    SYNTAX           SEQUENCE OF CfprApBiosVfFrequencyFloorOverrideEntry
    MAX-ACCESS       not-accessible
    STATUS           current
    DESCRIPTION
        "Cisco Firepower bios:VfFrequencyFloorOverride
        managed object table"
    ::= { cfprApBiosObjects 27 }

cfprApBiosVfFrequencyFloorOverrideEntry OBJECT-TYPE
    SYNTAX           CfprApBiosVfFrequencyFloorOverrideEntry
    MAX-ACCESS       not-accessible
    STATUS           current
    DESCRIPTION
        "Entry for the cfprApBiosVfFrequencyFloorOverrideTable table."
    INDEX { cfprApBiosVfFrequencyFloorOverrideInstanceId }
    ::= { cfprApBiosVfFrequencyFloorOverrideTable 1 }

CfprApBiosVfFrequencyFloorOverrideEntry ::= SEQUENCE {
    cfprApBiosVfFrequencyFloorOverrideInstanceId                     CfprApManagedObjectId,
    cfprApBiosVfFrequencyFloorOverrideDn                             CfprApManagedObjectDn,
    cfprApBiosVfFrequencyFloorOverrideRn                             SnmpAdminString,
    cfprApBiosVfFrequencyFloorOverrideVpFrequencyFloorOverride       CfprApBiosVfFrequencyFloorOverrideVpFrequencyFloorOverride
}

cfprApBiosVfFrequencyFloorOverrideInstanceId OBJECT-TYPE
    SYNTAX       CfprApManagedObjectId
    MAX-ACCESS   not-accessible
    STATUS       current
    DESCRIPTION
        "Instance identifier of the managed object."
    ::= { cfprApBiosVfFrequencyFloorOverrideEntry 1 }

cfprApBiosVfFrequencyFloorOverrideDn OBJECT-TYPE
    SYNTAX       CfprApManagedObjectDn
    MAX-ACCESS   read-only
    STATUS       current
    DESCRIPTION
        "Cisco Firepower bios:VfFrequencyFloorOverride:dn
        managed object property"
    ::= { cfprApBiosVfFrequencyFloorOverrideEntry 2 }

cfprApBiosVfFrequencyFloorOverrideRn OBJECT-TYPE
    SYNTAX       SnmpAdminString
    MAX-ACCESS   read-only
    STATUS       current
    DESCRIPTION
        "Cisco Firepower bios:VfFrequencyFloorOverride:rn
        managed object property"
    ::= { cfprApBiosVfFrequencyFloorOverrideEntry 3 }

cfprApBiosVfFrequencyFloorOverrideVpFrequencyFloorOverride OBJECT-TYPE
    SYNTAX       CfprApBiosVfFrequencyFloorOverrideVpFrequencyFloorOverride
    MAX-ACCESS   read-only
    STATUS       current
    DESCRIPTION
        "Cisco Firepower bios:VfFrequencyFloorOverride:vpFrequencyFloorOve
        rride managed object property"
    ::= { cfprApBiosVfFrequencyFloorOverrideEntry 4 }

cfprApBiosVfFrontPanelLockoutTable OBJECT-TYPE
    SYNTAX           SEQUENCE OF CfprApBiosVfFrontPanelLockoutEntry
    MAX-ACCESS       not-accessible
    STATUS           current
    DESCRIPTION
        "Cisco Firepower bios:VfFrontPanelLockout managed object table"
    ::= { cfprApBiosObjects 28 }

cfprApBiosVfFrontPanelLockoutEntry OBJECT-TYPE
    SYNTAX           CfprApBiosVfFrontPanelLockoutEntry
    MAX-ACCESS       not-accessible
    STATUS           current
    DESCRIPTION
        "Entry for the cfprApBiosVfFrontPanelLockoutTable table."
    INDEX { cfprApBiosVfFrontPanelLockoutInstanceId }
    ::= { cfprApBiosVfFrontPanelLockoutTable 1 }

CfprApBiosVfFrontPanelLockoutEntry ::= SEQUENCE {
    cfprApBiosVfFrontPanelLockoutInstanceId                          CfprApManagedObjectId,
    cfprApBiosVfFrontPanelLockoutDn                                  CfprApManagedObjectDn,
    cfprApBiosVfFrontPanelLockoutRn                                  SnmpAdminString,
    cfprApBiosVfFrontPanelLockoutVpFrontPanelLockout                 CfprApBiosVfFrontPanelLockoutVpFrontPanelLockout
}

cfprApBiosVfFrontPanelLockoutInstanceId OBJECT-TYPE
    SYNTAX       CfprApManagedObjectId
    MAX-ACCESS   not-accessible
    STATUS       current
    DESCRIPTION
        "Instance identifier of the managed object."
    ::= { cfprApBiosVfFrontPanelLockoutEntry 1 }

cfprApBiosVfFrontPanelLockoutDn OBJECT-TYPE
    SYNTAX       CfprApManagedObjectDn
    MAX-ACCESS   read-only
    STATUS       current
    DESCRIPTION
        "Cisco Firepower bios:VfFrontPanelLockout:dn managed
        object property"
    ::= { cfprApBiosVfFrontPanelLockoutEntry 2 }

cfprApBiosVfFrontPanelLockoutRn OBJECT-TYPE
    SYNTAX       SnmpAdminString
    MAX-ACCESS   read-only
    STATUS       current
    DESCRIPTION
        "Cisco Firepower bios:VfFrontPanelLockout:rn managed
        object property"
    ::= { cfprApBiosVfFrontPanelLockoutEntry 3 }

cfprApBiosVfFrontPanelLockoutVpFrontPanelLockout OBJECT-TYPE
    SYNTAX       CfprApBiosVfFrontPanelLockoutVpFrontPanelLockout
    MAX-ACCESS   read-only
    STATUS       current
    DESCRIPTION
        "Cisco Firepower bios:VfFrontPanelLockout:vpFrontPanelLockout
        managed object property"
    ::= { cfprApBiosVfFrontPanelLockoutEntry 4 }

cfprApBiosVfIntelEntrySASRAIDModuleTable OBJECT-TYPE
    SYNTAX           SEQUENCE OF CfprApBiosVfIntelEntrySASRAIDModuleEntry
    MAX-ACCESS       not-accessible
    STATUS           current
    DESCRIPTION
        "Cisco Firepower bios:VfIntelEntrySASRAIDModule
        managed object table"
    ::= { cfprApBiosObjects 29 }

cfprApBiosVfIntelEntrySASRAIDModuleEntry OBJECT-TYPE
    SYNTAX           CfprApBiosVfIntelEntrySASRAIDModuleEntry
    MAX-ACCESS       not-accessible
    STATUS           current
    DESCRIPTION
        "Entry for the cfprApBiosVfIntelEntrySASRAIDModuleTable table."
    INDEX { cfprApBiosVfIntelEntrySASRAIDModuleInstanceId }
    ::= { cfprApBiosVfIntelEntrySASRAIDModuleTable 1 }

CfprApBiosVfIntelEntrySASRAIDModuleEntry ::= SEQUENCE {
    cfprApBiosVfIntelEntrySASRAIDModuleInstanceId                    CfprApManagedObjectId,
    cfprApBiosVfIntelEntrySASRAIDModuleDn                            CfprApManagedObjectDn,
    cfprApBiosVfIntelEntrySASRAIDModuleRn                            SnmpAdminString,
    cfprApBiosVfIntelEntrySASRAIDModuleVpSASRAID                     CfprApBiosVfIntelEntrySASRAIDModuleVpSASRAID,
    cfprApBiosVfIntelEntrySASRAIDModuleVpSASRAIDModule               CfprApBiosVfIntelEntrySASRAIDModuleVpSASRAIDModule
}

cfprApBiosVfIntelEntrySASRAIDModuleInstanceId OBJECT-TYPE
    SYNTAX       CfprApManagedObjectId
    MAX-ACCESS   not-accessible
    STATUS       current
    DESCRIPTION
        "Instance identifier of the managed object."
    ::= { cfprApBiosVfIntelEntrySASRAIDModuleEntry 1 }

cfprApBiosVfIntelEntrySASRAIDModuleDn OBJECT-TYPE
    SYNTAX       CfprApManagedObjectDn
    MAX-ACCESS   read-only
    STATUS       current
    DESCRIPTION
        "Cisco Firepower bios:VfIntelEntrySASRAIDModule:dn
        managed object property"
    ::= { cfprApBiosVfIntelEntrySASRAIDModuleEntry 2 }

cfprApBiosVfIntelEntrySASRAIDModuleRn OBJECT-TYPE
    SYNTAX       SnmpAdminString
    MAX-ACCESS   read-only
    STATUS       current
    DESCRIPTION
        "Cisco Firepower bios:VfIntelEntrySASRAIDModule:rn
        managed object property"
    ::= { cfprApBiosVfIntelEntrySASRAIDModuleEntry 3 }

cfprApBiosVfIntelEntrySASRAIDModuleVpSASRAID OBJECT-TYPE
    SYNTAX       CfprApBiosVfIntelEntrySASRAIDModuleVpSASRAID
    MAX-ACCESS   read-only
    STATUS       current
    DESCRIPTION
        "Cisco Firepower bios:VfIntelEntrySASRAIDModule:vpSASRAID
        managed object property"
    ::= { cfprApBiosVfIntelEntrySASRAIDModuleEntry 4 }

cfprApBiosVfIntelEntrySASRAIDModuleVpSASRAIDModule OBJECT-TYPE
    SYNTAX       CfprApBiosVfIntelEntrySASRAIDModuleVpSASRAIDModule
    MAX-ACCESS   read-only
    STATUS       current
    DESCRIPTION
        "Cisco Firepower bios:VfIntelEntrySASRAIDModule:vpSASRAIDModule
        managed object property"
    ::= { cfprApBiosVfIntelEntrySASRAIDModuleEntry 5 }

cfprApBiosVfIntelHyperThreadingTechTable OBJECT-TYPE
    SYNTAX           SEQUENCE OF CfprApBiosVfIntelHyperThreadingTechEntry
    MAX-ACCESS       not-accessible
    STATUS           current
    DESCRIPTION
        "Cisco Firepower bios:VfIntelHyperThreadingTech
        managed object table"
    ::= { cfprApBiosObjects 30 }

cfprApBiosVfIntelHyperThreadingTechEntry OBJECT-TYPE
    SYNTAX           CfprApBiosVfIntelHyperThreadingTechEntry
    MAX-ACCESS       not-accessible
    STATUS           current
    DESCRIPTION
        "Entry for the cfprApBiosVfIntelHyperThreadingTechTable table."
    INDEX { cfprApBiosVfIntelHyperThreadingTechInstanceId }
    ::= { cfprApBiosVfIntelHyperThreadingTechTable 1 }

CfprApBiosVfIntelHyperThreadingTechEntry ::= SEQUENCE {
    cfprApBiosVfIntelHyperThreadingTechInstanceId                    CfprApManagedObjectId,
    cfprApBiosVfIntelHyperThreadingTechDn                            CfprApManagedObjectDn,
    cfprApBiosVfIntelHyperThreadingTechRn                            SnmpAdminString,
    cfprApBiosVfIntelHyperThreadingTechVpIntelHyperThreadingTech     CfprApBiosVfIntelHyperThreadingTechVpIntelHyperThreadingTech
}

cfprApBiosVfIntelHyperThreadingTechInstanceId OBJECT-TYPE
    SYNTAX       CfprApManagedObjectId
    MAX-ACCESS   not-accessible
    STATUS       current
    DESCRIPTION
        "Instance identifier of the managed object."
    ::= { cfprApBiosVfIntelHyperThreadingTechEntry 1 }

cfprApBiosVfIntelHyperThreadingTechDn OBJECT-TYPE
    SYNTAX       CfprApManagedObjectDn
    MAX-ACCESS   read-only
    STATUS       current
    DESCRIPTION
        "Cisco Firepower bios:VfIntelHyperThreadingTech:dn
        managed object property"
    ::= { cfprApBiosVfIntelHyperThreadingTechEntry 2 }

cfprApBiosVfIntelHyperThreadingTechRn OBJECT-TYPE
    SYNTAX       SnmpAdminString
    MAX-ACCESS   read-only
    STATUS       current
    DESCRIPTION
        "Cisco Firepower bios:VfIntelHyperThreadingTech:rn
        managed object property"
    ::= { cfprApBiosVfIntelHyperThreadingTechEntry 3 }

cfprApBiosVfIntelHyperThreadingTechVpIntelHyperThreadingTech OBJECT-TYPE
    SYNTAX       CfprApBiosVfIntelHyperThreadingTechVpIntelHyperThreadingTech
    MAX-ACCESS   read-only
    STATUS       current
    DESCRIPTION
        "Cisco Firepower bios:VfIntelHyperThreadingTech:vpIntelHyperThread
        ingTech managed object property"
    ::= { cfprApBiosVfIntelHyperThreadingTechEntry 4 }

cfprApBiosVfIntelTurboBoostTechTable OBJECT-TYPE
    SYNTAX           SEQUENCE OF CfprApBiosVfIntelTurboBoostTechEntry
    MAX-ACCESS       not-accessible
    STATUS           current
    DESCRIPTION
        "Cisco Firepower bios:VfIntelTurboBoostTech managed object table"
    ::= { cfprApBiosObjects 31 }

cfprApBiosVfIntelTurboBoostTechEntry OBJECT-TYPE
    SYNTAX           CfprApBiosVfIntelTurboBoostTechEntry
    MAX-ACCESS       not-accessible
    STATUS           current
    DESCRIPTION
        "Entry for the cfprApBiosVfIntelTurboBoostTechTable table."
    INDEX { cfprApBiosVfIntelTurboBoostTechInstanceId }
    ::= { cfprApBiosVfIntelTurboBoostTechTable 1 }

CfprApBiosVfIntelTurboBoostTechEntry ::= SEQUENCE {
    cfprApBiosVfIntelTurboBoostTechInstanceId                        CfprApManagedObjectId,
    cfprApBiosVfIntelTurboBoostTechDn                                CfprApManagedObjectDn,
    cfprApBiosVfIntelTurboBoostTechRn                                SnmpAdminString,
    cfprApBiosVfIntelTurboBoostTechVpIntelTurboBoostTech             CfprApBiosVfIntelTurboBoostTechVpIntelTurboBoostTech
}

cfprApBiosVfIntelTurboBoostTechInstanceId OBJECT-TYPE
    SYNTAX       CfprApManagedObjectId
    MAX-ACCESS   not-accessible
    STATUS       current
    DESCRIPTION
        "Instance identifier of the managed object."
    ::= { cfprApBiosVfIntelTurboBoostTechEntry 1 }

cfprApBiosVfIntelTurboBoostTechDn OBJECT-TYPE
    SYNTAX       CfprApManagedObjectDn
    MAX-ACCESS   read-only
    STATUS       current
    DESCRIPTION
        "Cisco Firepower bios:VfIntelTurboBoostTech:dn
        managed object property"
    ::= { cfprApBiosVfIntelTurboBoostTechEntry 2 }

cfprApBiosVfIntelTurboBoostTechRn OBJECT-TYPE
    SYNTAX       SnmpAdminString
    MAX-ACCESS   read-only
    STATUS       current
    DESCRIPTION
        "Cisco Firepower bios:VfIntelTurboBoostTech:rn
        managed object property"
    ::= { cfprApBiosVfIntelTurboBoostTechEntry 3 }

cfprApBiosVfIntelTurboBoostTechVpIntelTurboBoostTech OBJECT-TYPE
    SYNTAX       CfprApBiosVfIntelTurboBoostTechVpIntelTurboBoostTech
    MAX-ACCESS   read-only
    STATUS       current
    DESCRIPTION
        "Cisco Firepower bios:VfIntelTurboBoostTech:vpIntelTurboBoostTech
        managed object property"
    ::= { cfprApBiosVfIntelTurboBoostTechEntry 4 }

cfprApBiosVfIntelVTForDirectedIOTable OBJECT-TYPE
    SYNTAX           SEQUENCE OF CfprApBiosVfIntelVTForDirectedIOEntry
    MAX-ACCESS       not-accessible
    STATUS           current
    DESCRIPTION
        "Cisco Firepower bios:VfIntelVTForDirectedIO managed object table"
    ::= { cfprApBiosObjects 32 }

cfprApBiosVfIntelVTForDirectedIOEntry OBJECT-TYPE
    SYNTAX           CfprApBiosVfIntelVTForDirectedIOEntry
    MAX-ACCESS       not-accessible
    STATUS           current
    DESCRIPTION
        "Entry for the cfprApBiosVfIntelVTForDirectedIOTable table."
    INDEX { cfprApBiosVfIntelVTForDirectedIOInstanceId }
    ::= { cfprApBiosVfIntelVTForDirectedIOTable 1 }

CfprApBiosVfIntelVTForDirectedIOEntry ::= SEQUENCE {
    cfprApBiosVfIntelVTForDirectedIOInstanceId                       CfprApManagedObjectId,
    cfprApBiosVfIntelVTForDirectedIODn                               CfprApManagedObjectDn,
    cfprApBiosVfIntelVTForDirectedIORn                               SnmpAdminString,
    cfprApBiosVfIntelVTForDirectedIOVpIntelVTDATSSupport             CfprApBiosVfIntelVTForDirectedIOVpIntelVTDATSSupport,
    cfprApBiosVfIntelVTForDirectedIOVpIntelVTDCoherencySupport       CfprApBiosVfIntelVTForDirectedIOVpIntelVTDCoherencySupport,
    cfprApBiosVfIntelVTForDirectedIOVpIntelVTDInterruptRemapping     CfprApBiosVfIntelVTForDirectedIOVpIntelVTDInterruptRemapping,
    cfprApBiosVfIntelVTForDirectedIOVpIntelVTDPassThroughDMASupport  CfprApBiosVfIntelVTForDirectedIOVpIntelVTDPassThroughDMASupport,
    cfprApBiosVfIntelVTForDirectedIOVpIntelVTForDirectedIO           CfprApBiosVfIntelVTForDirectedIOVpIntelVTForDirectedIO
}

cfprApBiosVfIntelVTForDirectedIOInstanceId OBJECT-TYPE
    SYNTAX       CfprApManagedObjectId
    MAX-ACCESS   not-accessible
    STATUS       current
    DESCRIPTION
        "Instance identifier of the managed object."
    ::= { cfprApBiosVfIntelVTForDirectedIOEntry 1 }

cfprApBiosVfIntelVTForDirectedIODn OBJECT-TYPE
    SYNTAX       CfprApManagedObjectDn
    MAX-ACCESS   read-only
    STATUS       current
    DESCRIPTION
        "Cisco Firepower bios:VfIntelVTForDirectedIO:dn
        managed object property"
    ::= { cfprApBiosVfIntelVTForDirectedIOEntry 2 }

cfprApBiosVfIntelVTForDirectedIORn OBJECT-TYPE
    SYNTAX       SnmpAdminString
    MAX-ACCESS   read-only
    STATUS       current
    DESCRIPTION
        "Cisco Firepower bios:VfIntelVTForDirectedIO:rn
        managed object property"
    ::= { cfprApBiosVfIntelVTForDirectedIOEntry 3 }

cfprApBiosVfIntelVTForDirectedIOVpIntelVTDATSSupport OBJECT-TYPE
    SYNTAX       CfprApBiosVfIntelVTForDirectedIOVpIntelVTDATSSupport
    MAX-ACCESS   read-only
    STATUS       current
    DESCRIPTION
        "Cisco Firepower bios:VfIntelVTForDirectedIO:vpIntelVTDATSSupport
        managed object property"
    ::= { cfprApBiosVfIntelVTForDirectedIOEntry 4 }

cfprApBiosVfIntelVTForDirectedIOVpIntelVTDCoherencySupport OBJECT-TYPE
    SYNTAX       CfprApBiosVfIntelVTForDirectedIOVpIntelVTDCoherencySupport
    MAX-ACCESS   read-only
    STATUS       current
    DESCRIPTION
        "Cisco Firepower bios:VfIntelVTForDirectedIO:vpIntelVTDCoherencySu
        pport managed object property"
    ::= { cfprApBiosVfIntelVTForDirectedIOEntry 5 }

cfprApBiosVfIntelVTForDirectedIOVpIntelVTDInterruptRemapping OBJECT-TYPE
    SYNTAX       CfprApBiosVfIntelVTForDirectedIOVpIntelVTDInterruptRemapping
    MAX-ACCESS   read-only
    STATUS       current
    DESCRIPTION
        "Cisco Firepower bios:VfIntelVTForDirectedIO:vpIntelVTDInterruptRe
        mapping managed object property"
    ::= { cfprApBiosVfIntelVTForDirectedIOEntry 6 }

cfprApBiosVfIntelVTForDirectedIOVpIntelVTDPassThroughDMASupport OBJECT-TYPE
    SYNTAX       CfprApBiosVfIntelVTForDirectedIOVpIntelVTDPassThroughDMASupport
    MAX-ACCESS   read-only
    STATUS       current
    DESCRIPTION
        "Cisco Firepower bios:VfIntelVTForDirectedIO:vpIntelVTDPassThrough
        DMASupport managed object property"
    ::= { cfprApBiosVfIntelVTForDirectedIOEntry 7 }

cfprApBiosVfIntelVTForDirectedIOVpIntelVTForDirectedIO OBJECT-TYPE
    SYNTAX       CfprApBiosVfIntelVTForDirectedIOVpIntelVTForDirectedIO
    MAX-ACCESS   read-only
    STATUS       current
    DESCRIPTION
        "Cisco Firepower bios:VfIntelVTForDirectedIO:vpIntelVTForDirectedI
        O managed object property"
    ::= { cfprApBiosVfIntelVTForDirectedIOEntry 8 }

cfprApBiosVfIntelVirtualizationTechnologyTable OBJECT-TYPE
    SYNTAX           SEQUENCE OF CfprApBiosVfIntelVirtualizationTechnologyEntry
    MAX-ACCESS       not-accessible
    STATUS           current
    DESCRIPTION
        "Cisco Firepower bios:VfIntelVirtualizationTechnology
        managed object table"
    ::= { cfprApBiosObjects 33 }

cfprApBiosVfIntelVirtualizationTechnologyEntry OBJECT-TYPE
    SYNTAX           CfprApBiosVfIntelVirtualizationTechnologyEntry
    MAX-ACCESS       not-accessible
    STATUS           current
    DESCRIPTION
        "Entry for the cfprApBiosVfIntelVirtualizationTechnologyTable table."
    INDEX { cfprApBiosVfIntelVirtualizationTechnologyInstanceId }
    ::= { cfprApBiosVfIntelVirtualizationTechnologyTable 1 }

CfprApBiosVfIntelVirtualizationTechnologyEntry ::= SEQUENCE {
    cfprApBiosVfIntelVirtualizationTechnologyInstanceId              CfprApManagedObjectId,
    cfprApBiosVfIntelVirtualizationTechnologyDn                      CfprApManagedObjectDn,
    cfprApBiosVfIntelVirtualizationTechnologyRn                      SnmpAdminString,
    cfprApBiosVfIntelVirtualizationTechnologyVpIntelVirtualizationTechnology CfprApBiosVfIntelVirtualizationTechnologyVpIntelVirtTechnology
}

cfprApBiosVfIntelVirtualizationTechnologyInstanceId OBJECT-TYPE
    SYNTAX       CfprApManagedObjectId
    MAX-ACCESS   not-accessible
    STATUS       current
    DESCRIPTION
        "Instance identifier of the managed object."
    ::= { cfprApBiosVfIntelVirtualizationTechnologyEntry 1 }

cfprApBiosVfIntelVirtualizationTechnologyDn OBJECT-TYPE
    SYNTAX       CfprApManagedObjectDn
    MAX-ACCESS   read-only
    STATUS       current
    DESCRIPTION
        "Cisco Firepower bios:VfIntelVirtualizationTechnology:dn
        managed object property"
    ::= { cfprApBiosVfIntelVirtualizationTechnologyEntry 2 }

cfprApBiosVfIntelVirtualizationTechnologyRn OBJECT-TYPE
    SYNTAX       SnmpAdminString
    MAX-ACCESS   read-only
    STATUS       current
    DESCRIPTION
        "Cisco Firepower bios:VfIntelVirtualizationTechnology:rn
        managed object property"
    ::= { cfprApBiosVfIntelVirtualizationTechnologyEntry 3 }

cfprApBiosVfIntelVirtualizationTechnologyVpIntelVirtualizationTechnology OBJECT-TYPE
    SYNTAX       CfprApBiosVfIntelVirtualizationTechnologyVpIntelVirtTechnology
    MAX-ACCESS   read-only
    STATUS       current
    DESCRIPTION
        "Cisco Firepower bios:VfIntelVirtualizationTechnology:vpIntelVirtu
        alizationTechnology managed object property"
    ::= { cfprApBiosVfIntelVirtualizationTechnologyEntry 4 }

cfprApBiosVfInterleaveConfigurationTable OBJECT-TYPE
    SYNTAX           SEQUENCE OF CfprApBiosVfInterleaveConfigurationEntry
    MAX-ACCESS       not-accessible
    STATUS           current
    DESCRIPTION
        "Cisco Firepower bios:VfInterleaveConfiguration
        managed object table"
    ::= { cfprApBiosObjects 34 }

cfprApBiosVfInterleaveConfigurationEntry OBJECT-TYPE
    SYNTAX           CfprApBiosVfInterleaveConfigurationEntry
    MAX-ACCESS       not-accessible
    STATUS           current
    DESCRIPTION
        "Entry for the cfprApBiosVfInterleaveConfigurationTable table."
    INDEX { cfprApBiosVfInterleaveConfigurationInstanceId }
    ::= { cfprApBiosVfInterleaveConfigurationTable 1 }

CfprApBiosVfInterleaveConfigurationEntry ::= SEQUENCE {
    cfprApBiosVfInterleaveConfigurationInstanceId                    CfprApManagedObjectId,
    cfprApBiosVfInterleaveConfigurationDn                            CfprApManagedObjectDn,
    cfprApBiosVfInterleaveConfigurationRn                            SnmpAdminString,
    cfprApBiosVfInterleaveConfigurationVpChannelInterleaving         CfprApBiosVfInterleaveConfigurationVpChannelInterleaving,
    cfprApBiosVfInterleaveConfigurationVpMemoryInterleaving          CfprApBiosVfInterleaveConfigurationVpMemoryInterleaving,
    cfprApBiosVfInterleaveConfigurationVpRankInterleaving            CfprApBiosVfInterleaveConfigurationVpRankInterleaving
}

cfprApBiosVfInterleaveConfigurationInstanceId OBJECT-TYPE
    SYNTAX       CfprApManagedObjectId
    MAX-ACCESS   not-accessible
    STATUS       current
    DESCRIPTION
        "Instance identifier of the managed object."
    ::= { cfprApBiosVfInterleaveConfigurationEntry 1 }

cfprApBiosVfInterleaveConfigurationDn OBJECT-TYPE
    SYNTAX       CfprApManagedObjectDn
    MAX-ACCESS   read-only
    STATUS       current
    DESCRIPTION
        "Cisco Firepower bios:VfInterleaveConfiguration:dn
        managed object property"
    ::= { cfprApBiosVfInterleaveConfigurationEntry 2 }

cfprApBiosVfInterleaveConfigurationRn OBJECT-TYPE
    SYNTAX       SnmpAdminString
    MAX-ACCESS   read-only
    STATUS       current
    DESCRIPTION
        "Cisco Firepower bios:VfInterleaveConfiguration:rn
        managed object property"
    ::= { cfprApBiosVfInterleaveConfigurationEntry 3 }

cfprApBiosVfInterleaveConfigurationVpChannelInterleaving OBJECT-TYPE
    SYNTAX       CfprApBiosVfInterleaveConfigurationVpChannelInterleaving
    MAX-ACCESS   read-only
    STATUS       current
    DESCRIPTION
        "Cisco Firepower bios:VfInterleaveConfiguration:vpChannelInterleav
        ing managed object property"
    ::= { cfprApBiosVfInterleaveConfigurationEntry 4 }

cfprApBiosVfInterleaveConfigurationVpMemoryInterleaving OBJECT-TYPE
    SYNTAX       CfprApBiosVfInterleaveConfigurationVpMemoryInterleaving
    MAX-ACCESS   read-only
    STATUS       current
    DESCRIPTION
        "Cisco Firepower bios:VfInterleaveConfiguration:vpMemoryInterleavi
        ng managed object property"
    ::= { cfprApBiosVfInterleaveConfigurationEntry 5 }

cfprApBiosVfInterleaveConfigurationVpRankInterleaving OBJECT-TYPE
    SYNTAX       CfprApBiosVfInterleaveConfigurationVpRankInterleaving
    MAX-ACCESS   read-only
    STATUS       current
    DESCRIPTION
        "Cisco Firepower bios:VfInterleaveConfiguration:vpRankInterleaving
         managed object property"
    ::= { cfprApBiosVfInterleaveConfigurationEntry 6 }

cfprApBiosVfLocalX2ApicTable OBJECT-TYPE
    SYNTAX           SEQUENCE OF CfprApBiosVfLocalX2ApicEntry
    MAX-ACCESS       not-accessible
    STATUS           current
    DESCRIPTION
        "Cisco Firepower bios:VfLocalX2Apic managed object table"
    ::= { cfprApBiosObjects 35 }

cfprApBiosVfLocalX2ApicEntry OBJECT-TYPE
    SYNTAX           CfprApBiosVfLocalX2ApicEntry
    MAX-ACCESS       not-accessible
    STATUS           current
    DESCRIPTION
        "Entry for the cfprApBiosVfLocalX2ApicTable table."
    INDEX { cfprApBiosVfLocalX2ApicInstanceId }
    ::= { cfprApBiosVfLocalX2ApicTable 1 }

CfprApBiosVfLocalX2ApicEntry ::= SEQUENCE {
    cfprApBiosVfLocalX2ApicInstanceId                                CfprApManagedObjectId,
    cfprApBiosVfLocalX2ApicDn                                        CfprApManagedObjectDn,
    cfprApBiosVfLocalX2ApicRn                                        SnmpAdminString,
    cfprApBiosVfLocalX2ApicVpLocalX2Apic                             CfprApBiosVfLocalX2ApicVpLocalX2Apic
}

cfprApBiosVfLocalX2ApicInstanceId OBJECT-TYPE
    SYNTAX       CfprApManagedObjectId
    MAX-ACCESS   not-accessible
    STATUS       current
    DESCRIPTION
        "Instance identifier of the managed object."
    ::= { cfprApBiosVfLocalX2ApicEntry 1 }

cfprApBiosVfLocalX2ApicDn OBJECT-TYPE
    SYNTAX       CfprApManagedObjectDn
    MAX-ACCESS   read-only
    STATUS       current
    DESCRIPTION
        "Cisco Firepower bios:VfLocalX2Apic:dn managed object property"
    ::= { cfprApBiosVfLocalX2ApicEntry 2 }

cfprApBiosVfLocalX2ApicRn OBJECT-TYPE
    SYNTAX       SnmpAdminString
    MAX-ACCESS   read-only
    STATUS       current
    DESCRIPTION
        "Cisco Firepower bios:VfLocalX2Apic:rn managed object property"
    ::= { cfprApBiosVfLocalX2ApicEntry 3 }

cfprApBiosVfLocalX2ApicVpLocalX2Apic OBJECT-TYPE
    SYNTAX       CfprApBiosVfLocalX2ApicVpLocalX2Apic
    MAX-ACCESS   read-only
    STATUS       current
    DESCRIPTION
        "Cisco Firepower bios:VfLocalX2Apic:vpLocalX2Apic
        managed object property"
    ::= { cfprApBiosVfLocalX2ApicEntry 4 }

cfprApBiosVfLvDIMMSupportTable OBJECT-TYPE
    SYNTAX           SEQUENCE OF CfprApBiosVfLvDIMMSupportEntry
    MAX-ACCESS       not-accessible
    STATUS           current
    DESCRIPTION
        "Cisco Firepower bios:VfLvDIMMSupport managed object table"
    ::= { cfprApBiosObjects 36 }

cfprApBiosVfLvDIMMSupportEntry OBJECT-TYPE
    SYNTAX           CfprApBiosVfLvDIMMSupportEntry
    MAX-ACCESS       not-accessible
    STATUS           current
    DESCRIPTION
        "Entry for the cfprApBiosVfLvDIMMSupportTable table."
    INDEX { cfprApBiosVfLvDIMMSupportInstanceId }
    ::= { cfprApBiosVfLvDIMMSupportTable 1 }

CfprApBiosVfLvDIMMSupportEntry ::= SEQUENCE {
    cfprApBiosVfLvDIMMSupportInstanceId                              CfprApManagedObjectId,
    cfprApBiosVfLvDIMMSupportDn                                      CfprApManagedObjectDn,
    cfprApBiosVfLvDIMMSupportRn                                      SnmpAdminString,
    cfprApBiosVfLvDIMMSupportVpLvDDRMode                             CfprApBiosVfLvDIMMSupportVpLvDDRMode
}

cfprApBiosVfLvDIMMSupportInstanceId OBJECT-TYPE
    SYNTAX       CfprApManagedObjectId
    MAX-ACCESS   not-accessible
    STATUS       current
    DESCRIPTION
        "Instance identifier of the managed object."
    ::= { cfprApBiosVfLvDIMMSupportEntry 1 }

cfprApBiosVfLvDIMMSupportDn OBJECT-TYPE
    SYNTAX       CfprApManagedObjectDn
    MAX-ACCESS   read-only
    STATUS       current
    DESCRIPTION
        "Cisco Firepower bios:VfLvDIMMSupport:dn managed object property"
    ::= { cfprApBiosVfLvDIMMSupportEntry 2 }

cfprApBiosVfLvDIMMSupportRn OBJECT-TYPE
    SYNTAX       SnmpAdminString
    MAX-ACCESS   read-only
    STATUS       current
    DESCRIPTION
        "Cisco Firepower bios:VfLvDIMMSupport:rn managed object property"
    ::= { cfprApBiosVfLvDIMMSupportEntry 3 }

cfprApBiosVfLvDIMMSupportVpLvDDRMode OBJECT-TYPE
    SYNTAX       CfprApBiosVfLvDIMMSupportVpLvDDRMode
    MAX-ACCESS   read-only
    STATUS       current
    DESCRIPTION
        "Cisco Firepower bios:VfLvDIMMSupport:vpLvDDRMode
        managed object property"
    ::= { cfprApBiosVfLvDIMMSupportEntry 4 }

cfprApBiosVfMaxVariableMTRRSettingTable OBJECT-TYPE
    SYNTAX           SEQUENCE OF CfprApBiosVfMaxVariableMTRRSettingEntry
    MAX-ACCESS       not-accessible
    STATUS           current
    DESCRIPTION
        "Cisco Firepower bios:VfMaxVariableMTRRSetting
        managed object table"
    ::= { cfprApBiosObjects 37 }

cfprApBiosVfMaxVariableMTRRSettingEntry OBJECT-TYPE
    SYNTAX           CfprApBiosVfMaxVariableMTRRSettingEntry
    MAX-ACCESS       not-accessible
    STATUS           current
    DESCRIPTION
        "Entry for the cfprApBiosVfMaxVariableMTRRSettingTable table."
    INDEX { cfprApBiosVfMaxVariableMTRRSettingInstanceId }
    ::= { cfprApBiosVfMaxVariableMTRRSettingTable 1 }

CfprApBiosVfMaxVariableMTRRSettingEntry ::= SEQUENCE {
    cfprApBiosVfMaxVariableMTRRSettingInstanceId                     CfprApManagedObjectId,
    cfprApBiosVfMaxVariableMTRRSettingDn                             CfprApManagedObjectDn,
    cfprApBiosVfMaxVariableMTRRSettingRn                             SnmpAdminString,
    cfprApBiosVfMaxVariableMTRRSettingVpProcessorMtrr                CfprApBiosVfMaxVariableMTRRSettingVpProcessorMtrr
}

cfprApBiosVfMaxVariableMTRRSettingInstanceId OBJECT-TYPE
    SYNTAX       CfprApManagedObjectId
    MAX-ACCESS   not-accessible
    STATUS       current
    DESCRIPTION
        "Instance identifier of the managed object."
    ::= { cfprApBiosVfMaxVariableMTRRSettingEntry 1 }

cfprApBiosVfMaxVariableMTRRSettingDn OBJECT-TYPE
    SYNTAX       CfprApManagedObjectDn
    MAX-ACCESS   read-only
    STATUS       current
    DESCRIPTION
        "Cisco Firepower bios:VfMaxVariableMTRRSetting:dn
        managed object property"
    ::= { cfprApBiosVfMaxVariableMTRRSettingEntry 2 }

cfprApBiosVfMaxVariableMTRRSettingRn OBJECT-TYPE
    SYNTAX       SnmpAdminString
    MAX-ACCESS   read-only
    STATUS       current
    DESCRIPTION
        "Cisco Firepower bios:VfMaxVariableMTRRSetting:rn
        managed object property"
    ::= { cfprApBiosVfMaxVariableMTRRSettingEntry 3 }

cfprApBiosVfMaxVariableMTRRSettingVpProcessorMtrr OBJECT-TYPE
    SYNTAX       CfprApBiosVfMaxVariableMTRRSettingVpProcessorMtrr
    MAX-ACCESS   read-only
    STATUS       current
    DESCRIPTION
        "Cisco Firepower bios:VfMaxVariableMTRRSetting:vpProcessorMtrr
        managed object property"
    ::= { cfprApBiosVfMaxVariableMTRRSettingEntry 4 }

cfprApBiosVfMaximumMemoryBelow4GBTable OBJECT-TYPE
    SYNTAX           SEQUENCE OF CfprApBiosVfMaximumMemoryBelow4GBEntry
    MAX-ACCESS       not-accessible
    STATUS           current
    DESCRIPTION
        "Cisco Firepower bios:VfMaximumMemoryBelow4GB managed
        object table"
    ::= { cfprApBiosObjects 38 }

cfprApBiosVfMaximumMemoryBelow4GBEntry OBJECT-TYPE
    SYNTAX           CfprApBiosVfMaximumMemoryBelow4GBEntry
    MAX-ACCESS       not-accessible
    STATUS           current
    DESCRIPTION
        "Entry for the cfprApBiosVfMaximumMemoryBelow4GBTable table."
    INDEX { cfprApBiosVfMaximumMemoryBelow4GBInstanceId }
    ::= { cfprApBiosVfMaximumMemoryBelow4GBTable 1 }

CfprApBiosVfMaximumMemoryBelow4GBEntry ::= SEQUENCE {
    cfprApBiosVfMaximumMemoryBelow4GBInstanceId                      CfprApManagedObjectId,
    cfprApBiosVfMaximumMemoryBelow4GBDn                              CfprApManagedObjectDn,
    cfprApBiosVfMaximumMemoryBelow4GBRn                              SnmpAdminString,
    cfprApBiosVfMaximumMemoryBelow4GBVpMaximumMemoryBelow4GB         CfprApBiosVfMaximumMemoryBelow4GBVpMaximumMemoryBelow4GB
}

cfprApBiosVfMaximumMemoryBelow4GBInstanceId OBJECT-TYPE
    SYNTAX       CfprApManagedObjectId
    MAX-ACCESS   not-accessible
    STATUS       current
    DESCRIPTION
        "Instance identifier of the managed object."
    ::= { cfprApBiosVfMaximumMemoryBelow4GBEntry 1 }

cfprApBiosVfMaximumMemoryBelow4GBDn OBJECT-TYPE
    SYNTAX       CfprApManagedObjectDn
    MAX-ACCESS   read-only
    STATUS       current
    DESCRIPTION
        "Cisco Firepower bios:VfMaximumMemoryBelow4GB:dn
        managed object property"
    ::= { cfprApBiosVfMaximumMemoryBelow4GBEntry 2 }

cfprApBiosVfMaximumMemoryBelow4GBRn OBJECT-TYPE
    SYNTAX       SnmpAdminString
    MAX-ACCESS   read-only
    STATUS       current
    DESCRIPTION
        "Cisco Firepower bios:VfMaximumMemoryBelow4GB:rn
        managed object property"
    ::= { cfprApBiosVfMaximumMemoryBelow4GBEntry 3 }

cfprApBiosVfMaximumMemoryBelow4GBVpMaximumMemoryBelow4GB OBJECT-TYPE
    SYNTAX       CfprApBiosVfMaximumMemoryBelow4GBVpMaximumMemoryBelow4GB
    MAX-ACCESS   read-only
    STATUS       current
    DESCRIPTION
        "Cisco Firepower bios:VfMaximumMemoryBelow4GB:vpMaximumMemoryBelow
        4GB managed object property"
    ::= { cfprApBiosVfMaximumMemoryBelow4GBEntry 4 }

cfprApBiosVfMemoryMappedIOAbove4GBTable OBJECT-TYPE
    SYNTAX           SEQUENCE OF CfprApBiosVfMemoryMappedIOAbove4GBEntry
    MAX-ACCESS       not-accessible
    STATUS           current
    DESCRIPTION
        "Cisco Firepower bios:VfMemoryMappedIOAbove4GB
        managed object table"
    ::= { cfprApBiosObjects 39 }

cfprApBiosVfMemoryMappedIOAbove4GBEntry OBJECT-TYPE
    SYNTAX           CfprApBiosVfMemoryMappedIOAbove4GBEntry
    MAX-ACCESS       not-accessible
    STATUS           current
    DESCRIPTION
        "Entry for the cfprApBiosVfMemoryMappedIOAbove4GBTable table."
    INDEX { cfprApBiosVfMemoryMappedIOAbove4GBInstanceId }
    ::= { cfprApBiosVfMemoryMappedIOAbove4GBTable 1 }

CfprApBiosVfMemoryMappedIOAbove4GBEntry ::= SEQUENCE {
    cfprApBiosVfMemoryMappedIOAbove4GBInstanceId                     CfprApManagedObjectId,
    cfprApBiosVfMemoryMappedIOAbove4GBDn                             CfprApManagedObjectDn,
    cfprApBiosVfMemoryMappedIOAbove4GBRn                             SnmpAdminString,
    cfprApBiosVfMemoryMappedIOAbove4GBVpMemoryMappedIOAbove4GB       CfprApBiosVfMemoryMappedIOAbove4GBVpMemoryMappedIOAbove4GB
}

cfprApBiosVfMemoryMappedIOAbove4GBInstanceId OBJECT-TYPE
    SYNTAX       CfprApManagedObjectId
    MAX-ACCESS   not-accessible
    STATUS       current
    DESCRIPTION
        "Instance identifier of the managed object."
    ::= { cfprApBiosVfMemoryMappedIOAbove4GBEntry 1 }

cfprApBiosVfMemoryMappedIOAbove4GBDn OBJECT-TYPE
    SYNTAX       CfprApManagedObjectDn
    MAX-ACCESS   read-only
    STATUS       current
    DESCRIPTION
        "Cisco Firepower bios:VfMemoryMappedIOAbove4GB:dn
        managed object property"
    ::= { cfprApBiosVfMemoryMappedIOAbove4GBEntry 2 }

cfprApBiosVfMemoryMappedIOAbove4GBRn OBJECT-TYPE
    SYNTAX       SnmpAdminString
    MAX-ACCESS   read-only
    STATUS       current
    DESCRIPTION
        "Cisco Firepower bios:VfMemoryMappedIOAbove4GB:rn
        managed object property"
    ::= { cfprApBiosVfMemoryMappedIOAbove4GBEntry 3 }

cfprApBiosVfMemoryMappedIOAbove4GBVpMemoryMappedIOAbove4GB OBJECT-TYPE
    SYNTAX       CfprApBiosVfMemoryMappedIOAbove4GBVpMemoryMappedIOAbove4GB
    MAX-ACCESS   read-only
    STATUS       current
    DESCRIPTION
        "Cisco Firepower bios:VfMemoryMappedIOAbove4GB:vpMemoryMappedIOAbo
        ve4GB managed object property"
    ::= { cfprApBiosVfMemoryMappedIOAbove4GBEntry 4 }

cfprApBiosVfMirroringModeTable OBJECT-TYPE
    SYNTAX           SEQUENCE OF CfprApBiosVfMirroringModeEntry
    MAX-ACCESS       not-accessible
    STATUS           current
    DESCRIPTION
        "Cisco Firepower bios:VfMirroringMode managed object table"
    ::= { cfprApBiosObjects 40 }

cfprApBiosVfMirroringModeEntry OBJECT-TYPE
    SYNTAX           CfprApBiosVfMirroringModeEntry
    MAX-ACCESS       not-accessible
    STATUS           current
    DESCRIPTION
        "Entry for the cfprApBiosVfMirroringModeTable table."
    INDEX { cfprApBiosVfMirroringModeInstanceId }
    ::= { cfprApBiosVfMirroringModeTable 1 }

CfprApBiosVfMirroringModeEntry ::= SEQUENCE {
    cfprApBiosVfMirroringModeInstanceId                              CfprApManagedObjectId,
    cfprApBiosVfMirroringModeDn                                      CfprApManagedObjectDn,
    cfprApBiosVfMirroringModeRn                                      SnmpAdminString,
    cfprApBiosVfMirroringModeVpMirroringMode                         CfprApBiosVfMirroringModeVpMirroringMode
}

cfprApBiosVfMirroringModeInstanceId OBJECT-TYPE
    SYNTAX       CfprApManagedObjectId
    MAX-ACCESS   not-accessible
    STATUS       current
    DESCRIPTION
        "Instance identifier of the managed object."
    ::= { cfprApBiosVfMirroringModeEntry 1 }

cfprApBiosVfMirroringModeDn OBJECT-TYPE
    SYNTAX       CfprApManagedObjectDn
    MAX-ACCESS   read-only
    STATUS       current
    DESCRIPTION
        "Cisco Firepower bios:VfMirroringMode:dn managed object property"
    ::= { cfprApBiosVfMirroringModeEntry 2 }

cfprApBiosVfMirroringModeRn OBJECT-TYPE
    SYNTAX       SnmpAdminString
    MAX-ACCESS   read-only
    STATUS       current
    DESCRIPTION
        "Cisco Firepower bios:VfMirroringMode:rn managed object property"
    ::= { cfprApBiosVfMirroringModeEntry 3 }

cfprApBiosVfMirroringModeVpMirroringMode OBJECT-TYPE
    SYNTAX       CfprApBiosVfMirroringModeVpMirroringMode
    MAX-ACCESS   read-only
    STATUS       current
    DESCRIPTION
        "Cisco Firepower bios:VfMirroringMode:vpMirroringMode
        managed object property"
    ::= { cfprApBiosVfMirroringModeEntry 4 }

cfprApBiosVfNUMAOptimizedTable OBJECT-TYPE
    SYNTAX           SEQUENCE OF CfprApBiosVfNUMAOptimizedEntry
    MAX-ACCESS       not-accessible
    STATUS           current
    DESCRIPTION
        "Cisco Firepower bios:VfNUMAOptimized managed object table"
    ::= { cfprApBiosObjects 41 }

cfprApBiosVfNUMAOptimizedEntry OBJECT-TYPE
    SYNTAX           CfprApBiosVfNUMAOptimizedEntry
    MAX-ACCESS       not-accessible
    STATUS           current
    DESCRIPTION
        "Entry for the cfprApBiosVfNUMAOptimizedTable table."
    INDEX { cfprApBiosVfNUMAOptimizedInstanceId }
    ::= { cfprApBiosVfNUMAOptimizedTable 1 }

CfprApBiosVfNUMAOptimizedEntry ::= SEQUENCE {
    cfprApBiosVfNUMAOptimizedInstanceId                              CfprApManagedObjectId,
    cfprApBiosVfNUMAOptimizedDn                                      CfprApManagedObjectDn,
    cfprApBiosVfNUMAOptimizedRn                                      SnmpAdminString,
    cfprApBiosVfNUMAOptimizedVpNUMAOptimized                         CfprApBiosVfNUMAOptimizedVpNUMAOptimized
}

cfprApBiosVfNUMAOptimizedInstanceId OBJECT-TYPE
    SYNTAX       CfprApManagedObjectId
    MAX-ACCESS   not-accessible
    STATUS       current
    DESCRIPTION
        "Instance identifier of the managed object."
    ::= { cfprApBiosVfNUMAOptimizedEntry 1 }

cfprApBiosVfNUMAOptimizedDn OBJECT-TYPE
    SYNTAX       CfprApManagedObjectDn
    MAX-ACCESS   read-only
    STATUS       current
    DESCRIPTION
        "Cisco Firepower bios:VfNUMAOptimized:dn managed object property"
    ::= { cfprApBiosVfNUMAOptimizedEntry 2 }

cfprApBiosVfNUMAOptimizedRn OBJECT-TYPE
    SYNTAX       SnmpAdminString
    MAX-ACCESS   read-only
    STATUS       current
    DESCRIPTION
        "Cisco Firepower bios:VfNUMAOptimized:rn managed object property"
    ::= { cfprApBiosVfNUMAOptimizedEntry 3 }

cfprApBiosVfNUMAOptimizedVpNUMAOptimized OBJECT-TYPE
    SYNTAX       CfprApBiosVfNUMAOptimizedVpNUMAOptimized
    MAX-ACCESS   read-only
    STATUS       current
    DESCRIPTION
        "Cisco Firepower bios:VfNUMAOptimized:vpNUMAOptimized
        managed object property"
    ::= { cfprApBiosVfNUMAOptimizedEntry 4 }

cfprApBiosVfOSBootWatchdogTimerTable OBJECT-TYPE
    SYNTAX           SEQUENCE OF CfprApBiosVfOSBootWatchdogTimerEntry
    MAX-ACCESS       not-accessible
    STATUS           current
    DESCRIPTION
        "Cisco Firepower bios:VfOSBootWatchdogTimer managed object table"
    ::= { cfprApBiosObjects 42 }

cfprApBiosVfOSBootWatchdogTimerEntry OBJECT-TYPE
    SYNTAX           CfprApBiosVfOSBootWatchdogTimerEntry
    MAX-ACCESS       not-accessible
    STATUS           current
    DESCRIPTION
        "Entry for the cfprApBiosVfOSBootWatchdogTimerTable table."
    INDEX { cfprApBiosVfOSBootWatchdogTimerInstanceId }
    ::= { cfprApBiosVfOSBootWatchdogTimerTable 1 }

CfprApBiosVfOSBootWatchdogTimerEntry ::= SEQUENCE {
    cfprApBiosVfOSBootWatchdogTimerInstanceId                        CfprApManagedObjectId,
    cfprApBiosVfOSBootWatchdogTimerDn                                CfprApManagedObjectDn,
    cfprApBiosVfOSBootWatchdogTimerRn                                SnmpAdminString,
    cfprApBiosVfOSBootWatchdogTimerVpOSBootWatchdogTimer             CfprApBiosVfOSBootWatchdogTimerVpOSBootWatchdogTimer
}

cfprApBiosVfOSBootWatchdogTimerInstanceId OBJECT-TYPE
    SYNTAX       CfprApManagedObjectId
    MAX-ACCESS   not-accessible
    STATUS       current
    DESCRIPTION
        "Instance identifier of the managed object."
    ::= { cfprApBiosVfOSBootWatchdogTimerEntry 1 }

cfprApBiosVfOSBootWatchdogTimerDn OBJECT-TYPE
    SYNTAX       CfprApManagedObjectDn
    MAX-ACCESS   read-only
    STATUS       current
    DESCRIPTION
        "Cisco Firepower bios:VfOSBootWatchdogTimer:dn
        managed object property"
    ::= { cfprApBiosVfOSBootWatchdogTimerEntry 2 }

cfprApBiosVfOSBootWatchdogTimerRn OBJECT-TYPE
    SYNTAX       SnmpAdminString
    MAX-ACCESS   read-only
    STATUS       current
    DESCRIPTION
        "Cisco Firepower bios:VfOSBootWatchdogTimer:rn
        managed object property"
    ::= { cfprApBiosVfOSBootWatchdogTimerEntry 3 }

cfprApBiosVfOSBootWatchdogTimerVpOSBootWatchdogTimer OBJECT-TYPE
    SYNTAX       CfprApBiosVfOSBootWatchdogTimerVpOSBootWatchdogTimer
    MAX-ACCESS   read-only
    STATUS       current
    DESCRIPTION
        "Cisco Firepower bios:VfOSBootWatchdogTimer:vpOSBootWatchdogTimer
        managed object property"
    ::= { cfprApBiosVfOSBootWatchdogTimerEntry 4 }

cfprApBiosVfOSBootWatchdogTimerPolicyTable OBJECT-TYPE
    SYNTAX           SEQUENCE OF CfprApBiosVfOSBootWatchdogTimerPolicyEntry
    MAX-ACCESS       not-accessible
    STATUS           current
    DESCRIPTION
        "Cisco Firepower bios:VfOSBootWatchdogTimerPolicy
        managed object table"
    ::= { cfprApBiosObjects 43 }

cfprApBiosVfOSBootWatchdogTimerPolicyEntry OBJECT-TYPE
    SYNTAX           CfprApBiosVfOSBootWatchdogTimerPolicyEntry
    MAX-ACCESS       not-accessible
    STATUS           current
    DESCRIPTION
        "Entry for the cfprApBiosVfOSBootWatchdogTimerPolicyTable table."
    INDEX { cfprApBiosVfOSBootWatchdogTimerPolicyInstanceId }
    ::= { cfprApBiosVfOSBootWatchdogTimerPolicyTable 1 }

CfprApBiosVfOSBootWatchdogTimerPolicyEntry ::= SEQUENCE {
    cfprApBiosVfOSBootWatchdogTimerPolicyInstanceId                  CfprApManagedObjectId,
    cfprApBiosVfOSBootWatchdogTimerPolicyDn                          CfprApManagedObjectDn,
    cfprApBiosVfOSBootWatchdogTimerPolicyRn                          SnmpAdminString,
    cfprApBiosVfOSBootWatchdogTimerPolicyVpOSBootWatchdogTimerPolicy CfprApBiosVfOSBootWatchdogTimerPolicyVpOSBootWatchdogTimerPolicy
}

cfprApBiosVfOSBootWatchdogTimerPolicyInstanceId OBJECT-TYPE
    SYNTAX       CfprApManagedObjectId
    MAX-ACCESS   not-accessible
    STATUS       current
    DESCRIPTION
        "Instance identifier of the managed object."
    ::= { cfprApBiosVfOSBootWatchdogTimerPolicyEntry 1 }

cfprApBiosVfOSBootWatchdogTimerPolicyDn OBJECT-TYPE
    SYNTAX       CfprApManagedObjectDn
    MAX-ACCESS   read-only
    STATUS       current
    DESCRIPTION
        "Cisco Firepower bios:VfOSBootWatchdogTimerPolicy:dn
        managed object property"
    ::= { cfprApBiosVfOSBootWatchdogTimerPolicyEntry 2 }

cfprApBiosVfOSBootWatchdogTimerPolicyRn OBJECT-TYPE
    SYNTAX       SnmpAdminString
    MAX-ACCESS   read-only
    STATUS       current
    DESCRIPTION
        "Cisco Firepower bios:VfOSBootWatchdogTimerPolicy:rn
        managed object property"
    ::= { cfprApBiosVfOSBootWatchdogTimerPolicyEntry 3 }

cfprApBiosVfOSBootWatchdogTimerPolicyVpOSBootWatchdogTimerPolicy OBJECT-TYPE
    SYNTAX       CfprApBiosVfOSBootWatchdogTimerPolicyVpOSBootWatchdogTimerPolicy
    MAX-ACCESS   read-only
    STATUS       current
    DESCRIPTION
        "Cisco Firepower bios:VfOSBootWatchdogTimerPolicy:vpOSBootWatchdog
        TimerPolicy managed object property"
    ::= { cfprApBiosVfOSBootWatchdogTimerPolicyEntry 4 }

cfprApBiosVfOSBootWatchdogTimerTimeoutTable OBJECT-TYPE
    SYNTAX           SEQUENCE OF CfprApBiosVfOSBootWatchdogTimerTimeoutEntry
    MAX-ACCESS       not-accessible
    STATUS           current
    DESCRIPTION
        "Cisco Firepower bios:VfOSBootWatchdogTimerTimeout
        managed object table"
    ::= { cfprApBiosObjects 44 }

cfprApBiosVfOSBootWatchdogTimerTimeoutEntry OBJECT-TYPE
    SYNTAX           CfprApBiosVfOSBootWatchdogTimerTimeoutEntry
    MAX-ACCESS       not-accessible
    STATUS           current
    DESCRIPTION
        "Entry for the cfprApBiosVfOSBootWatchdogTimerTimeoutTable table."
    INDEX { cfprApBiosVfOSBootWatchdogTimerTimeoutInstanceId }
    ::= { cfprApBiosVfOSBootWatchdogTimerTimeoutTable 1 }

CfprApBiosVfOSBootWatchdogTimerTimeoutEntry ::= SEQUENCE {
    cfprApBiosVfOSBootWatchdogTimerTimeoutInstanceId                 CfprApManagedObjectId,
    cfprApBiosVfOSBootWatchdogTimerTimeoutDn                         CfprApManagedObjectDn,
    cfprApBiosVfOSBootWatchdogTimerTimeoutRn                         SnmpAdminString,
    cfprApBiosVfOSBootWatchdogTimerTimeoutVpOSBootWatchdogTimerTimeout CfprApBiosVfOSBootWatchdogTimerTimeoutVpOSBootWatchdogTimerTimeout
}

cfprApBiosVfOSBootWatchdogTimerTimeoutInstanceId OBJECT-TYPE
    SYNTAX       CfprApManagedObjectId
    MAX-ACCESS   not-accessible
    STATUS       current
    DESCRIPTION
        "Instance identifier of the managed object."
    ::= { cfprApBiosVfOSBootWatchdogTimerTimeoutEntry 1 }

cfprApBiosVfOSBootWatchdogTimerTimeoutDn OBJECT-TYPE
    SYNTAX       CfprApManagedObjectDn
    MAX-ACCESS   read-only
    STATUS       current
    DESCRIPTION
        "Cisco Firepower bios:VfOSBootWatchdogTimerTimeout:dn
        managed object property"
    ::= { cfprApBiosVfOSBootWatchdogTimerTimeoutEntry 2 }

cfprApBiosVfOSBootWatchdogTimerTimeoutRn OBJECT-TYPE
    SYNTAX       SnmpAdminString
    MAX-ACCESS   read-only
    STATUS       current
    DESCRIPTION
        "Cisco Firepower bios:VfOSBootWatchdogTimerTimeout:rn
        managed object property"
    ::= { cfprApBiosVfOSBootWatchdogTimerTimeoutEntry 3 }

cfprApBiosVfOSBootWatchdogTimerTimeoutVpOSBootWatchdogTimerTimeout OBJECT-TYPE
    SYNTAX       CfprApBiosVfOSBootWatchdogTimerTimeoutVpOSBootWatchdogTimerTimeout
    MAX-ACCESS   read-only
    STATUS       current
    DESCRIPTION
        "Cisco Firepower bios:VfOSBootWatchdogTimerTimeout:vpOSBootWatchdo
        gTimerTimeout managed object property"
    ::= { cfprApBiosVfOSBootWatchdogTimerTimeoutEntry 4 }

cfprApBiosVfOnboardSATAControllerTable OBJECT-TYPE
    SYNTAX           SEQUENCE OF CfprApBiosVfOnboardSATAControllerEntry
    MAX-ACCESS       not-accessible
    STATUS           current
    DESCRIPTION
        "Cisco Firepower bios:VfOnboardSATAController managed
        object table"
    ::= { cfprApBiosObjects 45 }

cfprApBiosVfOnboardSATAControllerEntry OBJECT-TYPE
    SYNTAX           CfprApBiosVfOnboardSATAControllerEntry
    MAX-ACCESS       not-accessible
    STATUS           current
    DESCRIPTION
        "Entry for the cfprApBiosVfOnboardSATAControllerTable table."
    INDEX { cfprApBiosVfOnboardSATAControllerInstanceId }
    ::= { cfprApBiosVfOnboardSATAControllerTable 1 }

CfprApBiosVfOnboardSATAControllerEntry ::= SEQUENCE {
    cfprApBiosVfOnboardSATAControllerInstanceId                      CfprApManagedObjectId,
    cfprApBiosVfOnboardSATAControllerDn                              CfprApManagedObjectDn,
    cfprApBiosVfOnboardSATAControllerRn                              SnmpAdminString,
    cfprApBiosVfOnboardSATAControllerVpOnboardSATAController         CfprApBiosVfOnboardSATAControllerVpOnboardSATAController,
    cfprApBiosVfOnboardSATAControllerVpSATAMode                      CfprApBiosVfOnboardSATAControllerVpSATAMode
}

cfprApBiosVfOnboardSATAControllerInstanceId OBJECT-TYPE
    SYNTAX       CfprApManagedObjectId
    MAX-ACCESS   not-accessible
    STATUS       current
    DESCRIPTION
        "Instance identifier of the managed object."
    ::= { cfprApBiosVfOnboardSATAControllerEntry 1 }

cfprApBiosVfOnboardSATAControllerDn OBJECT-TYPE
    SYNTAX       CfprApManagedObjectDn
    MAX-ACCESS   read-only
    STATUS       current
    DESCRIPTION
        "Cisco Firepower bios:VfOnboardSATAController:dn
        managed object property"
    ::= { cfprApBiosVfOnboardSATAControllerEntry 2 }

cfprApBiosVfOnboardSATAControllerRn OBJECT-TYPE
    SYNTAX       SnmpAdminString
    MAX-ACCESS   read-only
    STATUS       current
    DESCRIPTION
        "Cisco Firepower bios:VfOnboardSATAController:rn
        managed object property"
    ::= { cfprApBiosVfOnboardSATAControllerEntry 3 }

cfprApBiosVfOnboardSATAControllerVpOnboardSATAController OBJECT-TYPE
    SYNTAX       CfprApBiosVfOnboardSATAControllerVpOnboardSATAController
    MAX-ACCESS   read-only
    STATUS       current
    DESCRIPTION
        "Cisco Firepower bios:VfOnboardSATAController:vpOnboardSATAControl
        ler managed object property"
    ::= { cfprApBiosVfOnboardSATAControllerEntry 4 }

cfprApBiosVfOnboardSATAControllerVpSATAMode OBJECT-TYPE
    SYNTAX       CfprApBiosVfOnboardSATAControllerVpSATAMode
    MAX-ACCESS   read-only
    STATUS       current
    DESCRIPTION
        "Cisco Firepower bios:VfOnboardSATAController:vpSATAMode
        managed object property"
    ::= { cfprApBiosVfOnboardSATAControllerEntry 5 }

cfprApBiosVfOnboardStorageTable OBJECT-TYPE
    SYNTAX           SEQUENCE OF CfprApBiosVfOnboardStorageEntry
    MAX-ACCESS       not-accessible
    STATUS           current
    DESCRIPTION
        "Cisco Firepower bios:VfOnboardStorage managed object table"
    ::= { cfprApBiosObjects 46 }

cfprApBiosVfOnboardStorageEntry OBJECT-TYPE
    SYNTAX           CfprApBiosVfOnboardStorageEntry
    MAX-ACCESS       not-accessible
    STATUS           current
    DESCRIPTION
        "Entry for the cfprApBiosVfOnboardStorageTable table."
    INDEX { cfprApBiosVfOnboardStorageInstanceId }
    ::= { cfprApBiosVfOnboardStorageTable 1 }

CfprApBiosVfOnboardStorageEntry ::= SEQUENCE {
    cfprApBiosVfOnboardStorageInstanceId                             CfprApManagedObjectId,
    cfprApBiosVfOnboardStorageDn                                     CfprApManagedObjectDn,
    cfprApBiosVfOnboardStorageRn                                     SnmpAdminString,
    cfprApBiosVfOnboardStorageVpOnboardSCUStorageSupport             CfprApBiosVfOnboardStorageVpOnboardSCUStorageSupport
}

cfprApBiosVfOnboardStorageInstanceId OBJECT-TYPE
    SYNTAX       CfprApManagedObjectId
    MAX-ACCESS   not-accessible
    STATUS       current
    DESCRIPTION
        "Instance identifier of the managed object."
    ::= { cfprApBiosVfOnboardStorageEntry 1 }

cfprApBiosVfOnboardStorageDn OBJECT-TYPE
    SYNTAX       CfprApManagedObjectDn
    MAX-ACCESS   read-only
    STATUS       current
    DESCRIPTION
        "Cisco Firepower bios:VfOnboardStorage:dn managed object property"
    ::= { cfprApBiosVfOnboardStorageEntry 2 }

cfprApBiosVfOnboardStorageRn OBJECT-TYPE
    SYNTAX       SnmpAdminString
    MAX-ACCESS   read-only
    STATUS       current
    DESCRIPTION
        "Cisco Firepower bios:VfOnboardStorage:rn managed object property"
    ::= { cfprApBiosVfOnboardStorageEntry 3 }

cfprApBiosVfOnboardStorageVpOnboardSCUStorageSupport OBJECT-TYPE
    SYNTAX       CfprApBiosVfOnboardStorageVpOnboardSCUStorageSupport
    MAX-ACCESS   read-only
    STATUS       current
    DESCRIPTION
        "Cisco Firepower bios:VfOnboardStorage:vpOnboardSCUStorageSupport
        managed object property"
    ::= { cfprApBiosVfOnboardStorageEntry 4 }

cfprApBiosVfOptionROMEnableTable OBJECT-TYPE
    SYNTAX           SEQUENCE OF CfprApBiosVfOptionROMEnableEntry
    MAX-ACCESS       not-accessible
    STATUS           current
    DESCRIPTION
        "Cisco Firepower bios:VfOptionROMEnable managed object table"
    ::= { cfprApBiosObjects 47 }

cfprApBiosVfOptionROMEnableEntry OBJECT-TYPE
    SYNTAX           CfprApBiosVfOptionROMEnableEntry
    MAX-ACCESS       not-accessible
    STATUS           current
    DESCRIPTION
        "Entry for the cfprApBiosVfOptionROMEnableTable table."
    INDEX { cfprApBiosVfOptionROMEnableInstanceId }
    ::= { cfprApBiosVfOptionROMEnableTable 1 }

CfprApBiosVfOptionROMEnableEntry ::= SEQUENCE {
    cfprApBiosVfOptionROMEnableInstanceId                            CfprApManagedObjectId,
    cfprApBiosVfOptionROMEnableDn                                    CfprApManagedObjectDn,
    cfprApBiosVfOptionROMEnableRn                                    SnmpAdminString,
    cfprApBiosVfOptionROMEnableVpState                               CfprApBiosVfOptionROMEnableVpState
}

cfprApBiosVfOptionROMEnableInstanceId OBJECT-TYPE
    SYNTAX       CfprApManagedObjectId
    MAX-ACCESS   not-accessible
    STATUS       current
    DESCRIPTION
        "Instance identifier of the managed object."
    ::= { cfprApBiosVfOptionROMEnableEntry 1 }

cfprApBiosVfOptionROMEnableDn OBJECT-TYPE
    SYNTAX       CfprApManagedObjectDn
    MAX-ACCESS   read-only
    STATUS       current
    DESCRIPTION
        "Cisco Firepower bios:VfOptionROMEnable:dn managed
        object property"
    ::= { cfprApBiosVfOptionROMEnableEntry 2 }

cfprApBiosVfOptionROMEnableRn OBJECT-TYPE
    SYNTAX       SnmpAdminString
    MAX-ACCESS   read-only
    STATUS       current
    DESCRIPTION
        "Cisco Firepower bios:VfOptionROMEnable:rn managed
        object property"
    ::= { cfprApBiosVfOptionROMEnableEntry 3 }

cfprApBiosVfOptionROMEnableVpState OBJECT-TYPE
    SYNTAX       CfprApBiosVfOptionROMEnableVpState
    MAX-ACCESS   read-only
    STATUS       current
    DESCRIPTION
        "Cisco Firepower bios:VfOptionROMEnable:vpState
        managed object property"
    ::= { cfprApBiosVfOptionROMEnableEntry 4 }

cfprApBiosVfOptionROMLoadTable OBJECT-TYPE
    SYNTAX           SEQUENCE OF CfprApBiosVfOptionROMLoadEntry
    MAX-ACCESS       not-accessible
    STATUS           current
    DESCRIPTION
        "Cisco Firepower bios:VfOptionROMLoad managed object table"
    ::= { cfprApBiosObjects 48 }

cfprApBiosVfOptionROMLoadEntry OBJECT-TYPE
    SYNTAX           CfprApBiosVfOptionROMLoadEntry
    MAX-ACCESS       not-accessible
    STATUS           current
    DESCRIPTION
        "Entry for the cfprApBiosVfOptionROMLoadTable table."
    INDEX { cfprApBiosVfOptionROMLoadInstanceId }
    ::= { cfprApBiosVfOptionROMLoadTable 1 }

CfprApBiosVfOptionROMLoadEntry ::= SEQUENCE {
    cfprApBiosVfOptionROMLoadInstanceId                              CfprApManagedObjectId,
    cfprApBiosVfOptionROMLoadDn                                      CfprApManagedObjectDn,
    cfprApBiosVfOptionROMLoadRn                                      SnmpAdminString,
    cfprApBiosVfOptionROMLoadVpLoad                                  CfprApBiosVfOptionROMLoadVpLoad
}

cfprApBiosVfOptionROMLoadInstanceId OBJECT-TYPE
    SYNTAX       CfprApManagedObjectId
    MAX-ACCESS   not-accessible
    STATUS       current
    DESCRIPTION
        "Instance identifier of the managed object."
    ::= { cfprApBiosVfOptionROMLoadEntry 1 }

cfprApBiosVfOptionROMLoadDn OBJECT-TYPE
    SYNTAX       CfprApManagedObjectDn
    MAX-ACCESS   read-only
    STATUS       current
    DESCRIPTION
        "Cisco Firepower bios:VfOptionROMLoad:dn managed object property"
    ::= { cfprApBiosVfOptionROMLoadEntry 2 }

cfprApBiosVfOptionROMLoadRn OBJECT-TYPE
    SYNTAX       SnmpAdminString
    MAX-ACCESS   read-only
    STATUS       current
    DESCRIPTION
        "Cisco Firepower bios:VfOptionROMLoad:rn managed object property"
    ::= { cfprApBiosVfOptionROMLoadEntry 3 }

cfprApBiosVfOptionROMLoadVpLoad OBJECT-TYPE
    SYNTAX       CfprApBiosVfOptionROMLoadVpLoad
    MAX-ACCESS   read-only
    STATUS       current
    DESCRIPTION
        "Cisco Firepower bios:VfOptionROMLoad:vpLoad managed
        object property"
    ::= { cfprApBiosVfOptionROMLoadEntry 4 }

cfprApBiosVfPCISlotLinkSpeedTable OBJECT-TYPE
    SYNTAX           SEQUENCE OF CfprApBiosVfPCISlotLinkSpeedEntry
    MAX-ACCESS       not-accessible
    STATUS           current
    DESCRIPTION
        "Cisco Firepower bios:VfPCISlotLinkSpeed managed object table"
    ::= { cfprApBiosObjects 49 }

cfprApBiosVfPCISlotLinkSpeedEntry OBJECT-TYPE
    SYNTAX           CfprApBiosVfPCISlotLinkSpeedEntry
    MAX-ACCESS       not-accessible
    STATUS           current
    DESCRIPTION
        "Entry for the cfprApBiosVfPCISlotLinkSpeedTable table."
    INDEX { cfprApBiosVfPCISlotLinkSpeedInstanceId }
    ::= { cfprApBiosVfPCISlotLinkSpeedTable 1 }

CfprApBiosVfPCISlotLinkSpeedEntry ::= SEQUENCE {
    cfprApBiosVfPCISlotLinkSpeedInstanceId                           CfprApManagedObjectId,
    cfprApBiosVfPCISlotLinkSpeedDn                                   CfprApManagedObjectDn,
    cfprApBiosVfPCISlotLinkSpeedRn                                   SnmpAdminString,
    cfprApBiosVfPCISlotLinkSpeedVpPCIeSlot10LinkSpeed                CfprApBiosVfPCISlotLinkSpeedVpPCIeSlot10LinkSpeed,
    cfprApBiosVfPCISlotLinkSpeedVpPCIeSlot1LinkSpeed                 CfprApBiosVfPCISlotLinkSpeedVpPCIeSlot1LinkSpeed,
    cfprApBiosVfPCISlotLinkSpeedVpPCIeSlot2LinkSpeed                 CfprApBiosVfPCISlotLinkSpeedVpPCIeSlot2LinkSpeed,
    cfprApBiosVfPCISlotLinkSpeedVpPCIeSlot3LinkSpeed                 CfprApBiosVfPCISlotLinkSpeedVpPCIeSlot3LinkSpeed,
    cfprApBiosVfPCISlotLinkSpeedVpPCIeSlot4LinkSpeed                 CfprApBiosVfPCISlotLinkSpeedVpPCIeSlot4LinkSpeed,
    cfprApBiosVfPCISlotLinkSpeedVpPCIeSlot5LinkSpeed                 CfprApBiosVfPCISlotLinkSpeedVpPCIeSlot5LinkSpeed,
    cfprApBiosVfPCISlotLinkSpeedVpPCIeSlot6LinkSpeed                 CfprApBiosVfPCISlotLinkSpeedVpPCIeSlot6LinkSpeed,
    cfprApBiosVfPCISlotLinkSpeedVpPCIeSlot7LinkSpeed                 CfprApBiosVfPCISlotLinkSpeedVpPCIeSlot7LinkSpeed,
    cfprApBiosVfPCISlotLinkSpeedVpPCIeSlot8LinkSpeed                 CfprApBiosVfPCISlotLinkSpeedVpPCIeSlot8LinkSpeed,
    cfprApBiosVfPCISlotLinkSpeedVpPCIeSlot9LinkSpeed                 CfprApBiosVfPCISlotLinkSpeedVpPCIeSlot9LinkSpeed
}

cfprApBiosVfPCISlotLinkSpeedInstanceId OBJECT-TYPE
    SYNTAX       CfprApManagedObjectId
    MAX-ACCESS   not-accessible
    STATUS       current
    DESCRIPTION
        "Instance identifier of the managed object."
    ::= { cfprApBiosVfPCISlotLinkSpeedEntry 1 }

cfprApBiosVfPCISlotLinkSpeedDn OBJECT-TYPE
    SYNTAX       CfprApManagedObjectDn
    MAX-ACCESS   read-only
    STATUS       current
    DESCRIPTION
        "Cisco Firepower bios:VfPCISlotLinkSpeed:dn managed
        object property"
    ::= { cfprApBiosVfPCISlotLinkSpeedEntry 2 }

cfprApBiosVfPCISlotLinkSpeedRn OBJECT-TYPE
    SYNTAX       SnmpAdminString
    MAX-ACCESS   read-only
    STATUS       current
    DESCRIPTION
        "Cisco Firepower bios:VfPCISlotLinkSpeed:rn managed
        object property"
    ::= { cfprApBiosVfPCISlotLinkSpeedEntry 3 }

cfprApBiosVfPCISlotLinkSpeedVpPCIeSlot10LinkSpeed OBJECT-TYPE
    SYNTAX       CfprApBiosVfPCISlotLinkSpeedVpPCIeSlot10LinkSpeed
    MAX-ACCESS   read-only
    STATUS       current
    DESCRIPTION
        "Cisco Firepower bios:VfPCISlotLinkSpeed:vpPCIeSlot10LinkSpeed
        managed object property"
    ::= { cfprApBiosVfPCISlotLinkSpeedEntry 4 }

cfprApBiosVfPCISlotLinkSpeedVpPCIeSlot1LinkSpeed OBJECT-TYPE
    SYNTAX       CfprApBiosVfPCISlotLinkSpeedVpPCIeSlot1LinkSpeed
    MAX-ACCESS   read-only
    STATUS       current
    DESCRIPTION
        "Cisco Firepower bios:VfPCISlotLinkSpeed:vpPCIeSlot1LinkSpeed
        managed object property"
    ::= { cfprApBiosVfPCISlotLinkSpeedEntry 5 }

cfprApBiosVfPCISlotLinkSpeedVpPCIeSlot2LinkSpeed OBJECT-TYPE
    SYNTAX       CfprApBiosVfPCISlotLinkSpeedVpPCIeSlot2LinkSpeed
    MAX-ACCESS   read-only
    STATUS       current
    DESCRIPTION
        "Cisco Firepower bios:VfPCISlotLinkSpeed:vpPCIeSlot2LinkSpeed
        managed object property"
    ::= { cfprApBiosVfPCISlotLinkSpeedEntry 6 }

cfprApBiosVfPCISlotLinkSpeedVpPCIeSlot3LinkSpeed OBJECT-TYPE
    SYNTAX       CfprApBiosVfPCISlotLinkSpeedVpPCIeSlot3LinkSpeed
    MAX-ACCESS   read-only
    STATUS       current
    DESCRIPTION
        "Cisco Firepower bios:VfPCISlotLinkSpeed:vpPCIeSlot3LinkSpeed
        managed object property"
    ::= { cfprApBiosVfPCISlotLinkSpeedEntry 7 }

cfprApBiosVfPCISlotLinkSpeedVpPCIeSlot4LinkSpeed OBJECT-TYPE
    SYNTAX       CfprApBiosVfPCISlotLinkSpeedVpPCIeSlot4LinkSpeed
    MAX-ACCESS   read-only
    STATUS       current
    DESCRIPTION
        "Cisco Firepower bios:VfPCISlotLinkSpeed:vpPCIeSlot4LinkSpeed
        managed object property"
    ::= { cfprApBiosVfPCISlotLinkSpeedEntry 8 }

cfprApBiosVfPCISlotLinkSpeedVpPCIeSlot5LinkSpeed OBJECT-TYPE
    SYNTAX       CfprApBiosVfPCISlotLinkSpeedVpPCIeSlot5LinkSpeed
    MAX-ACCESS   read-only
    STATUS       current
    DESCRIPTION
        "Cisco Firepower bios:VfPCISlotLinkSpeed:vpPCIeSlot5LinkSpeed
        managed object property"
    ::= { cfprApBiosVfPCISlotLinkSpeedEntry 9 }

cfprApBiosVfPCISlotLinkSpeedVpPCIeSlot6LinkSpeed OBJECT-TYPE
    SYNTAX       CfprApBiosVfPCISlotLinkSpeedVpPCIeSlot6LinkSpeed
    MAX-ACCESS   read-only
    STATUS       current
    DESCRIPTION
        "Cisco Firepower bios:VfPCISlotLinkSpeed:vpPCIeSlot6LinkSpeed
        managed object property"
    ::= { cfprApBiosVfPCISlotLinkSpeedEntry 10 }

cfprApBiosVfPCISlotLinkSpeedVpPCIeSlot7LinkSpeed OBJECT-TYPE
    SYNTAX       CfprApBiosVfPCISlotLinkSpeedVpPCIeSlot7LinkSpeed
    MAX-ACCESS   read-only
    STATUS       current
    DESCRIPTION
        "Cisco Firepower bios:VfPCISlotLinkSpeed:vpPCIeSlot7LinkSpeed
        managed object property"
    ::= { cfprApBiosVfPCISlotLinkSpeedEntry 11 }

cfprApBiosVfPCISlotLinkSpeedVpPCIeSlot8LinkSpeed OBJECT-TYPE
    SYNTAX       CfprApBiosVfPCISlotLinkSpeedVpPCIeSlot8LinkSpeed
    MAX-ACCESS   read-only
    STATUS       current
    DESCRIPTION
        "Cisco Firepower bios:VfPCISlotLinkSpeed:vpPCIeSlot8LinkSpeed
        managed object property"
    ::= { cfprApBiosVfPCISlotLinkSpeedEntry 12 }

cfprApBiosVfPCISlotLinkSpeedVpPCIeSlot9LinkSpeed OBJECT-TYPE
    SYNTAX       CfprApBiosVfPCISlotLinkSpeedVpPCIeSlot9LinkSpeed
    MAX-ACCESS   read-only
    STATUS       current
    DESCRIPTION
        "Cisco Firepower bios:VfPCISlotLinkSpeed:vpPCIeSlot9LinkSpeed
        managed object property"
    ::= { cfprApBiosVfPCISlotLinkSpeedEntry 13 }

cfprApBiosVfPCISlotOptionROMEnableTable OBJECT-TYPE
    SYNTAX           SEQUENCE OF CfprApBiosVfPCISlotOptionROMEnableEntry
    MAX-ACCESS       not-accessible
    STATUS           current
    DESCRIPTION
        "Cisco Firepower bios:VfPCISlotOptionROMEnable
        managed object table"
    ::= { cfprApBiosObjects 50 }

cfprApBiosVfPCISlotOptionROMEnableEntry OBJECT-TYPE
    SYNTAX           CfprApBiosVfPCISlotOptionROMEnableEntry
    MAX-ACCESS       not-accessible
    STATUS           current
    DESCRIPTION
        "Entry for the cfprApBiosVfPCISlotOptionROMEnableTable table."
    INDEX { cfprApBiosVfPCISlotOptionROMEnableInstanceId }
    ::= { cfprApBiosVfPCISlotOptionROMEnableTable 1 }

CfprApBiosVfPCISlotOptionROMEnableEntry ::= SEQUENCE {
    cfprApBiosVfPCISlotOptionROMEnableInstanceId                     CfprApManagedObjectId,
    cfprApBiosVfPCISlotOptionROMEnableDn                             CfprApManagedObjectDn,
    cfprApBiosVfPCISlotOptionROMEnableRn                             SnmpAdminString,
    cfprApBiosVfPCISlotOptionROMEnableVpPCIeSlotHBAOptionROM         CfprApBiosVfPCISlotOptionROMEnableVpPCIeSlotHBAOptionROM,
    cfprApBiosVfPCISlotOptionROMEnableVpPCIeSlotMLOMOptionROM        CfprApBiosVfPCISlotOptionROMEnableVpPCIeSlotMLOMOptionROM,
    cfprApBiosVfPCISlotOptionROMEnableVpPCIeSlotN1OptionROM          CfprApBiosVfPCISlotOptionROMEnableVpPCIeSlotN1OptionROM,
    cfprApBiosVfPCISlotOptionROMEnableVpPCIeSlotN2OptionROM          CfprApBiosVfPCISlotOptionROMEnableVpPCIeSlotN2OptionROM,
    cfprApBiosVfPCISlotOptionROMEnableVpPCIeSlotSASOptionROM         CfprApBiosVfPCISlotOptionROMEnableVpPCIeSlotSASOptionROM,
    cfprApBiosVfPCISlotOptionROMEnableVpSlot10State                  CfprApBiosVfPCISlotOptionROMEnableVpSlot10State,
    cfprApBiosVfPCISlotOptionROMEnableVpSlot1State                   CfprApBiosVfPCISlotOptionROMEnableVpSlot1State,
    cfprApBiosVfPCISlotOptionROMEnableVpSlot2State                   CfprApBiosVfPCISlotOptionROMEnableVpSlot2State,
    cfprApBiosVfPCISlotOptionROMEnableVpSlot3State                   CfprApBiosVfPCISlotOptionROMEnableVpSlot3State,
    cfprApBiosVfPCISlotOptionROMEnableVpSlot4State                   CfprApBiosVfPCISlotOptionROMEnableVpSlot4State,
    cfprApBiosVfPCISlotOptionROMEnableVpSlot5State                   CfprApBiosVfPCISlotOptionROMEnableVpSlot5State,
    cfprApBiosVfPCISlotOptionROMEnableVpSlot6State                   CfprApBiosVfPCISlotOptionROMEnableVpSlot6State,
    cfprApBiosVfPCISlotOptionROMEnableVpSlot7State                   CfprApBiosVfPCISlotOptionROMEnableVpSlot7State,
    cfprApBiosVfPCISlotOptionROMEnableVpSlot8State                   CfprApBiosVfPCISlotOptionROMEnableVpSlot8State,
    cfprApBiosVfPCISlotOptionROMEnableVpSlot9State                   CfprApBiosVfPCISlotOptionROMEnableVpSlot9State,
    cfprApBiosVfPCISlotOptionROMEnableVpSlotMezzState                CfprApBiosVfPCISlotOptionROMEnableVpSlotMezzState
}

cfprApBiosVfPCISlotOptionROMEnableInstanceId OBJECT-TYPE
    SYNTAX       CfprApManagedObjectId
    MAX-ACCESS   not-accessible
    STATUS       current
    DESCRIPTION
        "Instance identifier of the managed object."
    ::= { cfprApBiosVfPCISlotOptionROMEnableEntry 1 }

cfprApBiosVfPCISlotOptionROMEnableDn OBJECT-TYPE
    SYNTAX       CfprApManagedObjectDn
    MAX-ACCESS   read-only
    STATUS       current
    DESCRIPTION
        "Cisco Firepower bios:VfPCISlotOptionROMEnable:dn
        managed object property"
    ::= { cfprApBiosVfPCISlotOptionROMEnableEntry 2 }

cfprApBiosVfPCISlotOptionROMEnableRn OBJECT-TYPE
    SYNTAX       SnmpAdminString
    MAX-ACCESS   read-only
    STATUS       current
    DESCRIPTION
        "Cisco Firepower bios:VfPCISlotOptionROMEnable:rn
        managed object property"
    ::= { cfprApBiosVfPCISlotOptionROMEnableEntry 3 }

cfprApBiosVfPCISlotOptionROMEnableVpPCIeSlotHBAOptionROM OBJECT-TYPE
    SYNTAX       CfprApBiosVfPCISlotOptionROMEnableVpPCIeSlotHBAOptionROM
    MAX-ACCESS   read-only
    STATUS       current
    DESCRIPTION
        "Cisco Firepower bios:VfPCISlotOptionROMEnable:vpPCIeSlotHBAOption
        ROM managed object property"
    ::= { cfprApBiosVfPCISlotOptionROMEnableEntry 4 }

cfprApBiosVfPCISlotOptionROMEnableVpPCIeSlotMLOMOptionROM OBJECT-TYPE
    SYNTAX       CfprApBiosVfPCISlotOptionROMEnableVpPCIeSlotMLOMOptionROM
    MAX-ACCESS   read-only
    STATUS       current
    DESCRIPTION
        "Cisco Firepower bios:VfPCISlotOptionROMEnable:vpPCIeSlotMLOMOptio
        nROM managed object property"
    ::= { cfprApBiosVfPCISlotOptionROMEnableEntry 5 }

cfprApBiosVfPCISlotOptionROMEnableVpPCIeSlotN1OptionROM OBJECT-TYPE
    SYNTAX       CfprApBiosVfPCISlotOptionROMEnableVpPCIeSlotN1OptionROM
    MAX-ACCESS   read-only
    STATUS       current
    DESCRIPTION
        "Cisco Firepower bios:VfPCISlotOptionROMEnable:vpPCIeSlotN1OptionR
        OM managed object property"
    ::= { cfprApBiosVfPCISlotOptionROMEnableEntry 6 }

cfprApBiosVfPCISlotOptionROMEnableVpPCIeSlotN2OptionROM OBJECT-TYPE
    SYNTAX       CfprApBiosVfPCISlotOptionROMEnableVpPCIeSlotN2OptionROM
    MAX-ACCESS   read-only
    STATUS       current
    DESCRIPTION
        "Cisco Firepower bios:VfPCISlotOptionROMEnable:vpPCIeSlotN2OptionR
        OM managed object property"
    ::= { cfprApBiosVfPCISlotOptionROMEnableEntry 7 }

cfprApBiosVfPCISlotOptionROMEnableVpPCIeSlotSASOptionROM OBJECT-TYPE
    SYNTAX       CfprApBiosVfPCISlotOptionROMEnableVpPCIeSlotSASOptionROM
    MAX-ACCESS   read-only
    STATUS       current
    DESCRIPTION
        "Cisco Firepower bios:VfPCISlotOptionROMEnable:vpPCIeSlotSASOption
        ROM managed object property"
    ::= { cfprApBiosVfPCISlotOptionROMEnableEntry 8 }

cfprApBiosVfPCISlotOptionROMEnableVpSlot10State OBJECT-TYPE
    SYNTAX       CfprApBiosVfPCISlotOptionROMEnableVpSlot10State
    MAX-ACCESS   read-only
    STATUS       current
    DESCRIPTION
        "Cisco Firepower bios:VfPCISlotOptionROMEnable:vpSlot10State
        managed object property"
    ::= { cfprApBiosVfPCISlotOptionROMEnableEntry 9 }

cfprApBiosVfPCISlotOptionROMEnableVpSlot1State OBJECT-TYPE
    SYNTAX       CfprApBiosVfPCISlotOptionROMEnableVpSlot1State
    MAX-ACCESS   read-only
    STATUS       current
    DESCRIPTION
        "Cisco Firepower bios:VfPCISlotOptionROMEnable:vpSlot1State
        managed object property"
    ::= { cfprApBiosVfPCISlotOptionROMEnableEntry 10 }

cfprApBiosVfPCISlotOptionROMEnableVpSlot2State OBJECT-TYPE
    SYNTAX       CfprApBiosVfPCISlotOptionROMEnableVpSlot2State
    MAX-ACCESS   read-only
    STATUS       current
    DESCRIPTION
        "Cisco Firepower bios:VfPCISlotOptionROMEnable:vpSlot2State
        managed object property"
    ::= { cfprApBiosVfPCISlotOptionROMEnableEntry 11 }

cfprApBiosVfPCISlotOptionROMEnableVpSlot3State OBJECT-TYPE
    SYNTAX       CfprApBiosVfPCISlotOptionROMEnableVpSlot3State
    MAX-ACCESS   read-only
    STATUS       current
    DESCRIPTION
        "Cisco Firepower bios:VfPCISlotOptionROMEnable:vpSlot3State
        managed object property"
    ::= { cfprApBiosVfPCISlotOptionROMEnableEntry 12 }

cfprApBiosVfPCISlotOptionROMEnableVpSlot4State OBJECT-TYPE
    SYNTAX       CfprApBiosVfPCISlotOptionROMEnableVpSlot4State
    MAX-ACCESS   read-only
    STATUS       current
    DESCRIPTION
        "Cisco Firepower bios:VfPCISlotOptionROMEnable:vpSlot4State
        managed object property"
    ::= { cfprApBiosVfPCISlotOptionROMEnableEntry 13 }

cfprApBiosVfPCISlotOptionROMEnableVpSlot5State OBJECT-TYPE
    SYNTAX       CfprApBiosVfPCISlotOptionROMEnableVpSlot5State
    MAX-ACCESS   read-only
    STATUS       current
    DESCRIPTION
        "Cisco Firepower bios:VfPCISlotOptionROMEnable:vpSlot5State
        managed object property"
    ::= { cfprApBiosVfPCISlotOptionROMEnableEntry 14 }

cfprApBiosVfPCISlotOptionROMEnableVpSlot6State OBJECT-TYPE
    SYNTAX       CfprApBiosVfPCISlotOptionROMEnableVpSlot6State
    MAX-ACCESS   read-only
    STATUS       current
    DESCRIPTION
        "Cisco Firepower bios:VfPCISlotOptionROMEnable:vpSlot6State
        managed object property"
    ::= { cfprApBiosVfPCISlotOptionROMEnableEntry 15 }

cfprApBiosVfPCISlotOptionROMEnableVpSlot7State OBJECT-TYPE
    SYNTAX       CfprApBiosVfPCISlotOptionROMEnableVpSlot7State
    MAX-ACCESS   read-only
    STATUS       current
    DESCRIPTION
        "Cisco Firepower bios:VfPCISlotOptionROMEnable:vpSlot7State
        managed object property"
    ::= { cfprApBiosVfPCISlotOptionROMEnableEntry 16 }

cfprApBiosVfPCISlotOptionROMEnableVpSlot8State OBJECT-TYPE
    SYNTAX       CfprApBiosVfPCISlotOptionROMEnableVpSlot8State
    MAX-ACCESS   read-only
    STATUS       current
    DESCRIPTION
        "Cisco Firepower bios:VfPCISlotOptionROMEnable:vpSlot8State
        managed object property"
    ::= { cfprApBiosVfPCISlotOptionROMEnableEntry 17 }

cfprApBiosVfPCISlotOptionROMEnableVpSlot9State OBJECT-TYPE
    SYNTAX       CfprApBiosVfPCISlotOptionROMEnableVpSlot9State
    MAX-ACCESS   read-only
    STATUS       current
    DESCRIPTION
        "Cisco Firepower bios:VfPCISlotOptionROMEnable:vpSlot9State
        managed object property"
    ::= { cfprApBiosVfPCISlotOptionROMEnableEntry 18 }

cfprApBiosVfPCISlotOptionROMEnableVpSlotMezzState OBJECT-TYPE
    SYNTAX       CfprApBiosVfPCISlotOptionROMEnableVpSlotMezzState
    MAX-ACCESS   read-only
    STATUS       current
    DESCRIPTION
        "Cisco Firepower bios:VfPCISlotOptionROMEnable:vpSlotMezzState
        managed object property"
    ::= { cfprApBiosVfPCISlotOptionROMEnableEntry 19 }

cfprApBiosVfPOSTErrorPauseTable OBJECT-TYPE
    SYNTAX           SEQUENCE OF CfprApBiosVfPOSTErrorPauseEntry
    MAX-ACCESS       not-accessible
    STATUS           current
    DESCRIPTION
        "Cisco Firepower bios:VfPOSTErrorPause managed object table"
    ::= { cfprApBiosObjects 51 }

cfprApBiosVfPOSTErrorPauseEntry OBJECT-TYPE
    SYNTAX           CfprApBiosVfPOSTErrorPauseEntry
    MAX-ACCESS       not-accessible
    STATUS           current
    DESCRIPTION
        "Entry for the cfprApBiosVfPOSTErrorPauseTable table."
    INDEX { cfprApBiosVfPOSTErrorPauseInstanceId }
    ::= { cfprApBiosVfPOSTErrorPauseTable 1 }

CfprApBiosVfPOSTErrorPauseEntry ::= SEQUENCE {
    cfprApBiosVfPOSTErrorPauseInstanceId                             CfprApManagedObjectId,
    cfprApBiosVfPOSTErrorPauseDn                                     CfprApManagedObjectDn,
    cfprApBiosVfPOSTErrorPauseRn                                     SnmpAdminString,
    cfprApBiosVfPOSTErrorPauseVpPOSTErrorPause                       CfprApBiosVfPOSTErrorPauseVpPOSTErrorPause
}

cfprApBiosVfPOSTErrorPauseInstanceId OBJECT-TYPE
    SYNTAX       CfprApManagedObjectId
    MAX-ACCESS   not-accessible
    STATUS       current
    DESCRIPTION
        "Instance identifier of the managed object."
    ::= { cfprApBiosVfPOSTErrorPauseEntry 1 }

cfprApBiosVfPOSTErrorPauseDn OBJECT-TYPE
    SYNTAX       CfprApManagedObjectDn
    MAX-ACCESS   read-only
    STATUS       current
    DESCRIPTION
        "Cisco Firepower bios:VfPOSTErrorPause:dn managed object property"
    ::= { cfprApBiosVfPOSTErrorPauseEntry 2 }

cfprApBiosVfPOSTErrorPauseRn OBJECT-TYPE
    SYNTAX       SnmpAdminString
    MAX-ACCESS   read-only
    STATUS       current
    DESCRIPTION
        "Cisco Firepower bios:VfPOSTErrorPause:rn managed object property"
    ::= { cfprApBiosVfPOSTErrorPauseEntry 3 }

cfprApBiosVfPOSTErrorPauseVpPOSTErrorPause OBJECT-TYPE
    SYNTAX       CfprApBiosVfPOSTErrorPauseVpPOSTErrorPause
    MAX-ACCESS   read-only
    STATUS       current
    DESCRIPTION
        "Cisco Firepower bios:VfPOSTErrorPause:vpPOSTErrorPause
        managed object property"
    ::= { cfprApBiosVfPOSTErrorPauseEntry 4 }

cfprApBiosVfPSTATECoordinationTable OBJECT-TYPE
    SYNTAX           SEQUENCE OF CfprApBiosVfPSTATECoordinationEntry
    MAX-ACCESS       not-accessible
    STATUS           current
    DESCRIPTION
        "Cisco Firepower bios:VfPSTATECoordination managed object table"
    ::= { cfprApBiosObjects 52 }

cfprApBiosVfPSTATECoordinationEntry OBJECT-TYPE
    SYNTAX           CfprApBiosVfPSTATECoordinationEntry
    MAX-ACCESS       not-accessible
    STATUS           current
    DESCRIPTION
        "Entry for the cfprApBiosVfPSTATECoordinationTable table."
    INDEX { cfprApBiosVfPSTATECoordinationInstanceId }
    ::= { cfprApBiosVfPSTATECoordinationTable 1 }

CfprApBiosVfPSTATECoordinationEntry ::= SEQUENCE {
    cfprApBiosVfPSTATECoordinationInstanceId                         CfprApManagedObjectId,
    cfprApBiosVfPSTATECoordinationDn                                 CfprApManagedObjectDn,
    cfprApBiosVfPSTATECoordinationRn                                 SnmpAdminString,
    cfprApBiosVfPSTATECoordinationVpPSTATECoordination               CfprApBiosVfPSTATECoordinationVpPSTATECoordination
}

cfprApBiosVfPSTATECoordinationInstanceId OBJECT-TYPE
    SYNTAX       CfprApManagedObjectId
    MAX-ACCESS   not-accessible
    STATUS       current
    DESCRIPTION
        "Instance identifier of the managed object."
    ::= { cfprApBiosVfPSTATECoordinationEntry 1 }

cfprApBiosVfPSTATECoordinationDn OBJECT-TYPE
    SYNTAX       CfprApManagedObjectDn
    MAX-ACCESS   read-only
    STATUS       current
    DESCRIPTION
        "Cisco Firepower bios:VfPSTATECoordination:dn managed
        object property"
    ::= { cfprApBiosVfPSTATECoordinationEntry 2 }

cfprApBiosVfPSTATECoordinationRn OBJECT-TYPE
    SYNTAX       SnmpAdminString
    MAX-ACCESS   read-only
    STATUS       current
    DESCRIPTION
        "Cisco Firepower bios:VfPSTATECoordination:rn managed
        object property"
    ::= { cfprApBiosVfPSTATECoordinationEntry 3 }

cfprApBiosVfPSTATECoordinationVpPSTATECoordination OBJECT-TYPE
    SYNTAX       CfprApBiosVfPSTATECoordinationVpPSTATECoordination
    MAX-ACCESS   read-only
    STATUS       current
    DESCRIPTION
        "Cisco Firepower bios:VfPSTATECoordination:vpPSTATECoordination
        managed object property"
    ::= { cfprApBiosVfPSTATECoordinationEntry 4 }

cfprApBiosVfPackageCStateLimitTable OBJECT-TYPE
    SYNTAX           SEQUENCE OF CfprApBiosVfPackageCStateLimitEntry
    MAX-ACCESS       not-accessible
    STATUS           current
    DESCRIPTION
        "Cisco Firepower bios:VfPackageCStateLimit managed object table"
    ::= { cfprApBiosObjects 53 }

cfprApBiosVfPackageCStateLimitEntry OBJECT-TYPE
    SYNTAX           CfprApBiosVfPackageCStateLimitEntry
    MAX-ACCESS       not-accessible
    STATUS           current
    DESCRIPTION
        "Entry for the cfprApBiosVfPackageCStateLimitTable table."
    INDEX { cfprApBiosVfPackageCStateLimitInstanceId }
    ::= { cfprApBiosVfPackageCStateLimitTable 1 }

CfprApBiosVfPackageCStateLimitEntry ::= SEQUENCE {
    cfprApBiosVfPackageCStateLimitInstanceId                         CfprApManagedObjectId,
    cfprApBiosVfPackageCStateLimitDn                                 CfprApManagedObjectDn,
    cfprApBiosVfPackageCStateLimitRn                                 SnmpAdminString,
    cfprApBiosVfPackageCStateLimitVpPackageCStateLimit               CfprApBiosVfPackageCStateLimitVpPackageCStateLimit
}

cfprApBiosVfPackageCStateLimitInstanceId OBJECT-TYPE
    SYNTAX       CfprApManagedObjectId
    MAX-ACCESS   not-accessible
    STATUS       current
    DESCRIPTION
        "Instance identifier of the managed object."
    ::= { cfprApBiosVfPackageCStateLimitEntry 1 }

cfprApBiosVfPackageCStateLimitDn OBJECT-TYPE
    SYNTAX       CfprApManagedObjectDn
    MAX-ACCESS   read-only
    STATUS       current
    DESCRIPTION
        "Cisco Firepower bios:VfPackageCStateLimit:dn managed
        object property"
    ::= { cfprApBiosVfPackageCStateLimitEntry 2 }

cfprApBiosVfPackageCStateLimitRn OBJECT-TYPE
    SYNTAX       SnmpAdminString
    MAX-ACCESS   read-only
    STATUS       current
    DESCRIPTION
        "Cisco Firepower bios:VfPackageCStateLimit:rn managed
        object property"
    ::= { cfprApBiosVfPackageCStateLimitEntry 3 }

cfprApBiosVfPackageCStateLimitVpPackageCStateLimit OBJECT-TYPE
    SYNTAX       CfprApBiosVfPackageCStateLimitVpPackageCStateLimit
    MAX-ACCESS   read-only
    STATUS       current
    DESCRIPTION
        "Cisco Firepower bios:VfPackageCStateLimit:vpPackageCStateLimit
        managed object property"
    ::= { cfprApBiosVfPackageCStateLimitEntry 4 }

cfprApBiosVfProcessorC1ETable OBJECT-TYPE
    SYNTAX           SEQUENCE OF CfprApBiosVfProcessorC1EEntry
    MAX-ACCESS       not-accessible
    STATUS           current
    DESCRIPTION
        "Cisco Firepower bios:VfProcessorC1E managed object table"
    ::= { cfprApBiosObjects 54 }

cfprApBiosVfProcessorC1EEntry OBJECT-TYPE
    SYNTAX           CfprApBiosVfProcessorC1EEntry
    MAX-ACCESS       not-accessible
    STATUS           current
    DESCRIPTION
        "Entry for the cfprApBiosVfProcessorC1ETable table."
    INDEX { cfprApBiosVfProcessorC1EInstanceId }
    ::= { cfprApBiosVfProcessorC1ETable 1 }

CfprApBiosVfProcessorC1EEntry ::= SEQUENCE {
    cfprApBiosVfProcessorC1EInstanceId                               CfprApManagedObjectId,
    cfprApBiosVfProcessorC1EDn                                       CfprApManagedObjectDn,
    cfprApBiosVfProcessorC1ERn                                       SnmpAdminString,
    cfprApBiosVfProcessorC1EVpProcessorC1E                           CfprApBiosVfProcessorC1EVpProcessorC1E
}

cfprApBiosVfProcessorC1EInstanceId OBJECT-TYPE
    SYNTAX       CfprApManagedObjectId
    MAX-ACCESS   not-accessible
    STATUS       current
    DESCRIPTION
        "Instance identifier of the managed object."
    ::= { cfprApBiosVfProcessorC1EEntry 1 }

cfprApBiosVfProcessorC1EDn OBJECT-TYPE
    SYNTAX       CfprApManagedObjectDn
    MAX-ACCESS   read-only
    STATUS       current
    DESCRIPTION
        "Cisco Firepower bios:VfProcessorC1E:dn managed object property"
    ::= { cfprApBiosVfProcessorC1EEntry 2 }

cfprApBiosVfProcessorC1ERn OBJECT-TYPE
    SYNTAX       SnmpAdminString
    MAX-ACCESS   read-only
    STATUS       current
    DESCRIPTION
        "Cisco Firepower bios:VfProcessorC1E:rn managed object property"
    ::= { cfprApBiosVfProcessorC1EEntry 3 }

cfprApBiosVfProcessorC1EVpProcessorC1E OBJECT-TYPE
    SYNTAX       CfprApBiosVfProcessorC1EVpProcessorC1E
    MAX-ACCESS   read-only
    STATUS       current
    DESCRIPTION
        "Cisco Firepower bios:VfProcessorC1E:vpProcessorC1E
        managed object property"
    ::= { cfprApBiosVfProcessorC1EEntry 4 }

cfprApBiosVfProcessorC3ReportTable OBJECT-TYPE
    SYNTAX           SEQUENCE OF CfprApBiosVfProcessorC3ReportEntry
    MAX-ACCESS       not-accessible
    STATUS           current
    DESCRIPTION
        "Cisco Firepower bios:VfProcessorC3Report managed object table"
    ::= { cfprApBiosObjects 55 }

cfprApBiosVfProcessorC3ReportEntry OBJECT-TYPE
    SYNTAX           CfprApBiosVfProcessorC3ReportEntry
    MAX-ACCESS       not-accessible
    STATUS           current
    DESCRIPTION
        "Entry for the cfprApBiosVfProcessorC3ReportTable table."
    INDEX { cfprApBiosVfProcessorC3ReportInstanceId }
    ::= { cfprApBiosVfProcessorC3ReportTable 1 }

CfprApBiosVfProcessorC3ReportEntry ::= SEQUENCE {
    cfprApBiosVfProcessorC3ReportInstanceId                          CfprApManagedObjectId,
    cfprApBiosVfProcessorC3ReportDn                                  CfprApManagedObjectDn,
    cfprApBiosVfProcessorC3ReportRn                                  SnmpAdminString,
    cfprApBiosVfProcessorC3ReportVpProcessorC3Report                 CfprApBiosVfProcessorC3ReportVpProcessorC3Report
}

cfprApBiosVfProcessorC3ReportInstanceId OBJECT-TYPE
    SYNTAX       CfprApManagedObjectId
    MAX-ACCESS   not-accessible
    STATUS       current
    DESCRIPTION
        "Instance identifier of the managed object."
    ::= { cfprApBiosVfProcessorC3ReportEntry 1 }

cfprApBiosVfProcessorC3ReportDn OBJECT-TYPE
    SYNTAX       CfprApManagedObjectDn
    MAX-ACCESS   read-only
    STATUS       current
    DESCRIPTION
        "Cisco Firepower bios:VfProcessorC3Report:dn managed
        object property"
    ::= { cfprApBiosVfProcessorC3ReportEntry 2 }

cfprApBiosVfProcessorC3ReportRn OBJECT-TYPE
    SYNTAX       SnmpAdminString
    MAX-ACCESS   read-only
    STATUS       current
    DESCRIPTION
        "Cisco Firepower bios:VfProcessorC3Report:rn managed
        object property"
    ::= { cfprApBiosVfProcessorC3ReportEntry 3 }

cfprApBiosVfProcessorC3ReportVpProcessorC3Report OBJECT-TYPE
    SYNTAX       CfprApBiosVfProcessorC3ReportVpProcessorC3Report
    MAX-ACCESS   read-only
    STATUS       current
    DESCRIPTION
        "Cisco Firepower bios:VfProcessorC3Report:vpProcessorC3Report
        managed object property"
    ::= { cfprApBiosVfProcessorC3ReportEntry 4 }

cfprApBiosVfProcessorC6ReportTable OBJECT-TYPE
    SYNTAX           SEQUENCE OF CfprApBiosVfProcessorC6ReportEntry
    MAX-ACCESS       not-accessible
    STATUS           current
    DESCRIPTION
        "Cisco Firepower bios:VfProcessorC6Report managed object table"
    ::= { cfprApBiosObjects 56 }

cfprApBiosVfProcessorC6ReportEntry OBJECT-TYPE
    SYNTAX           CfprApBiosVfProcessorC6ReportEntry
    MAX-ACCESS       not-accessible
    STATUS           current
    DESCRIPTION
        "Entry for the cfprApBiosVfProcessorC6ReportTable table."
    INDEX { cfprApBiosVfProcessorC6ReportInstanceId }
    ::= { cfprApBiosVfProcessorC6ReportTable 1 }

CfprApBiosVfProcessorC6ReportEntry ::= SEQUENCE {
    cfprApBiosVfProcessorC6ReportInstanceId                          CfprApManagedObjectId,
    cfprApBiosVfProcessorC6ReportDn                                  CfprApManagedObjectDn,
    cfprApBiosVfProcessorC6ReportRn                                  SnmpAdminString,
    cfprApBiosVfProcessorC6ReportVpProcessorC6Report                 CfprApBiosVfProcessorC6ReportVpProcessorC6Report
}

cfprApBiosVfProcessorC6ReportInstanceId OBJECT-TYPE
    SYNTAX       CfprApManagedObjectId
    MAX-ACCESS   not-accessible
    STATUS       current
    DESCRIPTION
        "Instance identifier of the managed object."
    ::= { cfprApBiosVfProcessorC6ReportEntry 1 }

cfprApBiosVfProcessorC6ReportDn OBJECT-TYPE
    SYNTAX       CfprApManagedObjectDn
    MAX-ACCESS   read-only
    STATUS       current
    DESCRIPTION
        "Cisco Firepower bios:VfProcessorC6Report:dn managed
        object property"
    ::= { cfprApBiosVfProcessorC6ReportEntry 2 }

cfprApBiosVfProcessorC6ReportRn OBJECT-TYPE
    SYNTAX       SnmpAdminString
    MAX-ACCESS   read-only
    STATUS       current
    DESCRIPTION
        "Cisco Firepower bios:VfProcessorC6Report:rn managed
        object property"
    ::= { cfprApBiosVfProcessorC6ReportEntry 3 }

cfprApBiosVfProcessorC6ReportVpProcessorC6Report OBJECT-TYPE
    SYNTAX       CfprApBiosVfProcessorC6ReportVpProcessorC6Report
    MAX-ACCESS   read-only
    STATUS       current
    DESCRIPTION
        "Cisco Firepower bios:VfProcessorC6Report:vpProcessorC6Report
        managed object property"
    ::= { cfprApBiosVfProcessorC6ReportEntry 4 }

cfprApBiosVfProcessorC7ReportTable OBJECT-TYPE
    SYNTAX           SEQUENCE OF CfprApBiosVfProcessorC7ReportEntry
    MAX-ACCESS       not-accessible
    STATUS           current
    DESCRIPTION
        "Cisco Firepower bios:VfProcessorC7Report managed object table"
    ::= { cfprApBiosObjects 57 }

cfprApBiosVfProcessorC7ReportEntry OBJECT-TYPE
    SYNTAX           CfprApBiosVfProcessorC7ReportEntry
    MAX-ACCESS       not-accessible
    STATUS           current
    DESCRIPTION
        "Entry for the cfprApBiosVfProcessorC7ReportTable table."
    INDEX { cfprApBiosVfProcessorC7ReportInstanceId }
    ::= { cfprApBiosVfProcessorC7ReportTable 1 }

CfprApBiosVfProcessorC7ReportEntry ::= SEQUENCE {
    cfprApBiosVfProcessorC7ReportInstanceId                          CfprApManagedObjectId,
    cfprApBiosVfProcessorC7ReportDn                                  CfprApManagedObjectDn,
    cfprApBiosVfProcessorC7ReportRn                                  SnmpAdminString,
    cfprApBiosVfProcessorC7ReportVpProcessorC7Report                 CfprApBiosVfProcessorC7ReportVpProcessorC7Report
}

cfprApBiosVfProcessorC7ReportInstanceId OBJECT-TYPE
    SYNTAX       CfprApManagedObjectId
    MAX-ACCESS   not-accessible
    STATUS       current
    DESCRIPTION
        "Instance identifier of the managed object."
    ::= { cfprApBiosVfProcessorC7ReportEntry 1 }

cfprApBiosVfProcessorC7ReportDn OBJECT-TYPE
    SYNTAX       CfprApManagedObjectDn
    MAX-ACCESS   read-only
    STATUS       current
    DESCRIPTION
        "Cisco Firepower bios:VfProcessorC7Report:dn managed
        object property"
    ::= { cfprApBiosVfProcessorC7ReportEntry 2 }

cfprApBiosVfProcessorC7ReportRn OBJECT-TYPE
    SYNTAX       SnmpAdminString
    MAX-ACCESS   read-only
    STATUS       current
    DESCRIPTION
        "Cisco Firepower bios:VfProcessorC7Report:rn managed
        object property"
    ::= { cfprApBiosVfProcessorC7ReportEntry 3 }

cfprApBiosVfProcessorC7ReportVpProcessorC7Report OBJECT-TYPE
    SYNTAX       CfprApBiosVfProcessorC7ReportVpProcessorC7Report
    MAX-ACCESS   read-only
    STATUS       current
    DESCRIPTION
        "Cisco Firepower bios:VfProcessorC7Report:vpProcessorC7Report
        managed object property"
    ::= { cfprApBiosVfProcessorC7ReportEntry 4 }

cfprApBiosVfProcessorCStateTable OBJECT-TYPE
    SYNTAX           SEQUENCE OF CfprApBiosVfProcessorCStateEntry
    MAX-ACCESS       not-accessible
    STATUS           current
    DESCRIPTION
        "Cisco Firepower bios:VfProcessorCState managed object table"
    ::= { cfprApBiosObjects 58 }

cfprApBiosVfProcessorCStateEntry OBJECT-TYPE
    SYNTAX           CfprApBiosVfProcessorCStateEntry
    MAX-ACCESS       not-accessible
    STATUS           current
    DESCRIPTION
        "Entry for the cfprApBiosVfProcessorCStateTable table."
    INDEX { cfprApBiosVfProcessorCStateInstanceId }
    ::= { cfprApBiosVfProcessorCStateTable 1 }

CfprApBiosVfProcessorCStateEntry ::= SEQUENCE {
    cfprApBiosVfProcessorCStateInstanceId                            CfprApManagedObjectId,
    cfprApBiosVfProcessorCStateDn                                    CfprApManagedObjectDn,
    cfprApBiosVfProcessorCStateRn                                    SnmpAdminString,
    cfprApBiosVfProcessorCStateVpProcessorCState                     CfprApBiosVfProcessorCStateVpProcessorCState
}

cfprApBiosVfProcessorCStateInstanceId OBJECT-TYPE
    SYNTAX       CfprApManagedObjectId
    MAX-ACCESS   not-accessible
    STATUS       current
    DESCRIPTION
        "Instance identifier of the managed object."
    ::= { cfprApBiosVfProcessorCStateEntry 1 }

cfprApBiosVfProcessorCStateDn OBJECT-TYPE
    SYNTAX       CfprApManagedObjectDn
    MAX-ACCESS   read-only
    STATUS       current
    DESCRIPTION
        "Cisco Firepower bios:VfProcessorCState:dn managed
        object property"
    ::= { cfprApBiosVfProcessorCStateEntry 2 }

cfprApBiosVfProcessorCStateRn OBJECT-TYPE
    SYNTAX       SnmpAdminString
    MAX-ACCESS   read-only
    STATUS       current
    DESCRIPTION
        "Cisco Firepower bios:VfProcessorCState:rn managed
        object property"
    ::= { cfprApBiosVfProcessorCStateEntry 3 }

cfprApBiosVfProcessorCStateVpProcessorCState OBJECT-TYPE
    SYNTAX       CfprApBiosVfProcessorCStateVpProcessorCState
    MAX-ACCESS   read-only
    STATUS       current
    DESCRIPTION
        "Cisco Firepower bios:VfProcessorCState:vpProcessorCState
        managed object property"
    ::= { cfprApBiosVfProcessorCStateEntry 4 }

cfprApBiosVfProcessorEnergyConfigurationTable OBJECT-TYPE
    SYNTAX           SEQUENCE OF CfprApBiosVfProcessorEnergyConfigurationEntry
    MAX-ACCESS       not-accessible
    STATUS           current
    DESCRIPTION
        "Cisco Firepower bios:VfProcessorEnergyConfiguration
        managed object table"
    ::= { cfprApBiosObjects 59 }

cfprApBiosVfProcessorEnergyConfigurationEntry OBJECT-TYPE
    SYNTAX           CfprApBiosVfProcessorEnergyConfigurationEntry
    MAX-ACCESS       not-accessible
    STATUS           current
    DESCRIPTION
        "Entry for the cfprApBiosVfProcessorEnergyConfigurationTable table."
    INDEX { cfprApBiosVfProcessorEnergyConfigurationInstanceId }
    ::= { cfprApBiosVfProcessorEnergyConfigurationTable 1 }

CfprApBiosVfProcessorEnergyConfigurationEntry ::= SEQUENCE {
    cfprApBiosVfProcessorEnergyConfigurationInstanceId               CfprApManagedObjectId,
    cfprApBiosVfProcessorEnergyConfigurationDn                       CfprApManagedObjectDn,
    cfprApBiosVfProcessorEnergyConfigurationRn                       SnmpAdminString,
    cfprApBiosVfProcessorEnergyConfigurationVpEnergyPerformance      CfprApBiosVfProcessorEnergyConfigurationVpEnergyPerformance,
    cfprApBiosVfProcessorEnergyConfigurationVpPowerTechnology        CfprApBiosVfProcessorEnergyConfigurationVpPowerTechnology
}

cfprApBiosVfProcessorEnergyConfigurationInstanceId OBJECT-TYPE
    SYNTAX       CfprApManagedObjectId
    MAX-ACCESS   not-accessible
    STATUS       current
    DESCRIPTION
        "Instance identifier of the managed object."
    ::= { cfprApBiosVfProcessorEnergyConfigurationEntry 1 }

cfprApBiosVfProcessorEnergyConfigurationDn OBJECT-TYPE
    SYNTAX       CfprApManagedObjectDn
    MAX-ACCESS   read-only
    STATUS       current
    DESCRIPTION
        "Cisco Firepower bios:VfProcessorEnergyConfiguration:dn
        managed object property"
    ::= { cfprApBiosVfProcessorEnergyConfigurationEntry 2 }

cfprApBiosVfProcessorEnergyConfigurationRn OBJECT-TYPE
    SYNTAX       SnmpAdminString
    MAX-ACCESS   read-only
    STATUS       current
    DESCRIPTION
        "Cisco Firepower bios:VfProcessorEnergyConfiguration:rn
        managed object property"
    ::= { cfprApBiosVfProcessorEnergyConfigurationEntry 3 }

cfprApBiosVfProcessorEnergyConfigurationVpEnergyPerformance OBJECT-TYPE
    SYNTAX       CfprApBiosVfProcessorEnergyConfigurationVpEnergyPerformance
    MAX-ACCESS   read-only
    STATUS       current
    DESCRIPTION
        "Cisco Firepower bios:VfProcessorEnergyConfiguration:vpEnergyPerfo
        rmance managed object property"
    ::= { cfprApBiosVfProcessorEnergyConfigurationEntry 4 }

cfprApBiosVfProcessorEnergyConfigurationVpPowerTechnology OBJECT-TYPE
    SYNTAX       CfprApBiosVfProcessorEnergyConfigurationVpPowerTechnology
    MAX-ACCESS   read-only
    STATUS       current
    DESCRIPTION
        "Cisco Firepower bios:VfProcessorEnergyConfiguration:vpPowerTechno
        logy managed object property"
    ::= { cfprApBiosVfProcessorEnergyConfigurationEntry 5 }

cfprApBiosVfProcessorPrefetchConfigTable OBJECT-TYPE
    SYNTAX           SEQUENCE OF CfprApBiosVfProcessorPrefetchConfigEntry
    MAX-ACCESS       not-accessible
    STATUS           current
    DESCRIPTION
        "Cisco Firepower bios:VfProcessorPrefetchConfig
        managed object table"
    ::= { cfprApBiosObjects 60 }

cfprApBiosVfProcessorPrefetchConfigEntry OBJECT-TYPE
    SYNTAX           CfprApBiosVfProcessorPrefetchConfigEntry
    MAX-ACCESS       not-accessible
    STATUS           current
    DESCRIPTION
        "Entry for the cfprApBiosVfProcessorPrefetchConfigTable table."
    INDEX { cfprApBiosVfProcessorPrefetchConfigInstanceId }
    ::= { cfprApBiosVfProcessorPrefetchConfigTable 1 }

CfprApBiosVfProcessorPrefetchConfigEntry ::= SEQUENCE {
    cfprApBiosVfProcessorPrefetchConfigInstanceId                    CfprApManagedObjectId,
    cfprApBiosVfProcessorPrefetchConfigDn                            CfprApManagedObjectDn,
    cfprApBiosVfProcessorPrefetchConfigRn                            SnmpAdminString,
    cfprApBiosVfProcessorPrefetchConfigVpAdjacentCacheLinePrefetcher CfprApBiosVfProcessorPrefetchConfigVpAdjacentCacheLinePrefetcher,
    cfprApBiosVfProcessorPrefetchConfigVpDCUIPPrefetcher             CfprApBiosVfProcessorPrefetchConfigVpDCUIPPrefetcher,
    cfprApBiosVfProcessorPrefetchConfigVpDCUStreamerPrefetch         CfprApBiosVfProcessorPrefetchConfigVpDCUStreamerPrefetch,
    cfprApBiosVfProcessorPrefetchConfigVpHardwarePrefetcher          CfprApBiosVfProcessorPrefetchConfigVpHardwarePrefetcher
}

cfprApBiosVfProcessorPrefetchConfigInstanceId OBJECT-TYPE
    SYNTAX       CfprApManagedObjectId
    MAX-ACCESS   not-accessible
    STATUS       current
    DESCRIPTION
        "Instance identifier of the managed object."
    ::= { cfprApBiosVfProcessorPrefetchConfigEntry 1 }

cfprApBiosVfProcessorPrefetchConfigDn OBJECT-TYPE
    SYNTAX       CfprApManagedObjectDn
    MAX-ACCESS   read-only
    STATUS       current
    DESCRIPTION
        "Cisco Firepower bios:VfProcessorPrefetchConfig:dn
        managed object property"
    ::= { cfprApBiosVfProcessorPrefetchConfigEntry 2 }

cfprApBiosVfProcessorPrefetchConfigRn OBJECT-TYPE
    SYNTAX       SnmpAdminString
    MAX-ACCESS   read-only
    STATUS       current
    DESCRIPTION
        "Cisco Firepower bios:VfProcessorPrefetchConfig:rn
        managed object property"
    ::= { cfprApBiosVfProcessorPrefetchConfigEntry 3 }

cfprApBiosVfProcessorPrefetchConfigVpAdjacentCacheLinePrefetcher OBJECT-TYPE
    SYNTAX       CfprApBiosVfProcessorPrefetchConfigVpAdjacentCacheLinePrefetcher
    MAX-ACCESS   read-only
    STATUS       current
    DESCRIPTION
        "Cisco Firepower bios:VfProcessorPrefetchConfig:vpAdjacentCacheLin
        ePrefetcher managed object property"
    ::= { cfprApBiosVfProcessorPrefetchConfigEntry 4 }

cfprApBiosVfProcessorPrefetchConfigVpDCUIPPrefetcher OBJECT-TYPE
    SYNTAX       CfprApBiosVfProcessorPrefetchConfigVpDCUIPPrefetcher
    MAX-ACCESS   read-only
    STATUS       current
    DESCRIPTION
        "Cisco Firepower bios:VfProcessorPrefetchConfig:vpDCUIPPrefetcher
        managed object property"
    ::= { cfprApBiosVfProcessorPrefetchConfigEntry 5 }

cfprApBiosVfProcessorPrefetchConfigVpDCUStreamerPrefetch OBJECT-TYPE
    SYNTAX       CfprApBiosVfProcessorPrefetchConfigVpDCUStreamerPrefetch
    MAX-ACCESS   read-only
    STATUS       current
    DESCRIPTION
        "Cisco Firepower bios:VfProcessorPrefetchConfig:vpDCUStreamerPrefe
        tch managed object property"
    ::= { cfprApBiosVfProcessorPrefetchConfigEntry 6 }

cfprApBiosVfProcessorPrefetchConfigVpHardwarePrefetcher OBJECT-TYPE
    SYNTAX       CfprApBiosVfProcessorPrefetchConfigVpHardwarePrefetcher
    MAX-ACCESS   read-only
    STATUS       current
    DESCRIPTION
        "Cisco Firepower bios:VfProcessorPrefetchConfig:vpHardwarePrefetch
        er managed object property"
    ::= { cfprApBiosVfProcessorPrefetchConfigEntry 7 }

cfprApBiosVfQPILinkFrequencySelectTable OBJECT-TYPE
    SYNTAX           SEQUENCE OF CfprApBiosVfQPILinkFrequencySelectEntry
    MAX-ACCESS       not-accessible
    STATUS           current
    DESCRIPTION
        "Cisco Firepower bios:VfQPILinkFrequencySelect
        managed object table"
    ::= { cfprApBiosObjects 61 }

cfprApBiosVfQPILinkFrequencySelectEntry OBJECT-TYPE
    SYNTAX           CfprApBiosVfQPILinkFrequencySelectEntry
    MAX-ACCESS       not-accessible
    STATUS           current
    DESCRIPTION
        "Entry for the cfprApBiosVfQPILinkFrequencySelectTable table."
    INDEX { cfprApBiosVfQPILinkFrequencySelectInstanceId }
    ::= { cfprApBiosVfQPILinkFrequencySelectTable 1 }

CfprApBiosVfQPILinkFrequencySelectEntry ::= SEQUENCE {
    cfprApBiosVfQPILinkFrequencySelectInstanceId                     CfprApManagedObjectId,
    cfprApBiosVfQPILinkFrequencySelectDn                             CfprApManagedObjectDn,
    cfprApBiosVfQPILinkFrequencySelectRn                             SnmpAdminString,
    cfprApBiosVfQPILinkFrequencySelectVpQPILinkFrequencySelect       CfprApBiosVfQPILinkFrequencySelectVpQPILinkFrequencySelect
}

cfprApBiosVfQPILinkFrequencySelectInstanceId OBJECT-TYPE
    SYNTAX       CfprApManagedObjectId
    MAX-ACCESS   not-accessible
    STATUS       current
    DESCRIPTION
        "Instance identifier of the managed object."
    ::= { cfprApBiosVfQPILinkFrequencySelectEntry 1 }

cfprApBiosVfQPILinkFrequencySelectDn OBJECT-TYPE
    SYNTAX       CfprApManagedObjectDn
    MAX-ACCESS   read-only
    STATUS       current
    DESCRIPTION
        "Cisco Firepower bios:VfQPILinkFrequencySelect:dn
        managed object property"
    ::= { cfprApBiosVfQPILinkFrequencySelectEntry 2 }

cfprApBiosVfQPILinkFrequencySelectRn OBJECT-TYPE
    SYNTAX       SnmpAdminString
    MAX-ACCESS   read-only
    STATUS       current
    DESCRIPTION
        "Cisco Firepower bios:VfQPILinkFrequencySelect:rn
        managed object property"
    ::= { cfprApBiosVfQPILinkFrequencySelectEntry 3 }

cfprApBiosVfQPILinkFrequencySelectVpQPILinkFrequencySelect OBJECT-TYPE
    SYNTAX       CfprApBiosVfQPILinkFrequencySelectVpQPILinkFrequencySelect
    MAX-ACCESS   read-only
    STATUS       current
    DESCRIPTION
        "Cisco Firepower bios:VfQPILinkFrequencySelect:vpQPILinkFrequencyS
        elect managed object property"
    ::= { cfprApBiosVfQPILinkFrequencySelectEntry 4 }

cfprApBiosVfQuietBootTable OBJECT-TYPE
    SYNTAX           SEQUENCE OF CfprApBiosVfQuietBootEntry
    MAX-ACCESS       not-accessible
    STATUS           current
    DESCRIPTION
        "Cisco Firepower bios:VfQuietBoot managed object table"
    ::= { cfprApBiosObjects 62 }

cfprApBiosVfQuietBootEntry OBJECT-TYPE
    SYNTAX           CfprApBiosVfQuietBootEntry
    MAX-ACCESS       not-accessible
    STATUS           current
    DESCRIPTION
        "Entry for the cfprApBiosVfQuietBootTable table."
    INDEX { cfprApBiosVfQuietBootInstanceId }
    ::= { cfprApBiosVfQuietBootTable 1 }

CfprApBiosVfQuietBootEntry ::= SEQUENCE {
    cfprApBiosVfQuietBootInstanceId                                  CfprApManagedObjectId,
    cfprApBiosVfQuietBootDn                                          CfprApManagedObjectDn,
    cfprApBiosVfQuietBootRn                                          SnmpAdminString,
    cfprApBiosVfQuietBootVpQuietBoot                                 CfprApBiosVfQuietBootVpQuietBoot
}

cfprApBiosVfQuietBootInstanceId OBJECT-TYPE
    SYNTAX       CfprApManagedObjectId
    MAX-ACCESS   not-accessible
    STATUS       current
    DESCRIPTION
        "Instance identifier of the managed object."
    ::= { cfprApBiosVfQuietBootEntry 1 }

cfprApBiosVfQuietBootDn OBJECT-TYPE
    SYNTAX       CfprApManagedObjectDn
    MAX-ACCESS   read-only
    STATUS       current
    DESCRIPTION
        "Cisco Firepower bios:VfQuietBoot:dn managed object property"
    ::= { cfprApBiosVfQuietBootEntry 2 }

cfprApBiosVfQuietBootRn OBJECT-TYPE
    SYNTAX       SnmpAdminString
    MAX-ACCESS   read-only
    STATUS       current
    DESCRIPTION
        "Cisco Firepower bios:VfQuietBoot:rn managed object property"
    ::= { cfprApBiosVfQuietBootEntry 3 }

cfprApBiosVfQuietBootVpQuietBoot OBJECT-TYPE
    SYNTAX       CfprApBiosVfQuietBootVpQuietBoot
    MAX-ACCESS   read-only
    STATUS       current
    DESCRIPTION
        "Cisco Firepower bios:VfQuietBoot:vpQuietBoot managed
        object property"
    ::= { cfprApBiosVfQuietBootEntry 4 }

cfprApBiosVfResumeOnACPowerLossTable OBJECT-TYPE
    SYNTAX           SEQUENCE OF CfprApBiosVfResumeOnACPowerLossEntry
    MAX-ACCESS       not-accessible
    STATUS           current
    DESCRIPTION
        "Cisco Firepower bios:VfResumeOnACPowerLoss managed object table"
    ::= { cfprApBiosObjects 63 }

cfprApBiosVfResumeOnACPowerLossEntry OBJECT-TYPE
    SYNTAX           CfprApBiosVfResumeOnACPowerLossEntry
    MAX-ACCESS       not-accessible
    STATUS           current
    DESCRIPTION
        "Entry for the cfprApBiosVfResumeOnACPowerLossTable table."
    INDEX { cfprApBiosVfResumeOnACPowerLossInstanceId }
    ::= { cfprApBiosVfResumeOnACPowerLossTable 1 }

CfprApBiosVfResumeOnACPowerLossEntry ::= SEQUENCE {
    cfprApBiosVfResumeOnACPowerLossInstanceId                        CfprApManagedObjectId,
    cfprApBiosVfResumeOnACPowerLossDn                                CfprApManagedObjectDn,
    cfprApBiosVfResumeOnACPowerLossRn                                SnmpAdminString,
    cfprApBiosVfResumeOnACPowerLossVpResumeOnACPowerLoss             CfprApBiosVfResumeOnACPowerLossVpResumeOnACPowerLoss
}

cfprApBiosVfResumeOnACPowerLossInstanceId OBJECT-TYPE
    SYNTAX       CfprApManagedObjectId
    MAX-ACCESS   not-accessible
    STATUS       current
    DESCRIPTION
        "Instance identifier of the managed object."
    ::= { cfprApBiosVfResumeOnACPowerLossEntry 1 }

cfprApBiosVfResumeOnACPowerLossDn OBJECT-TYPE
    SYNTAX       CfprApManagedObjectDn
    MAX-ACCESS   read-only
    STATUS       current
    DESCRIPTION
        "Cisco Firepower bios:VfResumeOnACPowerLoss:dn
        managed object property"
    ::= { cfprApBiosVfResumeOnACPowerLossEntry 2 }

cfprApBiosVfResumeOnACPowerLossRn OBJECT-TYPE
    SYNTAX       SnmpAdminString
    MAX-ACCESS   read-only
    STATUS       current
    DESCRIPTION
        "Cisco Firepower bios:VfResumeOnACPowerLoss:rn
        managed object property"
    ::= { cfprApBiosVfResumeOnACPowerLossEntry 3 }

cfprApBiosVfResumeOnACPowerLossVpResumeOnACPowerLoss OBJECT-TYPE
    SYNTAX       CfprApBiosVfResumeOnACPowerLossVpResumeOnACPowerLoss
    MAX-ACCESS   read-only
    STATUS       current
    DESCRIPTION
        "Cisco Firepower bios:VfResumeOnACPowerLoss:vpResumeOnACPowerLoss
        managed object property"
    ::= { cfprApBiosVfResumeOnACPowerLossEntry 4 }

cfprApBiosVfScrubPoliciesTable OBJECT-TYPE
    SYNTAX           SEQUENCE OF CfprApBiosVfScrubPoliciesEntry
    MAX-ACCESS       not-accessible
    STATUS           current
    DESCRIPTION
        "Cisco Firepower bios:VfScrubPolicies managed object table"
    ::= { cfprApBiosObjects 64 }

cfprApBiosVfScrubPoliciesEntry OBJECT-TYPE
    SYNTAX           CfprApBiosVfScrubPoliciesEntry
    MAX-ACCESS       not-accessible
    STATUS           current
    DESCRIPTION
        "Entry for the cfprApBiosVfScrubPoliciesTable table."
    INDEX { cfprApBiosVfScrubPoliciesInstanceId }
    ::= { cfprApBiosVfScrubPoliciesTable 1 }

CfprApBiosVfScrubPoliciesEntry ::= SEQUENCE {
    cfprApBiosVfScrubPoliciesInstanceId                              CfprApManagedObjectId,
    cfprApBiosVfScrubPoliciesDn                                      CfprApManagedObjectDn,
    cfprApBiosVfScrubPoliciesRn                                      SnmpAdminString,
    cfprApBiosVfScrubPoliciesVpDemandScrub                           CfprApBiosVfScrubPoliciesVpDemandScrub,
    cfprApBiosVfScrubPoliciesVpPatrolScrub                           CfprApBiosVfScrubPoliciesVpPatrolScrub
}

cfprApBiosVfScrubPoliciesInstanceId OBJECT-TYPE
    SYNTAX       CfprApManagedObjectId
    MAX-ACCESS   not-accessible
    STATUS       current
    DESCRIPTION
        "Instance identifier of the managed object."
    ::= { cfprApBiosVfScrubPoliciesEntry 1 }

cfprApBiosVfScrubPoliciesDn OBJECT-TYPE
    SYNTAX       CfprApManagedObjectDn
    MAX-ACCESS   read-only
    STATUS       current
    DESCRIPTION
        "Cisco Firepower bios:VfScrubPolicies:dn managed object property"
    ::= { cfprApBiosVfScrubPoliciesEntry 2 }

cfprApBiosVfScrubPoliciesRn OBJECT-TYPE
    SYNTAX       SnmpAdminString
    MAX-ACCESS   read-only
    STATUS       current
    DESCRIPTION
        "Cisco Firepower bios:VfScrubPolicies:rn managed object property"
    ::= { cfprApBiosVfScrubPoliciesEntry 3 }

cfprApBiosVfScrubPoliciesVpDemandScrub OBJECT-TYPE
    SYNTAX       CfprApBiosVfScrubPoliciesVpDemandScrub
    MAX-ACCESS   read-only
    STATUS       current
    DESCRIPTION
        "Cisco Firepower bios:VfScrubPolicies:vpDemandScrub
        managed object property"
    ::= { cfprApBiosVfScrubPoliciesEntry 4 }

cfprApBiosVfScrubPoliciesVpPatrolScrub OBJECT-TYPE
    SYNTAX       CfprApBiosVfScrubPoliciesVpPatrolScrub
    MAX-ACCESS   read-only
    STATUS       current
    DESCRIPTION
        "Cisco Firepower bios:VfScrubPolicies:vpPatrolScrub
        managed object property"
    ::= { cfprApBiosVfScrubPoliciesEntry 5 }

cfprApBiosVfSelectMemoryRASConfigurationTable OBJECT-TYPE
    SYNTAX           SEQUENCE OF CfprApBiosVfSelectMemoryRASConfigurationEntry
    MAX-ACCESS       not-accessible
    STATUS           current
    DESCRIPTION
        "Cisco Firepower bios:VfSelectMemoryRASConfiguration
        managed object table"
    ::= { cfprApBiosObjects 65 }

cfprApBiosVfSelectMemoryRASConfigurationEntry OBJECT-TYPE
    SYNTAX           CfprApBiosVfSelectMemoryRASConfigurationEntry
    MAX-ACCESS       not-accessible
    STATUS           current
    DESCRIPTION
        "Entry for the cfprApBiosVfSelectMemoryRASConfigurationTable table."
    INDEX { cfprApBiosVfSelectMemoryRASConfigurationInstanceId }
    ::= { cfprApBiosVfSelectMemoryRASConfigurationTable 1 }

CfprApBiosVfSelectMemoryRASConfigurationEntry ::= SEQUENCE {
    cfprApBiosVfSelectMemoryRASConfigurationInstanceId               CfprApManagedObjectId,
    cfprApBiosVfSelectMemoryRASConfigurationDn                       CfprApManagedObjectDn,
    cfprApBiosVfSelectMemoryRASConfigurationRn                       SnmpAdminString,
    cfprApBiosVfSelectMemoryRASConfigurationVpSelectMemoryRASConfiguration CfprApBiosVfSelectMemoryRASConfigurationVpSelectMemoryRASConf
}

cfprApBiosVfSelectMemoryRASConfigurationInstanceId OBJECT-TYPE
    SYNTAX       CfprApManagedObjectId
    MAX-ACCESS   not-accessible
    STATUS       current
    DESCRIPTION
        "Instance identifier of the managed object."
    ::= { cfprApBiosVfSelectMemoryRASConfigurationEntry 1 }

cfprApBiosVfSelectMemoryRASConfigurationDn OBJECT-TYPE
    SYNTAX       CfprApManagedObjectDn
    MAX-ACCESS   read-only
    STATUS       current
    DESCRIPTION
        "Cisco Firepower bios:VfSelectMemoryRASConfiguration:dn
        managed object property"
    ::= { cfprApBiosVfSelectMemoryRASConfigurationEntry 2 }

cfprApBiosVfSelectMemoryRASConfigurationRn OBJECT-TYPE
    SYNTAX       SnmpAdminString
    MAX-ACCESS   read-only
    STATUS       current
    DESCRIPTION
        "Cisco Firepower bios:VfSelectMemoryRASConfiguration:rn
        managed object property"
    ::= { cfprApBiosVfSelectMemoryRASConfigurationEntry 3 }

cfprApBiosVfSelectMemoryRASConfigurationVpSelectMemoryRASConfiguration OBJECT-TYPE
    SYNTAX       CfprApBiosVfSelectMemoryRASConfigurationVpSelectMemoryRASConf
    MAX-ACCESS   read-only
    STATUS       current
    DESCRIPTION
        "Cisco Firepower bios:VfSelectMemoryRASConfiguration:vpSelectMemor
        yRASConfiguration managed object property"
    ::= { cfprApBiosVfSelectMemoryRASConfigurationEntry 4 }

cfprApBiosVfSerialPortAEnableTable OBJECT-TYPE
    SYNTAX           SEQUENCE OF CfprApBiosVfSerialPortAEnableEntry
    MAX-ACCESS       not-accessible
    STATUS           current
    DESCRIPTION
        "Cisco Firepower bios:VfSerialPortAEnable managed object table"
    ::= { cfprApBiosObjects 66 }

cfprApBiosVfSerialPortAEnableEntry OBJECT-TYPE
    SYNTAX           CfprApBiosVfSerialPortAEnableEntry
    MAX-ACCESS       not-accessible
    STATUS           current
    DESCRIPTION
        "Entry for the cfprApBiosVfSerialPortAEnableTable table."
    INDEX { cfprApBiosVfSerialPortAEnableInstanceId }
    ::= { cfprApBiosVfSerialPortAEnableTable 1 }

CfprApBiosVfSerialPortAEnableEntry ::= SEQUENCE {
    cfprApBiosVfSerialPortAEnableInstanceId                          CfprApManagedObjectId,
    cfprApBiosVfSerialPortAEnableDn                                  CfprApManagedObjectDn,
    cfprApBiosVfSerialPortAEnableRn                                  SnmpAdminString,
    cfprApBiosVfSerialPortAEnableVpSerialPortAEnable                 CfprApBiosVfSerialPortAEnableVpSerialPortAEnable
}

cfprApBiosVfSerialPortAEnableInstanceId OBJECT-TYPE
    SYNTAX       CfprApManagedObjectId
    MAX-ACCESS   not-accessible
    STATUS       current
    DESCRIPTION
        "Instance identifier of the managed object."
    ::= { cfprApBiosVfSerialPortAEnableEntry 1 }

cfprApBiosVfSerialPortAEnableDn OBJECT-TYPE
    SYNTAX       CfprApManagedObjectDn
    MAX-ACCESS   read-only
    STATUS       current
    DESCRIPTION
        "Cisco Firepower bios:VfSerialPortAEnable:dn managed
        object property"
    ::= { cfprApBiosVfSerialPortAEnableEntry 2 }

cfprApBiosVfSerialPortAEnableRn OBJECT-TYPE
    SYNTAX       SnmpAdminString
    MAX-ACCESS   read-only
    STATUS       current
    DESCRIPTION
        "Cisco Firepower bios:VfSerialPortAEnable:rn managed
        object property"
    ::= { cfprApBiosVfSerialPortAEnableEntry 3 }

cfprApBiosVfSerialPortAEnableVpSerialPortAEnable OBJECT-TYPE
    SYNTAX       CfprApBiosVfSerialPortAEnableVpSerialPortAEnable
    MAX-ACCESS   read-only
    STATUS       current
    DESCRIPTION
        "Cisco Firepower bios:VfSerialPortAEnable:vpSerialPortAEnable
        managed object property"
    ::= { cfprApBiosVfSerialPortAEnableEntry 4 }

cfprApBiosVfSparingModeTable OBJECT-TYPE
    SYNTAX           SEQUENCE OF CfprApBiosVfSparingModeEntry
    MAX-ACCESS       not-accessible
    STATUS           current
    DESCRIPTION
        "Cisco Firepower bios:VfSparingMode managed object table"
    ::= { cfprApBiosObjects 67 }

cfprApBiosVfSparingModeEntry OBJECT-TYPE
    SYNTAX           CfprApBiosVfSparingModeEntry
    MAX-ACCESS       not-accessible
    STATUS           current
    DESCRIPTION
        "Entry for the cfprApBiosVfSparingModeTable table."
    INDEX { cfprApBiosVfSparingModeInstanceId }
    ::= { cfprApBiosVfSparingModeTable 1 }

CfprApBiosVfSparingModeEntry ::= SEQUENCE {
    cfprApBiosVfSparingModeInstanceId                                CfprApManagedObjectId,
    cfprApBiosVfSparingModeDn                                        CfprApManagedObjectDn,
    cfprApBiosVfSparingModeRn                                        SnmpAdminString,
    cfprApBiosVfSparingModeVpSparingMode                             CfprApBiosVfSparingModeVpSparingMode
}

cfprApBiosVfSparingModeInstanceId OBJECT-TYPE
    SYNTAX       CfprApManagedObjectId
    MAX-ACCESS   not-accessible
    STATUS       current
    DESCRIPTION
        "Instance identifier of the managed object."
    ::= { cfprApBiosVfSparingModeEntry 1 }

cfprApBiosVfSparingModeDn OBJECT-TYPE
    SYNTAX       CfprApManagedObjectDn
    MAX-ACCESS   read-only
    STATUS       current
    DESCRIPTION
        "Cisco Firepower bios:VfSparingMode:dn managed object property"
    ::= { cfprApBiosVfSparingModeEntry 2 }

cfprApBiosVfSparingModeRn OBJECT-TYPE
    SYNTAX       SnmpAdminString
    MAX-ACCESS   read-only
    STATUS       current
    DESCRIPTION
        "Cisco Firepower bios:VfSparingMode:rn managed object property"
    ::= { cfprApBiosVfSparingModeEntry 3 }

cfprApBiosVfSparingModeVpSparingMode OBJECT-TYPE
    SYNTAX       CfprApBiosVfSparingModeVpSparingMode
    MAX-ACCESS   read-only
    STATUS       current
    DESCRIPTION
        "Cisco Firepower bios:VfSparingMode:vpSparingMode
        managed object property"
    ::= { cfprApBiosVfSparingModeEntry 4 }

cfprApBiosVfSriovConfigTable OBJECT-TYPE
    SYNTAX           SEQUENCE OF CfprApBiosVfSriovConfigEntry
    MAX-ACCESS       not-accessible
    STATUS           current
    DESCRIPTION
        "Cisco Firepower bios:VfSriovConfig managed object table"
    ::= { cfprApBiosObjects 68 }

cfprApBiosVfSriovConfigEntry OBJECT-TYPE
    SYNTAX           CfprApBiosVfSriovConfigEntry
    MAX-ACCESS       not-accessible
    STATUS           current
    DESCRIPTION
        "Entry for the cfprApBiosVfSriovConfigTable table."
    INDEX { cfprApBiosVfSriovConfigInstanceId }
    ::= { cfprApBiosVfSriovConfigTable 1 }

CfprApBiosVfSriovConfigEntry ::= SEQUENCE {
    cfprApBiosVfSriovConfigInstanceId                                CfprApManagedObjectId,
    cfprApBiosVfSriovConfigDn                                        CfprApManagedObjectDn,
    cfprApBiosVfSriovConfigRn                                        SnmpAdminString,
    cfprApBiosVfSriovConfigVpSriov                                   CfprApBiosVfSriovConfigVpSriov
}

cfprApBiosVfSriovConfigInstanceId OBJECT-TYPE
    SYNTAX       CfprApManagedObjectId
    MAX-ACCESS   not-accessible
    STATUS       current
    DESCRIPTION
        "Instance identifier of the managed object."
    ::= { cfprApBiosVfSriovConfigEntry 1 }

cfprApBiosVfSriovConfigDn OBJECT-TYPE
    SYNTAX       CfprApManagedObjectDn
    MAX-ACCESS   read-only
    STATUS       current
    DESCRIPTION
        "Cisco Firepower bios:VfSriovConfig:dn managed object property"
    ::= { cfprApBiosVfSriovConfigEntry 2 }

cfprApBiosVfSriovConfigRn OBJECT-TYPE
    SYNTAX       SnmpAdminString
    MAX-ACCESS   read-only
    STATUS       current
    DESCRIPTION
        "Cisco Firepower bios:VfSriovConfig:rn managed object property"
    ::= { cfprApBiosVfSriovConfigEntry 3 }

cfprApBiosVfSriovConfigVpSriov OBJECT-TYPE
    SYNTAX       CfprApBiosVfSriovConfigVpSriov
    MAX-ACCESS   read-only
    STATUS       current
    DESCRIPTION
        "Cisco Firepower bios:VfSriovConfig:vpSriov managed
        object property"
    ::= { cfprApBiosVfSriovConfigEntry 4 }

cfprApBiosVfTPMSupportTable OBJECT-TYPE
    SYNTAX           SEQUENCE OF CfprApBiosVfTPMSupportEntry
    MAX-ACCESS       not-accessible
    STATUS           current
    DESCRIPTION
        "Cisco Firepower bios:VfTPMSupport managed object table"
    ::= { cfprApBiosObjects 69 }

cfprApBiosVfTPMSupportEntry OBJECT-TYPE
    SYNTAX           CfprApBiosVfTPMSupportEntry
    MAX-ACCESS       not-accessible
    STATUS           current
    DESCRIPTION
        "Entry for the cfprApBiosVfTPMSupportTable table."
    INDEX { cfprApBiosVfTPMSupportInstanceId }
    ::= { cfprApBiosVfTPMSupportTable 1 }

CfprApBiosVfTPMSupportEntry ::= SEQUENCE {
    cfprApBiosVfTPMSupportInstanceId                                 CfprApManagedObjectId,
    cfprApBiosVfTPMSupportDn                                         CfprApManagedObjectDn,
    cfprApBiosVfTPMSupportRn                                         SnmpAdminString,
    cfprApBiosVfTPMSupportVpTPMSupport                               CfprApBiosVfTPMSupportVpTPMSupport
}

cfprApBiosVfTPMSupportInstanceId OBJECT-TYPE
    SYNTAX       CfprApManagedObjectId
    MAX-ACCESS   not-accessible
    STATUS       current
    DESCRIPTION
        "Instance identifier of the managed object."
    ::= { cfprApBiosVfTPMSupportEntry 1 }

cfprApBiosVfTPMSupportDn OBJECT-TYPE
    SYNTAX       CfprApManagedObjectDn
    MAX-ACCESS   read-only
    STATUS       current
    DESCRIPTION
        "Cisco Firepower bios:VfTPMSupport:dn managed object property"
    ::= { cfprApBiosVfTPMSupportEntry 2 }

cfprApBiosVfTPMSupportRn OBJECT-TYPE
    SYNTAX       SnmpAdminString
    MAX-ACCESS   read-only
    STATUS       current
    DESCRIPTION
        "Cisco Firepower bios:VfTPMSupport:rn managed object property"
    ::= { cfprApBiosVfTPMSupportEntry 3 }

cfprApBiosVfTPMSupportVpTPMSupport OBJECT-TYPE
    SYNTAX       CfprApBiosVfTPMSupportVpTPMSupport
    MAX-ACCESS   read-only
    STATUS       current
    DESCRIPTION
        "Cisco Firepower bios:VfTPMSupport:vpTPMSupport
        managed object property"
    ::= { cfprApBiosVfTPMSupportEntry 4 }

cfprApBiosVfUCSMBootModeControlTable OBJECT-TYPE
    SYNTAX           SEQUENCE OF CfprApBiosVfUCSMBootModeControlEntry
    MAX-ACCESS       not-accessible
    STATUS           current
    DESCRIPTION
        "Cisco Firepower bios:VfUCSMBootModeControl managed object table"
    ::= { cfprApBiosObjects 70 }

cfprApBiosVfUCSMBootModeControlEntry OBJECT-TYPE
    SYNTAX           CfprApBiosVfUCSMBootModeControlEntry
    MAX-ACCESS       not-accessible
    STATUS           current
    DESCRIPTION
        "Entry for the cfprApBiosVfUCSMBootModeControlTable table."
    INDEX { cfprApBiosVfUCSMBootModeControlInstanceId }
    ::= { cfprApBiosVfUCSMBootModeControlTable 1 }

CfprApBiosVfUCSMBootModeControlEntry ::= SEQUENCE {
    cfprApBiosVfUCSMBootModeControlInstanceId                        CfprApManagedObjectId,
    cfprApBiosVfUCSMBootModeControlDn                                CfprApManagedObjectDn,
    cfprApBiosVfUCSMBootModeControlRn                                SnmpAdminString,
    cfprApBiosVfUCSMBootModeControlVpUEFIBootMode                    CfprApBiosVfUCSMBootModeControlVpUEFIBootMode
}

cfprApBiosVfUCSMBootModeControlInstanceId OBJECT-TYPE
    SYNTAX       CfprApManagedObjectId
    MAX-ACCESS   not-accessible
    STATUS       current
    DESCRIPTION
        "Instance identifier of the managed object."
    ::= { cfprApBiosVfUCSMBootModeControlEntry 1 }

cfprApBiosVfUCSMBootModeControlDn OBJECT-TYPE
    SYNTAX       CfprApManagedObjectDn
    MAX-ACCESS   read-only
    STATUS       current
    DESCRIPTION
        "Cisco Firepower bios:VfUCSMBootModeControl:dn
        managed object property"
    ::= { cfprApBiosVfUCSMBootModeControlEntry 2 }

cfprApBiosVfUCSMBootModeControlRn OBJECT-TYPE
    SYNTAX       SnmpAdminString
    MAX-ACCESS   read-only
    STATUS       current
    DESCRIPTION
        "Cisco Firepower bios:VfUCSMBootModeControl:rn
        managed object property"
    ::= { cfprApBiosVfUCSMBootModeControlEntry 3 }

cfprApBiosVfUCSMBootModeControlVpUEFIBootMode OBJECT-TYPE
    SYNTAX       CfprApBiosVfUCSMBootModeControlVpUEFIBootMode
    MAX-ACCESS   read-only
    STATUS       current
    DESCRIPTION
        "Cisco Firepower bios:VfUCSMBootModeControl:vpUEFIBootMode
        managed object property"
    ::= { cfprApBiosVfUCSMBootModeControlEntry 4 }

cfprApBiosVfUCSMBootOrderRuleControlTable OBJECT-TYPE
    SYNTAX           SEQUENCE OF CfprApBiosVfUCSMBootOrderRuleControlEntry
    MAX-ACCESS       not-accessible
    STATUS           current
    DESCRIPTION
        "Cisco Firepower bios:VfUCSMBootOrderRuleControl
        managed object table"
    ::= { cfprApBiosObjects 71 }

cfprApBiosVfUCSMBootOrderRuleControlEntry OBJECT-TYPE
    SYNTAX           CfprApBiosVfUCSMBootOrderRuleControlEntry
    MAX-ACCESS       not-accessible
    STATUS           current
    DESCRIPTION
        "Entry for the cfprApBiosVfUCSMBootOrderRuleControlTable table."
    INDEX { cfprApBiosVfUCSMBootOrderRuleControlInstanceId }
    ::= { cfprApBiosVfUCSMBootOrderRuleControlTable 1 }

CfprApBiosVfUCSMBootOrderRuleControlEntry ::= SEQUENCE {
    cfprApBiosVfUCSMBootOrderRuleControlInstanceId                   CfprApManagedObjectId,
    cfprApBiosVfUCSMBootOrderRuleControlDn                           CfprApManagedObjectDn,
    cfprApBiosVfUCSMBootOrderRuleControlRn                           SnmpAdminString,
    cfprApBiosVfUCSMBootOrderRuleControlVpUCSMBootOrderRule          CfprApBiosVfUCSMBootOrderRuleControlVpUCSMBootOrderRule
}

cfprApBiosVfUCSMBootOrderRuleControlInstanceId OBJECT-TYPE
    SYNTAX       CfprApManagedObjectId
    MAX-ACCESS   not-accessible
    STATUS       current
    DESCRIPTION
        "Instance identifier of the managed object."
    ::= { cfprApBiosVfUCSMBootOrderRuleControlEntry 1 }

cfprApBiosVfUCSMBootOrderRuleControlDn OBJECT-TYPE
    SYNTAX       CfprApManagedObjectDn
    MAX-ACCESS   read-only
    STATUS       current
    DESCRIPTION
        "Cisco Firepower bios:VfUCSMBootOrderRuleControl:dn
        managed object property"
    ::= { cfprApBiosVfUCSMBootOrderRuleControlEntry 2 }

cfprApBiosVfUCSMBootOrderRuleControlRn OBJECT-TYPE
    SYNTAX       SnmpAdminString
    MAX-ACCESS   read-only
    STATUS       current
    DESCRIPTION
        "Cisco Firepower bios:VfUCSMBootOrderRuleControl:rn
        managed object property"
    ::= { cfprApBiosVfUCSMBootOrderRuleControlEntry 3 }

cfprApBiosVfUCSMBootOrderRuleControlVpUCSMBootOrderRule OBJECT-TYPE
    SYNTAX       CfprApBiosVfUCSMBootOrderRuleControlVpUCSMBootOrderRule
    MAX-ACCESS   read-only
    STATUS       current
    DESCRIPTION
        "Cisco Firepower bios:VfUCSMBootOrderRuleControl:vpUCSMBootOrderRu
        le managed object property"
    ::= { cfprApBiosVfUCSMBootOrderRuleControlEntry 4 }

cfprApBiosVfUEFIOSUseLegacyVideoTable OBJECT-TYPE
    SYNTAX           SEQUENCE OF CfprApBiosVfUEFIOSUseLegacyVideoEntry
    MAX-ACCESS       not-accessible
    STATUS           current
    DESCRIPTION
        "Cisco Firepower bios:VfUEFIOSUseLegacyVideo managed object table"
    ::= { cfprApBiosObjects 72 }

cfprApBiosVfUEFIOSUseLegacyVideoEntry OBJECT-TYPE
    SYNTAX           CfprApBiosVfUEFIOSUseLegacyVideoEntry
    MAX-ACCESS       not-accessible
    STATUS           current
    DESCRIPTION
        "Entry for the cfprApBiosVfUEFIOSUseLegacyVideoTable table."
    INDEX { cfprApBiosVfUEFIOSUseLegacyVideoInstanceId }
    ::= { cfprApBiosVfUEFIOSUseLegacyVideoTable 1 }

CfprApBiosVfUEFIOSUseLegacyVideoEntry ::= SEQUENCE {
    cfprApBiosVfUEFIOSUseLegacyVideoInstanceId                       CfprApManagedObjectId,
    cfprApBiosVfUEFIOSUseLegacyVideoDn                               CfprApManagedObjectDn,
    cfprApBiosVfUEFIOSUseLegacyVideoRn                               SnmpAdminString,
    cfprApBiosVfUEFIOSUseLegacyVideoVpUEFIOSUseLegacyVideo           CfprApBiosVfUEFIOSUseLegacyVideoVpUEFIOSUseLegacyVideo
}

cfprApBiosVfUEFIOSUseLegacyVideoInstanceId OBJECT-TYPE
    SYNTAX       CfprApManagedObjectId
    MAX-ACCESS   not-accessible
    STATUS       current
    DESCRIPTION
        "Instance identifier of the managed object."
    ::= { cfprApBiosVfUEFIOSUseLegacyVideoEntry 1 }

cfprApBiosVfUEFIOSUseLegacyVideoDn OBJECT-TYPE
    SYNTAX       CfprApManagedObjectDn
    MAX-ACCESS   read-only
    STATUS       current
    DESCRIPTION
        "Cisco Firepower bios:VfUEFIOSUseLegacyVideo:dn
        managed object property"
    ::= { cfprApBiosVfUEFIOSUseLegacyVideoEntry 2 }

cfprApBiosVfUEFIOSUseLegacyVideoRn OBJECT-TYPE
    SYNTAX       SnmpAdminString
    MAX-ACCESS   read-only
    STATUS       current
    DESCRIPTION
        "Cisco Firepower bios:VfUEFIOSUseLegacyVideo:rn
        managed object property"
    ::= { cfprApBiosVfUEFIOSUseLegacyVideoEntry 3 }

cfprApBiosVfUEFIOSUseLegacyVideoVpUEFIOSUseLegacyVideo OBJECT-TYPE
    SYNTAX       CfprApBiosVfUEFIOSUseLegacyVideoVpUEFIOSUseLegacyVideo
    MAX-ACCESS   read-only
    STATUS       current
    DESCRIPTION
        "Cisco Firepower bios:VfUEFIOSUseLegacyVideo:vpUEFIOSUseLegacyVide
        o managed object property"
    ::= { cfprApBiosVfUEFIOSUseLegacyVideoEntry 4 }

cfprApBiosVfUSBBootConfigTable OBJECT-TYPE
    SYNTAX           SEQUENCE OF CfprApBiosVfUSBBootConfigEntry
    MAX-ACCESS       not-accessible
    STATUS           current
    DESCRIPTION
        "Cisco Firepower bios:VfUSBBootConfig managed object table"
    ::= { cfprApBiosObjects 73 }

cfprApBiosVfUSBBootConfigEntry OBJECT-TYPE
    SYNTAX           CfprApBiosVfUSBBootConfigEntry
    MAX-ACCESS       not-accessible
    STATUS           current
    DESCRIPTION
        "Entry for the cfprApBiosVfUSBBootConfigTable table."
    INDEX { cfprApBiosVfUSBBootConfigInstanceId }
    ::= { cfprApBiosVfUSBBootConfigTable 1 }

CfprApBiosVfUSBBootConfigEntry ::= SEQUENCE {
    cfprApBiosVfUSBBootConfigInstanceId                              CfprApManagedObjectId,
    cfprApBiosVfUSBBootConfigDn                                      CfprApManagedObjectDn,
    cfprApBiosVfUSBBootConfigRn                                      SnmpAdminString,
    cfprApBiosVfUSBBootConfigVpLegacyUSBSupport                      CfprApBiosVfUSBBootConfigVpLegacyUSBSupport,
    cfprApBiosVfUSBBootConfigVpMakeDeviceNonBootable                 CfprApBiosVfUSBBootConfigVpMakeDeviceNonBootable
}

cfprApBiosVfUSBBootConfigInstanceId OBJECT-TYPE
    SYNTAX       CfprApManagedObjectId
    MAX-ACCESS   not-accessible
    STATUS       current
    DESCRIPTION
        "Instance identifier of the managed object."
    ::= { cfprApBiosVfUSBBootConfigEntry 1 }

cfprApBiosVfUSBBootConfigDn OBJECT-TYPE
    SYNTAX       CfprApManagedObjectDn
    MAX-ACCESS   read-only
    STATUS       current
    DESCRIPTION
        "Cisco Firepower bios:VfUSBBootConfig:dn managed object property"
    ::= { cfprApBiosVfUSBBootConfigEntry 2 }

cfprApBiosVfUSBBootConfigRn OBJECT-TYPE
    SYNTAX       SnmpAdminString
    MAX-ACCESS   read-only
    STATUS       current
    DESCRIPTION
        "Cisco Firepower bios:VfUSBBootConfig:rn managed object property"
    ::= { cfprApBiosVfUSBBootConfigEntry 3 }

cfprApBiosVfUSBBootConfigVpLegacyUSBSupport OBJECT-TYPE
    SYNTAX       CfprApBiosVfUSBBootConfigVpLegacyUSBSupport
    MAX-ACCESS   read-only
    STATUS       current
    DESCRIPTION
        "Cisco Firepower bios:VfUSBBootConfig:vpLegacyUSBSupport
        managed object property"
    ::= { cfprApBiosVfUSBBootConfigEntry 4 }

cfprApBiosVfUSBBootConfigVpMakeDeviceNonBootable OBJECT-TYPE
    SYNTAX       CfprApBiosVfUSBBootConfigVpMakeDeviceNonBootable
    MAX-ACCESS   read-only
    STATUS       current
    DESCRIPTION
        "Cisco Firepower bios:VfUSBBootConfig:vpMakeDeviceNonBootable
        managed object property"
    ::= { cfprApBiosVfUSBBootConfigEntry 5 }

cfprApBiosVfUSBConfigurationTable OBJECT-TYPE
    SYNTAX           SEQUENCE OF CfprApBiosVfUSBConfigurationEntry
    MAX-ACCESS       not-accessible
    STATUS           current
    DESCRIPTION
        "Cisco Firepower bios:VfUSBConfiguration managed object table"
    ::= { cfprApBiosObjects 74 }

cfprApBiosVfUSBConfigurationEntry OBJECT-TYPE
    SYNTAX           CfprApBiosVfUSBConfigurationEntry
    MAX-ACCESS       not-accessible
    STATUS           current
    DESCRIPTION
        "Entry for the cfprApBiosVfUSBConfigurationTable table."
    INDEX { cfprApBiosVfUSBConfigurationInstanceId }
    ::= { cfprApBiosVfUSBConfigurationTable 1 }

CfprApBiosVfUSBConfigurationEntry ::= SEQUENCE {
    cfprApBiosVfUSBConfigurationInstanceId                           CfprApManagedObjectId,
    cfprApBiosVfUSBConfigurationDn                                   CfprApManagedObjectDn,
    cfprApBiosVfUSBConfigurationRn                                   SnmpAdminString,
    cfprApBiosVfUSBConfigurationVpLegacyUSBSupport                   CfprApBiosVfUSBConfigurationVpLegacyUSBSupport,
    cfprApBiosVfUSBConfigurationVpXHCIMode                           CfprApBiosVfUSBConfigurationVpXHCIMode
}

cfprApBiosVfUSBConfigurationInstanceId OBJECT-TYPE
    SYNTAX       CfprApManagedObjectId
    MAX-ACCESS   not-accessible
    STATUS       current
    DESCRIPTION
        "Instance identifier of the managed object."
    ::= { cfprApBiosVfUSBConfigurationEntry 1 }

cfprApBiosVfUSBConfigurationDn OBJECT-TYPE
    SYNTAX       CfprApManagedObjectDn
    MAX-ACCESS   read-only
    STATUS       current
    DESCRIPTION
        "Cisco Firepower bios:VfUSBConfiguration:dn managed
        object property"
    ::= { cfprApBiosVfUSBConfigurationEntry 2 }

cfprApBiosVfUSBConfigurationRn OBJECT-TYPE
    SYNTAX       SnmpAdminString
    MAX-ACCESS   read-only
    STATUS       current
    DESCRIPTION
        "Cisco Firepower bios:VfUSBConfiguration:rn managed
        object property"
    ::= { cfprApBiosVfUSBConfigurationEntry 3 }

cfprApBiosVfUSBConfigurationVpLegacyUSBSupport OBJECT-TYPE
    SYNTAX       CfprApBiosVfUSBConfigurationVpLegacyUSBSupport
    MAX-ACCESS   read-only
    STATUS       current
    DESCRIPTION
        "Cisco Firepower bios:VfUSBConfiguration:vpLegacyUSBSupport
        managed object property"
    ::= { cfprApBiosVfUSBConfigurationEntry 4 }

cfprApBiosVfUSBConfigurationVpXHCIMode OBJECT-TYPE
    SYNTAX       CfprApBiosVfUSBConfigurationVpXHCIMode
    MAX-ACCESS   read-only
    STATUS       current
    DESCRIPTION
        "Cisco Firepower bios:VfUSBConfiguration:vpXHCIMode
        managed object property"
    ::= { cfprApBiosVfUSBConfigurationEntry 5 }

cfprApBiosVfUSBFrontPanelAccessLockTable OBJECT-TYPE
    SYNTAX           SEQUENCE OF CfprApBiosVfUSBFrontPanelAccessLockEntry
    MAX-ACCESS       not-accessible
    STATUS           current
    DESCRIPTION
        "Cisco Firepower bios:VfUSBFrontPanelAccessLock
        managed object table"
    ::= { cfprApBiosObjects 75 }

cfprApBiosVfUSBFrontPanelAccessLockEntry OBJECT-TYPE
    SYNTAX           CfprApBiosVfUSBFrontPanelAccessLockEntry
    MAX-ACCESS       not-accessible
    STATUS           current
    DESCRIPTION
        "Entry for the cfprApBiosVfUSBFrontPanelAccessLockTable table."
    INDEX { cfprApBiosVfUSBFrontPanelAccessLockInstanceId }
    ::= { cfprApBiosVfUSBFrontPanelAccessLockTable 1 }

CfprApBiosVfUSBFrontPanelAccessLockEntry ::= SEQUENCE {
    cfprApBiosVfUSBFrontPanelAccessLockInstanceId                    CfprApManagedObjectId,
    cfprApBiosVfUSBFrontPanelAccessLockDn                            CfprApManagedObjectDn,
    cfprApBiosVfUSBFrontPanelAccessLockRn                            SnmpAdminString,
    cfprApBiosVfUSBFrontPanelAccessLockVpUSBFrontPanelLock           CfprApBiosVfUSBFrontPanelAccessLockVpUSBFrontPanelLock
}

cfprApBiosVfUSBFrontPanelAccessLockInstanceId OBJECT-TYPE
    SYNTAX       CfprApManagedObjectId
    MAX-ACCESS   not-accessible
    STATUS       current
    DESCRIPTION
        "Instance identifier of the managed object."
    ::= { cfprApBiosVfUSBFrontPanelAccessLockEntry 1 }

cfprApBiosVfUSBFrontPanelAccessLockDn OBJECT-TYPE
    SYNTAX       CfprApManagedObjectDn
    MAX-ACCESS   read-only
    STATUS       current
    DESCRIPTION
        "Cisco Firepower bios:VfUSBFrontPanelAccessLock:dn
        managed object property"
    ::= { cfprApBiosVfUSBFrontPanelAccessLockEntry 2 }

cfprApBiosVfUSBFrontPanelAccessLockRn OBJECT-TYPE
    SYNTAX       SnmpAdminString
    MAX-ACCESS   read-only
    STATUS       current
    DESCRIPTION
        "Cisco Firepower bios:VfUSBFrontPanelAccessLock:rn
        managed object property"
    ::= { cfprApBiosVfUSBFrontPanelAccessLockEntry 3 }

cfprApBiosVfUSBFrontPanelAccessLockVpUSBFrontPanelLock OBJECT-TYPE
    SYNTAX       CfprApBiosVfUSBFrontPanelAccessLockVpUSBFrontPanelLock
    MAX-ACCESS   read-only
    STATUS       current
    DESCRIPTION
        "Cisco Firepower bios:VfUSBFrontPanelAccessLock:vpUSBFrontPanelLoc
        k managed object property"
    ::= { cfprApBiosVfUSBFrontPanelAccessLockEntry 4 }

cfprApBiosVfUSBPortConfigurationTable OBJECT-TYPE
    SYNTAX           SEQUENCE OF CfprApBiosVfUSBPortConfigurationEntry
    MAX-ACCESS       not-accessible
    STATUS           current
    DESCRIPTION
        "Cisco Firepower bios:VfUSBPortConfiguration managed object table"
    ::= { cfprApBiosObjects 76 }

cfprApBiosVfUSBPortConfigurationEntry OBJECT-TYPE
    SYNTAX           CfprApBiosVfUSBPortConfigurationEntry
    MAX-ACCESS       not-accessible
    STATUS           current
    DESCRIPTION
        "Entry for the cfprApBiosVfUSBPortConfigurationTable table."
    INDEX { cfprApBiosVfUSBPortConfigurationInstanceId }
    ::= { cfprApBiosVfUSBPortConfigurationTable 1 }

CfprApBiosVfUSBPortConfigurationEntry ::= SEQUENCE {
    cfprApBiosVfUSBPortConfigurationInstanceId                       CfprApManagedObjectId,
    cfprApBiosVfUSBPortConfigurationDn                               CfprApManagedObjectDn,
    cfprApBiosVfUSBPortConfigurationRn                               SnmpAdminString,
    cfprApBiosVfUSBPortConfigurationVpPort6064Emulation              CfprApBiosVfUSBPortConfigurationVpPort6064Emulation,
    cfprApBiosVfUSBPortConfigurationVpUSBPortFront                   CfprApBiosVfUSBPortConfigurationVpUSBPortFront,
    cfprApBiosVfUSBPortConfigurationVpUSBPortInternal                CfprApBiosVfUSBPortConfigurationVpUSBPortInternal,
    cfprApBiosVfUSBPortConfigurationVpUSBPortKVM                     CfprApBiosVfUSBPortConfigurationVpUSBPortKVM,
    cfprApBiosVfUSBPortConfigurationVpUSBPortRear                    CfprApBiosVfUSBPortConfigurationVpUSBPortRear,
    cfprApBiosVfUSBPortConfigurationVpUSBPortSDCard                  CfprApBiosVfUSBPortConfigurationVpUSBPortSDCard,
    cfprApBiosVfUSBPortConfigurationVpUSBPortVMedia                  CfprApBiosVfUSBPortConfigurationVpUSBPortVMedia
}

cfprApBiosVfUSBPortConfigurationInstanceId OBJECT-TYPE
    SYNTAX       CfprApManagedObjectId
    MAX-ACCESS   not-accessible
    STATUS       current
    DESCRIPTION
        "Instance identifier of the managed object."
    ::= { cfprApBiosVfUSBPortConfigurationEntry 1 }

cfprApBiosVfUSBPortConfigurationDn OBJECT-TYPE
    SYNTAX       CfprApManagedObjectDn
    MAX-ACCESS   read-only
    STATUS       current
    DESCRIPTION
        "Cisco Firepower bios:VfUSBPortConfiguration:dn
        managed object property"
    ::= { cfprApBiosVfUSBPortConfigurationEntry 2 }

cfprApBiosVfUSBPortConfigurationRn OBJECT-TYPE
    SYNTAX       SnmpAdminString
    MAX-ACCESS   read-only
    STATUS       current
    DESCRIPTION
        "Cisco Firepower bios:VfUSBPortConfiguration:rn
        managed object property"
    ::= { cfprApBiosVfUSBPortConfigurationEntry 3 }

cfprApBiosVfUSBPortConfigurationVpPort6064Emulation OBJECT-TYPE
    SYNTAX       CfprApBiosVfUSBPortConfigurationVpPort6064Emulation
    MAX-ACCESS   read-only
    STATUS       current
    DESCRIPTION
        "Cisco Firepower bios:VfUSBPortConfiguration:vpPort6064Emulation
        managed object property"
    ::= { cfprApBiosVfUSBPortConfigurationEntry 4 }

cfprApBiosVfUSBPortConfigurationVpUSBPortFront OBJECT-TYPE
    SYNTAX       CfprApBiosVfUSBPortConfigurationVpUSBPortFront
    MAX-ACCESS   read-only
    STATUS       current
    DESCRIPTION
        "Cisco Firepower bios:VfUSBPortConfiguration:vpUSBPortFront
        managed object property"
    ::= { cfprApBiosVfUSBPortConfigurationEntry 5 }

cfprApBiosVfUSBPortConfigurationVpUSBPortInternal OBJECT-TYPE
    SYNTAX       CfprApBiosVfUSBPortConfigurationVpUSBPortInternal
    MAX-ACCESS   read-only
    STATUS       current
    DESCRIPTION
        "Cisco Firepower bios:VfUSBPortConfiguration:vpUSBPortInternal
        managed object property"
    ::= { cfprApBiosVfUSBPortConfigurationEntry 6 }

cfprApBiosVfUSBPortConfigurationVpUSBPortKVM OBJECT-TYPE
    SYNTAX       CfprApBiosVfUSBPortConfigurationVpUSBPortKVM
    MAX-ACCESS   read-only
    STATUS       current
    DESCRIPTION
        "Cisco Firepower bios:VfUSBPortConfiguration:vpUSBPortKVM
        managed object property"
    ::= { cfprApBiosVfUSBPortConfigurationEntry 7 }

cfprApBiosVfUSBPortConfigurationVpUSBPortRear OBJECT-TYPE
    SYNTAX       CfprApBiosVfUSBPortConfigurationVpUSBPortRear
    MAX-ACCESS   read-only
    STATUS       current
    DESCRIPTION
        "Cisco Firepower bios:VfUSBPortConfiguration:vpUSBPortRear
        managed object property"
    ::= { cfprApBiosVfUSBPortConfigurationEntry 8 }

cfprApBiosVfUSBPortConfigurationVpUSBPortSDCard OBJECT-TYPE
    SYNTAX       CfprApBiosVfUSBPortConfigurationVpUSBPortSDCard
    MAX-ACCESS   read-only
    STATUS       current
    DESCRIPTION
        "Cisco Firepower bios:VfUSBPortConfiguration:vpUSBPortSDCard
        managed object property"
    ::= { cfprApBiosVfUSBPortConfigurationEntry 9 }

cfprApBiosVfUSBPortConfigurationVpUSBPortVMedia OBJECT-TYPE
    SYNTAX       CfprApBiosVfUSBPortConfigurationVpUSBPortVMedia
    MAX-ACCESS   read-only
    STATUS       current
    DESCRIPTION
        "Cisco Firepower bios:VfUSBPortConfiguration:vpUSBPortVMedia
        managed object property"
    ::= { cfprApBiosVfUSBPortConfigurationEntry 10 }

cfprApBiosVfUSBSystemIdlePowerOptimizingSettingTable OBJECT-TYPE
    SYNTAX           SEQUENCE OF CfprApBiosVfUSBSystemIdlePowerOptimizingSettingEntry
    MAX-ACCESS       not-accessible
    STATUS           current
    DESCRIPTION
        "Cisco Firepower bios:VfUSBSystemIdlePowerOptimizingSetting
        managed object table"
    ::= { cfprApBiosObjects 77 }

cfprApBiosVfUSBSystemIdlePowerOptimizingSettingEntry OBJECT-TYPE
    SYNTAX           CfprApBiosVfUSBSystemIdlePowerOptimizingSettingEntry
    MAX-ACCESS       not-accessible
    STATUS           current
    DESCRIPTION
        "Entry for the cfprApBiosVfUSBSystemIdlePowerOptimizingSettingTable table."
    INDEX { cfprApBiosVfUSBSystemIdlePowerOptimizingSettingInstanceId }
    ::= { cfprApBiosVfUSBSystemIdlePowerOptimizingSettingTable 1 }

CfprApBiosVfUSBSystemIdlePowerOptimizingSettingEntry ::= SEQUENCE {
    cfprApBiosVfUSBSystemIdlePowerOptimizingSettingInstanceId        CfprApManagedObjectId,
    cfprApBiosVfUSBSystemIdlePowerOptimizingSettingDn                CfprApManagedObjectDn,
    cfprApBiosVfUSBSystemIdlePowerOptimizingSettingRn                SnmpAdminString,
    cfprApBiosVfUSBSystemIdlePowerOptimizingSettingVpUSBIdlePowerOptimizing CfprApBiosVfUSBSysIdlePowerOptimizingSettingVpUSBIdlePowerOptimize
}

cfprApBiosVfUSBSystemIdlePowerOptimizingSettingInstanceId OBJECT-TYPE
    SYNTAX       CfprApManagedObjectId
    MAX-ACCESS   not-accessible
    STATUS       current
    DESCRIPTION
        "Instance identifier of the managed object."
    ::= { cfprApBiosVfUSBSystemIdlePowerOptimizingSettingEntry 1 }

cfprApBiosVfUSBSystemIdlePowerOptimizingSettingDn OBJECT-TYPE
    SYNTAX       CfprApManagedObjectDn
    MAX-ACCESS   read-only
    STATUS       current
    DESCRIPTION
        "Cisco Firepower bios:VfUSBSystemIdlePowerOptimizingSetting:dn
        managed object property"
    ::= { cfprApBiosVfUSBSystemIdlePowerOptimizingSettingEntry 2 }

cfprApBiosVfUSBSystemIdlePowerOptimizingSettingRn OBJECT-TYPE
    SYNTAX       SnmpAdminString
    MAX-ACCESS   read-only
    STATUS       current
    DESCRIPTION
        "Cisco Firepower bios:VfUSBSystemIdlePowerOptimizingSetting:rn
        managed object property"
    ::= { cfprApBiosVfUSBSystemIdlePowerOptimizingSettingEntry 3 }

cfprApBiosVfUSBSystemIdlePowerOptimizingSettingVpUSBIdlePowerOptimizing OBJECT-TYPE
    SYNTAX       CfprApBiosVfUSBSysIdlePowerOptimizingSettingVpUSBIdlePowerOptimize
    MAX-ACCESS   read-only
    STATUS       current
    DESCRIPTION
        "Cisco Firepower bios:VfUSBSystemIdlePowerOptimizingSetting:vpUSBI
        dlePowerOptimizing managed object property"
    ::= { cfprApBiosVfUSBSystemIdlePowerOptimizingSettingEntry 4 }

cfprApBiosVfVGAPriorityTable OBJECT-TYPE
    SYNTAX           SEQUENCE OF CfprApBiosVfVGAPriorityEntry
    MAX-ACCESS       not-accessible
    STATUS           current
    DESCRIPTION
        "Cisco Firepower bios:VfVGAPriority managed object table"
    ::= { cfprApBiosObjects 78 }

cfprApBiosVfVGAPriorityEntry OBJECT-TYPE
    SYNTAX           CfprApBiosVfVGAPriorityEntry
    MAX-ACCESS       not-accessible
    STATUS           current
    DESCRIPTION
        "Entry for the cfprApBiosVfVGAPriorityTable table."
    INDEX { cfprApBiosVfVGAPriorityInstanceId }
    ::= { cfprApBiosVfVGAPriorityTable 1 }

CfprApBiosVfVGAPriorityEntry ::= SEQUENCE {
    cfprApBiosVfVGAPriorityInstanceId                                CfprApManagedObjectId,
    cfprApBiosVfVGAPriorityDn                                        CfprApManagedObjectDn,
    cfprApBiosVfVGAPriorityRn                                        SnmpAdminString,
    cfprApBiosVfVGAPriorityVpVGAPriority                             CfprApBiosVfVGAPriorityVpVGAPriority
}

cfprApBiosVfVGAPriorityInstanceId OBJECT-TYPE
    SYNTAX       CfprApManagedObjectId
    MAX-ACCESS   not-accessible
    STATUS       current
    DESCRIPTION
        "Instance identifier of the managed object."
    ::= { cfprApBiosVfVGAPriorityEntry 1 }

cfprApBiosVfVGAPriorityDn OBJECT-TYPE
    SYNTAX       CfprApManagedObjectDn
    MAX-ACCESS   read-only
    STATUS       current
    DESCRIPTION
        "Cisco Firepower bios:VfVGAPriority:dn managed object property"
    ::= { cfprApBiosVfVGAPriorityEntry 2 }

cfprApBiosVfVGAPriorityRn OBJECT-TYPE
    SYNTAX       SnmpAdminString
    MAX-ACCESS   read-only
    STATUS       current
    DESCRIPTION
        "Cisco Firepower bios:VfVGAPriority:rn managed object property"
    ::= { cfprApBiosVfVGAPriorityEntry 3 }

cfprApBiosVfVGAPriorityVpVGAPriority OBJECT-TYPE
    SYNTAX       CfprApBiosVfVGAPriorityVpVGAPriority
    MAX-ACCESS   read-only
    STATUS       current
    DESCRIPTION
        "Cisco Firepower bios:VfVGAPriority:vpVGAPriority
        managed object property"
    ::= { cfprApBiosVfVGAPriorityEntry 4 }

END
