-- ArubaOS 6.5.1.3_58402
-- vim:set ts=4 sw=4: 
WLSX-WLAN-MIB DEFINITIONS ::= BEGIN

   IMPORTS
       TEXTUAL-CONVENTION FROM SNMPv2-TC 

       MODULE-IDENTITY,
       OBJECT-TYPE,
       snmpModules,
       Integer32,
       Unsigned32,
	   Counter32,
	   IpAddress,
	   NOTIFICATION-TYPE
           FROM SNMPv2-SMI

       TDomain,
       DisplayString,
       PhysAddress,
       TAddress,
       TimeInterval,
       RowStatus,
       StorageType,
       TestAndIncr,
	   MacAddress,
	   TruthValue
           FROM SNMPv2-TC

       ifIndex
           FROM RFC1213-MIB

	   ArubaEnableValue,
	   ArubaFrameType,
	   ArubaActiveState,
	   ArubaRogueApType,
	   ArubaAuthenticationMethods,
	   ArubaEncryptionMethods,
	   ArubaPhyType,
	   ArubaVoipProtocolType,
	   ArubaVlanValidRange,
	   ArubaAccessPointMode,
	   ArubaAPStatus,
	   ArubaEnet1Mode,
	   ArubaUnprovisionedStatus,
	   ArubaMonitorMode,
	   ArubaAntennaSetting,
       ArubaMeshRole,
	   ArubaHTMode,
	   ArubaHTExtChannel
	   		FROM ARUBA-TC

       OBJECT-GROUP
           FROM SNMPv2-CONF
		wlsxEnterpriseMibModules
			FROM ARUBA-MIB;

   wlsxWlanMIB MODULE-IDENTITY 
       LAST-UPDATED "1001261806Z"
       ORGANIZATION "Aruba Wireless Networks"
       CONTACT-INFO
            "Postal:    1322 Crossman Avenue
                        Sunnyvale, CA 94089	
            E-mail:     dl-support@arubanetworks.com
            Phone:      +1 408 227 4500"
       DESCRIPTION
           "This MIB module defines MIB objects which provide
            information about the Wireless Management System (WMS) in the 
			Aruba Controller."
       REVISION        "1001261806Z"
       DESCRIPTION
           "The initial revision."
       ::= { wlsxEnterpriseMibModules 5 }

   wlsxWlanConfigGroup     	OBJECT IDENTIFIER ::= { wlsxWlanMIB 1 }
   wlsxWlanStateGroup     	OBJECT IDENTIFIER ::= { wlsxWlanMIB 2 }
   wlsxWlanStatsGroup     	OBJECT IDENTIFIER ::= { wlsxWlanMIB 3 }
   wlsxRAPTraps                 OBJECT IDENTIFIER ::= { wlsxWlanMIB 100 }

-- wlsxWlanAccessPointInfoGroup contains a Local Access Point Information Table.
-- which lists all the APs connected to the controller, a Global AP Info Table
-- which lists all the APs in the Aruba Domain. The Global table is valid only
-- on the Master controller. The Group also contains two scalar objects which 
-- indicate the total number of APs and the total number of Clients connected.

   wlsxWlanAccessPointInfoGroup  OBJECT IDENTIFIER ::= { wlsxWlanStateGroup 1 }
   wlsxWlanStationInfoGroup  OBJECT IDENTIFIER ::= { wlsxWlanStateGroup 2 }
   wlsxWlanAssociationInfoGroup  OBJECT IDENTIFIER ::= { wlsxWlanStateGroup 3 }
   wlsxWlanAccessPointStatsGroup  OBJECT IDENTIFIER ::= { wlsxWlanStatsGroup 1 }
   wlsxWlanStationStatsGroup  OBJECT IDENTIFIER ::= { wlsxWlanStatsGroup 2 }
   wlsxWlanSwitchStatsGroup  OBJECT IDENTIFIER ::= { wlsxWlanStatsGroup 3 }
   wlsxSSIDConfigGroup  OBJECT IDENTIFIER ::= { wlsxWlanConfigGroup 1 }
   wlsxAPConfigGroup  OBJECT IDENTIFIER ::= { wlsxWlanConfigGroup 2 }

   wlsxWlanTotalNumAccessPoints  OBJECT-TYPE 
         SYNTAX       Unsigned32
         MAX-ACCESS   read-only
         STATUS       current
         DESCRIPTION
            "
			Total Number of Access Points connected to the controller.
            "
        ::= { wlsxWlanAccessPointInfoGroup 1 }

   wlsxWlanTotalNumStationsAssociated  OBJECT-TYPE 
         SYNTAX       Unsigned32
         MAX-ACCESS   read-only
         STATUS       current
         DESCRIPTION
            "
			Total Number of Stations Associated to the controller.
            "
        ::= { wlsxWlanAccessPointInfoGroup 2 }

-- AP Group Table
   wlsxWlanAPGroupTable  OBJECT-TYPE 
	  SYNTAX       SEQUENCE OF WlanAPGroupEntry 
	  MAX-ACCESS   not-accessible		
      STATUS       current 
      DESCRIPTION 
	  	"
			This Table lists all the Access Points Groups configured in the 
			Aruba controller. 
		"
      ::= { wlsxWlanAccessPointInfoGroup 3 } 

   wlsxWlanAPGroupEntry OBJECT-TYPE 
	  SYNTAX       WlanAPGroupEntry 
	  MAX-ACCESS   not-accessible		
      STATUS       current 
      DESCRIPTION 
             "AP Group Entry"
	  INDEX {wlanAPGroup}
      ::= { wlsxWlanAPGroupTable 1 } 

   WlanAPGroupEntry ::=
     SEQUENCE {
         wlanAPGroup	DisplayString,
		 wlanAPNumAps		Integer32
   }

    wlanAPGroup OBJECT-TYPE
         SYNTAX       DisplayString
         MAX-ACCESS   not-accessible
         STATUS       current
         DESCRIPTION
            "
			The name of an AP group
            "
        ::= { wlsxWlanAPGroupEntry 1 }

   	wlanAPNumAps OBJECT-TYPE
         SYNTAX       Integer32
         MAX-ACCESS   read-only
         STATUS       current
         DESCRIPTION
            "
			The number of APs in the AP Group
            "
        ::= { wlsxWlanAPGroupEntry 2 }


 -- AP Table

   wlsxWlanAPTable  OBJECT-TYPE 
	  SYNTAX       SEQUENCE OF WlanAPEntry 
	  MAX-ACCESS   not-accessible		
      STATUS       current 
      DESCRIPTION 
	  	"
			This table lists all the Access Points connected to the 
			controller. 
		"
      ::= { wlsxWlanAccessPointInfoGroup 4 } 

   wlsxWlanAPEntry OBJECT-TYPE 
	  SYNTAX       WlanAPEntry 
	  MAX-ACCESS   not-accessible		
      STATUS       current 
      DESCRIPTION 
             "Access Point Entry"
	  INDEX {wlanAPMacAddress}
      ::= { wlsxWlanAPTable 1 } 

   WlanAPEntry ::=
     SEQUENCE {
         wlanAPMacAddress			MacAddress,
		 wlanAPIpAddress			IpAddress,
		 wlanAPName					DisplayString,
		 wlanAPGroupName			DisplayString,
		 wlanAPModel				OBJECT IDENTIFIER,
		 wlanAPSerialNumber			DisplayString,
		 wlanAPdot11aAntennaGain	Integer32,
		 wlanAPdot11gAntennaGain	Integer32,
		 wlanAPNumRadios			Integer32,
		 wlanAPEnet1Mode			ArubaEnet1Mode,
		 wlanAPIpsecMode			ArubaEnableValue,
		 wlanAPUpTime				TimeTicks,
		 wlanAPModelName			DisplayString,
		 wlanAPLocation			    DisplayString,
		 wlanAPBuilding				Integer32,
		 wlanAPFloor				Integer32,
		 wlanAPLoc					Integer32,
		 wlanAPExternalAntenna		ArubaAntennaSetting,
		 wlanAPStatus				ArubaAPStatus,
		 wlanAPNumBootstraps		Integer32,
		 wlanAPNumReboots			Integer32,
		 wlanAPUnprovisioned        ArubaUnprovisionedStatus,
		 wlanAPMonitorMode          ArubaMonitorMode,
		 wlanAPFQLNBuilding			DisplayString,
		 wlanAPFQLNFloor			DisplayString,
		 wlanAPFQLN					DisplayString,
		 wlanAPFQLNCampus			DisplayString,
		 wlanAPLongitude   			DisplayString,
		 wlanAPLatitude    			DisplayString,
		 wlanAPAltitude    			DisplayString,
		 wlanAPMeshRole             ArubaMeshRole,
         wlanAPSysLocation          DisplayString,
         wlanAPHwVersion            DisplayString,
         wlanAPSwVersion            DisplayString,
         wlanAPNumWarmReboots       Integer32,
         wlanAPOuterIpAddress       IpAddress,
         wlanAPRemoteLanIpAddress   IpAddress,
         wlanAPActiveUplink         INTEGER,
         wlanAPSwitchIpAddress      IpAddress,
         wlanAPStandbyIpAddress     IpAddress,
         wlanAPConnectedAsStandby   INTEGER,
         wlanAPServiceTag           DisplayString
   }

   	wlanAPMacAddress OBJECT-TYPE
         SYNTAX       MacAddress
         MAX-ACCESS   not-accessible
         STATUS       current
         DESCRIPTION
            "
			Ethernet MAC Address of the Access Point
            "
        ::= { wlsxWlanAPEntry 1 }

   	wlanAPIpAddress OBJECT-TYPE
         SYNTAX       IpAddress
         MAX-ACCESS   read-only
         STATUS       current
         DESCRIPTION
            "
			IP Address of the Access Point
            "
        ::= { wlsxWlanAPEntry 2 }

	wlanAPName OBJECT-TYPE
         SYNTAX       DisplayString
         MAX-ACCESS   read-write
         STATUS       current
         DESCRIPTION
            "
			Host name of the Access Point.
            "
        ::= { wlsxWlanAPEntry 3 }

	wlanAPGroupName OBJECT-TYPE
         SYNTAX       DisplayString
         MAX-ACCESS   read-write
         STATUS       current
         DESCRIPTION
            "
			Group Name of the Access Point.
            "
        ::= { wlsxWlanAPEntry 4 }

   	wlanAPModel	OBJECT-TYPE
         SYNTAX       OBJECT IDENTIFIER
         MAX-ACCESS   read-only
         STATUS       current
         DESCRIPTION
            "
			 Sys OID of the Access Point.
            "
        ::= { wlsxWlanAPEntry 5 }

   	wlanAPSerialNumber	OBJECT-TYPE
         SYNTAX       DisplayString(SIZE(0..32))
         MAX-ACCESS   read-only
         STATUS       current
         DESCRIPTION
            "
			Serial Number of the Access Point.
            "
        ::= { wlsxWlanAPEntry 6 }

   	wlanAPdot11aAntennaGain	OBJECT-TYPE
         SYNTAX       Integer32
         MAX-ACCESS   read-only
         STATUS       current
         DESCRIPTION
            "
			Configured antenna  gain for 'A' Radio.
            "
        ::= { wlsxWlanAPEntry 7 }

   	wlanAPdot11gAntennaGain	OBJECT-TYPE
         SYNTAX       Integer32
         MAX-ACCESS   read-only
         STATUS       current
         DESCRIPTION
            "
			Configured antenna  gain for 'G' Radio.
            "
        ::= { wlsxWlanAPEntry 8 }

   	wlanAPNumRadios	OBJECT-TYPE
         SYNTAX       Integer32
         MAX-ACCESS   read-only
         STATUS       current
         DESCRIPTION
            "
			Number of Radios in the Access Point.
            "
        ::= { wlsxWlanAPEntry 9 }

   	wlanAPEnet1Mode OBJECT-TYPE
         SYNTAX       ArubaEnet1Mode
         MAX-ACCESS   read-only
         STATUS       current
         DESCRIPTION
            "
			Enet1 Mode of the Access Point.
            "
        ::= { wlsxWlanAPEntry 10 }

   	wlanAPIpsecMode OBJECT-TYPE
         SYNTAX       ArubaEnableValue
         MAX-ACCESS   read-only
         STATUS       current
         DESCRIPTION
            "
			IPSEC Mode of the Access Point.
            "
        ::= { wlsxWlanAPEntry 11 }

   	wlanAPUpTime OBJECT-TYPE
         SYNTAX       TimeTicks
         MAX-ACCESS   read-only
         STATUS       current
         DESCRIPTION
            "
			Time (in hundredths of seconds) since the last time the Access
			 Point bootstrapped with the controller.
            "
        ::= { wlsxWlanAPEntry 12 }

	wlanAPModelName OBJECT-TYPE
         SYNTAX       DisplayString
         MAX-ACCESS   read-only
         STATUS       current
         DESCRIPTION
            "
			Model name of the Access Point.
            "
        ::= { wlsxWlanAPEntry 13 }

	wlanAPLocation OBJECT-TYPE
         SYNTAX       DisplayString
         MAX-ACCESS   read-only
         STATUS       current
         DESCRIPTION
            "
			Location of the Access Point.
            "
        ::= { wlsxWlanAPEntry 14 }

	wlanAPBuilding OBJECT-TYPE
         SYNTAX       Integer32
         MAX-ACCESS   read-only
         STATUS       current
         DESCRIPTION
            "
			AP Building Number.
            "
        ::= { wlsxWlanAPEntry 15 }

	wlanAPFloor OBJECT-TYPE
         SYNTAX       Integer32
         MAX-ACCESS   read-only
         STATUS       current
         DESCRIPTION
            "
			AP Floor Number.
            "
        ::= { wlsxWlanAPEntry 16 }

	wlanAPLoc OBJECT-TYPE
         SYNTAX       Integer32
         MAX-ACCESS   read-only
         STATUS       current
         DESCRIPTION
            "
			AP Location.
            "
        ::= { wlsxWlanAPEntry 17 }

	wlanAPExternalAntenna OBJECT-TYPE
         SYNTAX       ArubaAntennaSetting
         MAX-ACCESS   read-only
         STATUS       current
         DESCRIPTION
            "
			AP Antenna Status.
            "
        ::= { wlsxWlanAPEntry 18 }

	wlanAPStatus OBJECT-TYPE
         SYNTAX       ArubaAPStatus
         MAX-ACCESS   read-only
         STATUS       current
         DESCRIPTION
            "
			AP Status.
            "
        ::= { wlsxWlanAPEntry 19 }

	wlanAPNumBootstraps OBJECT-TYPE
         SYNTAX       Integer32
         MAX-ACCESS   read-only
         STATUS       current
         DESCRIPTION
            "
			Number of times the AP has bootstrapped with the controller.
            "
        ::= { wlsxWlanAPEntry 20 }

	wlanAPNumReboots OBJECT-TYPE
         SYNTAX       Integer32
         MAX-ACCESS   read-only
         STATUS       current
         DESCRIPTION
            "
			Number of times the AP has rebooted.
            "
        ::= { wlsxWlanAPEntry 21 }

	wlanAPUnprovisioned OBJECT-TYPE
         SYNTAX       ArubaUnprovisionedStatus
         MAX-ACCESS   read-only
         STATUS       current
         DESCRIPTION
            "
			Indicates whether the AP is unprovisioned due to lack of
			 antenna gain or location code settings.
            "
        ::= { wlsxWlanAPEntry 22 }

	wlanAPMonitorMode OBJECT-TYPE
         SYNTAX       ArubaMonitorMode
         MAX-ACCESS   read-only
         STATUS       current
         DESCRIPTION
            "
			Indicates whether any radio on this AP is acting as an
			 air monitor.
            "
        ::= { wlsxWlanAPEntry 23 }

	wlanAPFQLNBuilding OBJECT-TYPE
         SYNTAX       DisplayString
         MAX-ACCESS   read-only
         STATUS       current
         DESCRIPTION
            "
			The building component of the AP's FQLN.
            "
        ::= { wlsxWlanAPEntry 24 }

	wlanAPFQLNFloor OBJECT-TYPE
         SYNTAX       DisplayString
         MAX-ACCESS   read-only
         STATUS       current
         DESCRIPTION
            "
			The floor component of the AP's FQLN.
            "
        ::= { wlsxWlanAPEntry 25 }

	wlanAPFQLN OBJECT-TYPE
         SYNTAX       DisplayString
         MAX-ACCESS   read-write
         STATUS       current
         DESCRIPTION
            "
			The AP's Fully Qualified Location Name (FQLN).
            "
        ::= { wlsxWlanAPEntry 26 }

	wlanAPFQLNCampus OBJECT-TYPE
         SYNTAX       DisplayString
         MAX-ACCESS   read-only
         STATUS       current
         DESCRIPTION
            "
			The campus component of the AP's FQLN.
            "
        ::= { wlsxWlanAPEntry 27 }

	wlanAPLongitude OBJECT-TYPE
         SYNTAX       DisplayString
         MAX-ACCESS   read-write
         STATUS       current
         DESCRIPTION
            "
			Longitude of the AP. Signed floating-point value.
            "
        ::= { wlsxWlanAPEntry 28 }

	wlanAPLatitude OBJECT-TYPE
         SYNTAX       DisplayString
         MAX-ACCESS   read-write
         STATUS       current
         DESCRIPTION
            "
			Latitude of the AP. Signed floating-point value.
            "
        ::= { wlsxWlanAPEntry 29 }

	wlanAPAltitude OBJECT-TYPE
         SYNTAX       DisplayString
         MAX-ACCESS   read-write
         STATUS       current
         DESCRIPTION
            "
			Altitude of the AP. Signed floating-point value.
            "
        ::= { wlsxWlanAPEntry 30 }

	wlanAPMeshRole OBJECT-TYPE
         SYNTAX       ArubaMeshRole
         MAX-ACCESS   read-write
         STATUS       current
         DESCRIPTION
            "
			AP Mesh role
            "
        ::= { wlsxWlanAPEntry 31 }
        
	wlanAPSysLocation OBJECT-TYPE
         SYNTAX       DisplayString
         MAX-ACCESS   read-only
         STATUS       current
         DESCRIPTION
            "
			AP sysLocation
            "
        ::= { wlsxWlanAPEntry 32 }
        
    wlanAPHwVersion OBJECT-TYPE
         SYNTAX       DisplayString  (SIZE(1..64))
         MAX-ACCESS   read-only
         STATUS       current
         DESCRIPTION
            "
                        Hardware version of the AP.
            "
        ::= { wlsxWlanAPEntry 33 }
 
    wlanAPSwVersion OBJECT-TYPE
         SYNTAX       DisplayString  (SIZE(1..64))
         MAX-ACCESS   read-only
         STATUS       current
         DESCRIPTION
            "
                        Software version of the AP.
            "
        ::= { wlsxWlanAPEntry 34 }

        wlanAPNumWarmReboots OBJECT-TYPE
         SYNTAX       Integer32
         MAX-ACCESS   read-only
         STATUS       current
         DESCRIPTION
            "
                        Number of times the AP has warm-rebooted.
            "
        ::= { wlsxWlanAPEntry 35 }

         wlanAPOuterIpAddress OBJECT-TYPE
         SYNTAX       IpAddress
         MAX-ACCESS   read-only
         STATUS       current
         DESCRIPTION
            "
                        Outer IP Address of the Access Point.
            "
        ::= { wlsxWlanAPEntry 36 }

        wlanAPRemoteLanIpAddress OBJECT-TYPE
         SYNTAX       IpAddress
         MAX-ACCESS   read-only
         STATUS       current
         DESCRIPTION
            "
                        LAN IP Address of the Remote Access Point.
            "
        ::= { wlsxWlanAPEntry 37 }

        wlanAPActiveUplink OBJECT-TYPE
         SYNTAX       INTEGER {
                                  ethernet(1),
                                  usb(2),
                                  pppoe(3)
                             }
         MAX-ACCESS   read-only
         STATUS       current
         DESCRIPTION
            "
                        Uplink of the RAP(Ethernet or USB).
            "
        ::= { wlsxWlanAPEntry 38 }

        wlanAPSwitchIpAddress OBJECT-TYPE
        SYNTAX       IpAddress
        MAX-ACCESS   read-only
        STATUS       current
        DESCRIPTION
            "
                        Access points' Serving Controller's IP Address.
            "
        ::= { wlsxWlanAPEntry 39 }

        wlanAPStandbyIpAddress OBJECT-TYPE
        SYNTAX       IpAddress
        MAX-ACCESS   read-only
        STATUS       current
        DESCRIPTION
            "
                        Access points' Standby Controller's IP Address.
            "
        ::= { wlsxWlanAPEntry 40 }

        wlanAPConnectedAsStandby OBJECT-TYPE
        SYNTAX       INTEGER {
                                 active(0),
                                 standby(1)
                             }
        MAX-ACCESS   read-only
        STATUS       current
        DESCRIPTION
            "
                        Access point connected as active/standby.
            "
        ::= { wlsxWlanAPEntry 41 }

        wlanAPServiceTag OBJECT-TYPE
        SYNTAX       DisplayString  (SIZE(1..64))
        MAX-ACCESS   read-only
        STATUS       current
        DESCRIPTION
            "
                        Access point service tag.
            "
        ::= { wlsxWlanAPEntry 42 }

 
-- Radio table is indexed by the Mac Address of the AP and the type of the
-- radio.

   wlsxWlanRadioTable  OBJECT-TYPE 
	  SYNTAX       SEQUENCE OF WlanRadioEntry 
	  MAX-ACCESS   not-accessible		
      STATUS       current 
      DESCRIPTION 
	  	"
			This table lists all the radios known to the 
			controller. 
		"
      ::= { wlsxWlanAccessPointInfoGroup 5 } 

   wlsxWlanRadioEntry OBJECT-TYPE 
	  SYNTAX       WlanRadioEntry 
	  MAX-ACCESS   not-accessible		
      STATUS       current 
      DESCRIPTION 
             "AP Radio Entry"
	  INDEX {wlanAPMacAddress, wlanAPRadioNumber}
      ::= { wlsxWlanRadioTable 1 } 

   WlanRadioEntry ::=
     SEQUENCE {
		 wlanAPRadioNumber					Integer32,
		 wlanAPRadioType					ArubaPhyType,
		 wlanAPRadioChannel					Integer32,
		 wlanAPRadioTransmitPower			Integer32,
		 wlanAPRadioMode					ArubaAccessPointMode,
		 wlanAPRadioUtilization				Integer32,
		 wlanAPRadioNumAssociatedClients	Integer32,
		 wlanAPRadioNumMonitoredClients		Integer32,
		 wlanAPRadioNumActiveBSSIDs			Integer32,
		 wlanAPRadioNumMonitoredBSSIDs		Integer32,
		 wlanAPRadioBearing     			DisplayString,
		 wlanAPRadioTiltAngle   			DisplayString,
		 wlanAPRadioHTMode					ArubaHTMode,
		 wlanAPRadioHTExtChannel			ArubaHTExtChannel,
		 wlanAPRadioHTChannel				DisplayString,
		 wlanAPRadioAPName  				DisplayString
	 }

   	wlanAPRadioNumber OBJECT-TYPE
         SYNTAX       Integer32
         MAX-ACCESS   not-accessible
         STATUS       current
         DESCRIPTION
            "
			The radio number
            "
        ::= { wlsxWlanRadioEntry 1 }

   	wlanAPRadioType OBJECT-TYPE
         SYNTAX       ArubaPhyType
         MAX-ACCESS   read-write
         STATUS       current
         DESCRIPTION
            "
			Type of the Radio
            "
        ::= { wlsxWlanRadioEntry 2 }

	wlanAPRadioChannel OBJECT-TYPE
         SYNTAX       Integer32
         MAX-ACCESS   read-only
         STATUS       current
         DESCRIPTION
            "
			The channel the radio is currently operating on.
            "
        ::= { wlsxWlanRadioEntry 3 }

	wlanAPRadioTransmitPower OBJECT-TYPE
         SYNTAX       Integer32
         MAX-ACCESS   read-only
         STATUS       current
         DESCRIPTION
            "
			The current power level of the radio. (Transmitted as txpwr*2)
            "
        ::= { wlsxWlanRadioEntry 4 }

	wlanAPRadioMode OBJECT-TYPE
         SYNTAX       ArubaAccessPointMode
         MAX-ACCESS   read-only
         STATUS       current
         DESCRIPTION
            "
			The Mode in which the radio is operating.
            "
        ::= { wlsxWlanRadioEntry 5 }

	wlanAPRadioUtilization OBJECT-TYPE
         SYNTAX       Integer32
         MAX-ACCESS   read-only
         STATUS       current
         DESCRIPTION
            "
			The Utilization of the radio as a percentage of the total capacity.
			"
        ::= { wlsxWlanRadioEntry 6 }


	wlanAPRadioNumAssociatedClients OBJECT-TYPE
         SYNTAX       Integer32
         MAX-ACCESS   read-only
         STATUS       current
         DESCRIPTION
            "
			The number of Clients associated to this radio.
            "
        ::= { wlsxWlanRadioEntry 7 }


	wlanAPRadioNumMonitoredClients OBJECT-TYPE
         SYNTAX       Integer32
         MAX-ACCESS   read-only
         STATUS       current
         DESCRIPTION
            "
			The number of Clients this Radio is monitoring.
            "
        ::= { wlsxWlanRadioEntry 8 }


	wlanAPRadioNumActiveBSSIDs OBJECT-TYPE
         SYNTAX       Integer32
         MAX-ACCESS   read-only
         STATUS       current
         DESCRIPTION
            "
			The number of active BSSIDs on this Radio.
            "
        ::= { wlsxWlanRadioEntry 9 }


	wlanAPRadioNumMonitoredBSSIDs OBJECT-TYPE
         SYNTAX       Integer32
         MAX-ACCESS   read-only
         STATUS       current
         DESCRIPTION
            "
			The number of AP BSSIDs this radio is monitoring.
            "
        ::= { wlsxWlanRadioEntry 10 }

	wlanAPRadioBearing OBJECT-TYPE
         SYNTAX       DisplayString
         MAX-ACCESS   read-write
         STATUS       current
         DESCRIPTION
            "
            Antenna Bearing in degrees from True North.
            Unsigned floating-point value. Range: 0-360.
            "
        ::= { wlsxWlanRadioEntry 11 }

	wlanAPRadioTiltAngle OBJECT-TYPE
         SYNTAX       DisplayString
         MAX-ACCESS   read-write
         STATUS       current
         DESCRIPTION
            "
            Tilt angle of antenna in degrees. -ve for downtilt,
            +ve for uptilt. Signed floating-point value. Range: -90 to +90.
            "
        ::= { wlsxWlanRadioEntry 12 }

	wlanAPRadioHTMode OBJECT-TYPE
         SYNTAX       ArubaHTMode
         MAX-ACCESS   read-only
         STATUS       current
         DESCRIPTION
            "
            The HT mode of the radio, if any.
            "
        ::= { wlsxWlanRadioEntry 13 }

	wlanAPRadioHTExtChannel OBJECT-TYPE
         SYNTAX       ArubaHTExtChannel
         MAX-ACCESS   read-only
         STATUS       current
         DESCRIPTION
            "
            Indicates the offset of the extension channel, if any. Will return secondary channel
            number in 80+80 MHz mode.
            "
        ::= { wlsxWlanRadioEntry 14 }

	wlanAPRadioHTChannel OBJECT-TYPE
         SYNTAX       DisplayString
         MAX-ACCESS   read-write
         STATUS       current
         DESCRIPTION
            "
            A display string indicating the current channel.  If wlanAPRadioHTExtChannel
            is set to 'above' or 'below', then the channel number will be appended
			with '+' or '-' respectively.
            "
        ::= { wlsxWlanRadioEntry 15 }

	wlanAPRadioAPName OBJECT-TYPE
         SYNTAX       DisplayString
         MAX-ACCESS   read-write
         STATUS       current
         DESCRIPTION
            "Name of the AP the radio belongs to"
        ::= { wlsxWlanRadioEntry 16 }

-- Local Access Point Table.

   wlsxWlanAPBssidTable  OBJECT-TYPE 
	  SYNTAX       SEQUENCE OF WlanAPBssidEntry 
	  MAX-ACCESS   not-accessible		
      STATUS       current 
      DESCRIPTION 
	  	"
			This table lists all the BSSIDs active on this controller. 
		"
      ::= { wlsxWlanAccessPointInfoGroup 7 } 

   wlsxWlanAPBssidEntry OBJECT-TYPE 
	  SYNTAX       WlanAPBssidEntry 
	  MAX-ACCESS   not-accessible		
      STATUS       current 
      DESCRIPTION 
             "BSSID Entry"
	  INDEX {wlanAPMacAddress, wlanAPRadioNumber, wlanAPBSSID}
      ::= { wlsxWlanAPBssidTable 1 } 

   WlanAPBssidEntry ::=
     SEQUENCE {
         wlanAPBSSID						MacAddress,
		 wlanAPESSID						DisplayString,
		 wlanAPBssidSlot					Unsigned32,
		 wlanAPBssidPort					Unsigned32,
		 wlanAPBssidPhyType					ArubaPhyType,
		 wlanAPBssidRogueType				ArubaRogueApType,
		 wlanAPBssidMode					INTEGER,
		 wlanAPBssidChannel					INTEGER,
		 wlanAPBssidUpTime					TimeTicks,
		 wlanAPBssidInactiveTime			TimeTicks,
		 wlanAPBssidLoadBalancing			TruthValue,
		 wlanAPBssidNumAssociatedStations	Unsigned32,
		 wlanAPBssidAPMacAddress			MacAddress,
		 wlanAPBssidPhyNumber				Integer32,
		 wlanAPBssidHTMode					ArubaHTMode,
		 wlanAPBssidHTExtChannel			ArubaHTExtChannel,
         wlanAPBssidHTChannel               DisplayString,
         wlanAPBssidSnr                     Integer32
   }

   	wlanAPBSSID OBJECT-TYPE
         SYNTAX       MacAddress
         MAX-ACCESS   not-accessible
         STATUS       current
         DESCRIPTION
            "
			The MAC address of the Access Point.
            "
        ::= { wlsxWlanAPBssidEntry 1 }

   	wlanAPESSID OBJECT-TYPE
         SYNTAX       DisplayString(SIZE(0..64))
         MAX-ACCESS   read-only
         STATUS       current
         DESCRIPTION
            "
			ESSID this BSSID is advertising.
            "
        ::= { wlsxWlanAPBssidEntry 2 }

   	wlanAPBssidSlot OBJECT-TYPE
         SYNTAX       Unsigned32
         MAX-ACCESS   read-only
         STATUS       current
         DESCRIPTION
            "
			Slot to which the Access Point is connected.
            "
        ::= { wlsxWlanAPBssidEntry 3 }

   	wlanAPBssidPort OBJECT-TYPE
         SYNTAX       Unsigned32
         MAX-ACCESS   read-only
         STATUS       current
         DESCRIPTION
            "
			Port to which the Access Point is connected.
            "
        ::= { wlsxWlanAPBssidEntry 4 }

   	wlanAPBssidPhyType OBJECT-TYPE
         SYNTAX       ArubaPhyType
         MAX-ACCESS   read-only
         STATUS       current
         DESCRIPTION
            "
			Physical Layer Protocol support of the AP.
            "
        ::= { wlsxWlanAPBssidEntry 5 }

   	wlanAPBssidRogueType OBJECT-TYPE
         SYNTAX       ArubaRogueApType
         MAX-ACCESS   read-only
         STATUS       current
         DESCRIPTION
            "
			The type of the Rogue.
			"
        ::= { wlsxWlanAPBssidEntry 6 }

   	wlanAPBssidMode OBJECT-TYPE
         SYNTAX       INTEGER{
						ap(1),
						am(2),
						mpp(3),
						mp(4)
					  }
         MAX-ACCESS   read-only
         STATUS       current
         DESCRIPTION
            "
			Indicates whether the Access point is an Air Monitor or regular AP
			or Mesh Portal or Mesh Point.
            "
        ::= { wlsxWlanAPBssidEntry 7 }

   	wlanAPBssidChannel OBJECT-TYPE
         SYNTAX       INTEGER(1..165)
         MAX-ACCESS   read-only
         STATUS       current
         DESCRIPTION
            "
			The current operating channel.
            "
        ::= { wlsxWlanAPBssidEntry 8 }

   	wlanAPBssidUpTime OBJECT-TYPE
         SYNTAX       TimeTicks
         MAX-ACCESS   read-only
         STATUS       current
         DESCRIPTION
            "
			Time (in hundredths of seconds) since the tunnel was created 
			 between the access point and controller 
            "
        ::= { wlsxWlanAPBssidEntry 9 }

   	wlanAPBssidInactiveTime OBJECT-TYPE
         SYNTAX       TimeTicks
         MAX-ACCESS   read-only
         STATUS       current
         DESCRIPTION
            "
			Time (in hundredths of seconds) since any activity took place on
			 the BSSID.
            "
        ::= { wlsxWlanAPBssidEntry 10 }

   	wlanAPBssidLoadBalancing OBJECT-TYPE
         SYNTAX       TruthValue
         MAX-ACCESS   read-only
         STATUS       current
         DESCRIPTION
            "
			Indicates whether load balancing is enabled or not.
            "
        ::= { wlsxWlanAPBssidEntry 11 }

   	wlanAPBssidNumAssociatedStations OBJECT-TYPE
         SYNTAX       Unsigned32
         MAX-ACCESS   read-only
         STATUS       current
         DESCRIPTION
            "
			Indicates the number of stations associated to this BSSID.
            "
        ::= { wlsxWlanAPBssidEntry 12 }

	
   	wlanAPBssidAPMacAddress OBJECT-TYPE
         SYNTAX       MacAddress
         MAX-ACCESS   read-only
         STATUS       current
         DESCRIPTION
            "
			Indicates the Access Point to which this BSSID belongs.
            "
        ::= { wlsxWlanAPBssidEntry 13 }

   	wlanAPBssidPhyNumber OBJECT-TYPE
         SYNTAX       Integer32
         MAX-ACCESS   read-only
         STATUS       current
         DESCRIPTION
            "
			Indicates the radio number to which this BSSID belongs.
            "
        ::= { wlsxWlanAPBssidEntry 14 }

   	wlanAPBssidHTMode OBJECT-TYPE
         SYNTAX       ArubaHTMode
         MAX-ACCESS   read-only
         STATUS       current
         DESCRIPTION
            "
			Indicates the HT mode of this BSSID, if any.
            "
        ::= { wlsxWlanAPBssidEntry 15 }

   	wlanAPBssidHTExtChannel OBJECT-TYPE
         SYNTAX       ArubaHTExtChannel
         MAX-ACCESS   read-only
         STATUS       current
         DESCRIPTION
            "
            Indicates the offset of the 40MHz extension channel, if any.
            "
        ::= { wlsxWlanAPBssidEntry 16 }

   	wlanAPBssidHTChannel OBJECT-TYPE
         SYNTAX       DisplayString
         MAX-ACCESS   read-only
         STATUS       current
         DESCRIPTION
            "
            A display string indicating the current channel.  If wlanAPBssidHTExtChannel
            is set to 'above' or 'below', then the channel number will be appended
			with '+' or '-' respectively.
            "
        ::= { wlsxWlanAPBssidEntry 17 }

        wlanAPBssidSnr OBJECT-TYPE
         SYNTAX       Integer32
         MAX-ACCESS   read-only
         STATUS       current
         DESCRIPTION
            "
                        Indicates the Signal Noise Ratio of this BSSID.
            "
        ::= { wlsxWlanAPBssidEntry 18 }

-- ESSID Table

   wlsxWlanESSIDTable  OBJECT-TYPE 
	  SYNTAX       SEQUENCE OF WlanESSIDEntry 
	  MAX-ACCESS   not-accessible		
      STATUS       current 
      DESCRIPTION 
	  	"
			This Table lists all the ESSIDs advertised by this controller. 
		"
      ::= { wlsxWlanAccessPointInfoGroup 8 } 

   wlsxWlanESSIDEntry OBJECT-TYPE 
	  SYNTAX       WlanESSIDEntry 
	  MAX-ACCESS   not-accessible		
      STATUS       current 
      DESCRIPTION 
             "ESSID Entry"
	  INDEX {wlanESSID}
      ::= { wlsxWlanESSIDTable 1 } 

   WlanESSIDEntry ::=
     SEQUENCE {
		 wlanESSID						DisplayString,
		 wlanESSIDNumStations			Unsigned32,
		 wlanESSIDNumAccessPointsUp		Unsigned32,
		 wlanESSIDNumAccessPointsDown	Unsigned32,
		 wlanESSIDEncryptionType		ArubaEncryptionMethods
   }

   	wlanESSID OBJECT-TYPE
         SYNTAX       DisplayString(SIZE(0..64))
         MAX-ACCESS   not-accessible
         STATUS       current
         DESCRIPTION
            "
			The ESSID being advertised.
            "
        ::= { wlsxWlanESSIDEntry 1 }

   	wlanESSIDNumStations OBJECT-TYPE
         SYNTAX       Unsigned32
         MAX-ACCESS   read-only
         STATUS       current
         DESCRIPTION
            "
			The number of stations connected to this ESSID.
            "
        ::= { wlsxWlanESSIDEntry 2 }

   	wlanESSIDNumAccessPointsUp OBJECT-TYPE
         SYNTAX       Unsigned32
         MAX-ACCESS   read-only
         STATUS       current
         DESCRIPTION
            "
			The number of APs currently advertising this ESSID.
            "
        ::= { wlsxWlanESSIDEntry 3 }

   	wlanESSIDNumAccessPointsDown OBJECT-TYPE
         SYNTAX       Unsigned32
         MAX-ACCESS   read-only
         STATUS       current
         DESCRIPTION
            "
			The number of APs configured to advertise this ESSID that
			 are not currently operational.
            "
        ::= { wlsxWlanESSIDEntry 4 }

   	wlanESSIDEncryptionType OBJECT-TYPE
        SYNTAX      ArubaEncryptionMethods

         MAX-ACCESS   read-only
         STATUS       current
         DESCRIPTION
            "
			The encryption methods supported on this ESSID.
            "
        ::= { wlsxWlanESSIDEntry 5 }

-- ESSID Vlan Pool Table

   wlsxWlanESSIDVlanPoolTable  OBJECT-TYPE 
	  SYNTAX       SEQUENCE OF WlanESSIDVlanPoolEntry 
	  MAX-ACCESS   not-accessible		
      STATUS       current 
      DESCRIPTION 
	  	"
			This Table lists all the VLANs associated with this ESSID. 
		"
      ::= { wlsxWlanAccessPointInfoGroup 9 } 

   wlsxWlanESSIDVlanPoolEntry OBJECT-TYPE 
	  SYNTAX       WlanESSIDVlanPoolEntry 
	  MAX-ACCESS   not-accessible		
      STATUS       current 
      DESCRIPTION 
             "ESSID Vlan Pool Entry"
	  INDEX {wlanESSID, wlanESSIDVlanId}
      ::= { wlsxWlanESSIDVlanPoolTable 1 } 

   WlanESSIDVlanPoolEntry ::=
     SEQUENCE {
		 wlanESSIDVlanId				Unsigned32,
		 wlanESSIDVlanPoolStatus			RowStatus
     }

   	wlanESSIDVlanId OBJECT-TYPE
         SYNTAX       Unsigned32
         MAX-ACCESS   not-accessible
         STATUS       current
         DESCRIPTION
            "
			VLAN which is part of the VLAN pool for this ESSID.
            "
        ::= { wlsxWlanESSIDVlanPoolEntry 1 }

   	wlanESSIDVlanPoolStatus OBJECT-TYPE
         SYNTAX       RowStatus
         MAX-ACCESS   read-create
         STATUS       current
         DESCRIPTION
            "
				Row status object used to indicate the status of the row.
            "
        ::= { wlsxWlanESSIDVlanPoolEntry 2 }

--Station Info Group contains the State information for the stations.

--Station Table contains all the station associated with an AP.

   wlsxWlanStationTable  OBJECT-TYPE 
	  SYNTAX       SEQUENCE OF WlanStationEntry 
	  MAX-ACCESS   not-accessible		
      STATUS       current 
      DESCRIPTION 
	  	"
			This Table lists all the wireless stations associated with the 
			Access points connected to this controller. 
		"
	
      ::= { wlsxWlanStationInfoGroup 1} 

   wlsxWlanStationEntry OBJECT-TYPE 
	  SYNTAX       WlanStationEntry 
	  MAX-ACCESS   not-accessible		
      STATUS       current 
      DESCRIPTION 
             "Station Entry"
	  INDEX {wlanStaPhyAddress}
      ::= { wlsxWlanStationTable 1 } 

   WlanStationEntry ::=
     SEQUENCE {
         wlanStaPhyAddress				MacAddress,
         wlanStaApBssid					MacAddress,
		 wlanStaPhyType					ArubaPhyType,
		 wlanStaIsAuthenticated			TruthValue,
		 wlanStaIsAssociated			TruthValue,
		 wlanStaChannel					INTEGER,
		 wlanStaVlanId					ArubaVlanValidRange,
		 wlanStaVOIPState				TruthValue,
		 wlanStaVOIPProtocol			ArubaVoipProtocolType,
		 wlanStaTransmitRate			Unsigned32,
		 wlanStaAssociationID			Unsigned32,
		 wlanStaAccessPointESSID		DisplayString,
		 wlanStaPhyNumber				Integer32,
		 wlanStaRSSI					Integer32,
		 wlanStaUpTime					TimeTicks,
		 wlanStaHTMode					ArubaHTMode,
		 wlanStaTransmitRateCode		Unsigned32
   }

   	wlanStaPhyAddress OBJECT-TYPE
         SYNTAX       MacAddress
         MAX-ACCESS   not-accessible
         STATUS       current
         DESCRIPTION
            "
			The Physical Address of the Station.
            "
        ::= { wlsxWlanStationEntry 1 }

   	wlanStaApBssid OBJECT-TYPE
         SYNTAX       MacAddress
         MAX-ACCESS   not-accessible
         STATUS       current
         DESCRIPTION
            "
			The Access point to which this station last associated to.
            "
        ::= { wlsxWlanStationEntry 2 }

	wlanStaPhyType OBJECT-TYPE
         SYNTAX       ArubaPhyType
         MAX-ACCESS   read-only
         STATUS       current
         DESCRIPTION
            "
			Type of the Station.
            "
        ::= { wlsxWlanStationEntry 3 }

	wlanStaIsAuthenticated OBJECT-TYPE
         SYNTAX       TruthValue
         MAX-ACCESS   read-only
         STATUS       current
         DESCRIPTION
            "
            Indicates whether the station is authenticated.
            "
        ::= { wlsxWlanStationEntry 4 }

	wlanStaIsAssociated OBJECT-TYPE
         SYNTAX       TruthValue
         MAX-ACCESS   read-only
         STATUS       current
         DESCRIPTION
            "
            Indicates whether the station is associated.
            "
        ::= { wlsxWlanStationEntry 5 }

	wlanStaChannel OBJECT-TYPE
         SYNTAX       INTEGER(1..165)
         MAX-ACCESS   read-only
         STATUS       current
         DESCRIPTION
            "
			Channel on which the station is associated.
            "
        ::= { wlsxWlanStationEntry 6 }

	wlanStaVlanId OBJECT-TYPE
         SYNTAX       ArubaVlanValidRange
         MAX-ACCESS   read-only
         STATUS       current
         DESCRIPTION
            "
			VLAN in which the station is present.
            "
        ::= { wlsxWlanStationEntry 7 }

	wlanStaVOIPState OBJECT-TYPE
         SYNTAX       TruthValue
         MAX-ACCESS   read-only
         STATUS       current
         DESCRIPTION
            "
			The State of VoIP for this station.
            "
        ::= { wlsxWlanStationEntry 8 }

	wlanStaVOIPProtocol OBJECT-TYPE
         SYNTAX       ArubaVoipProtocolType
         MAX-ACCESS   read-only
         STATUS       current
         DESCRIPTION
            "
			If VoIP is enabled, the type of the protocol supported.
            "
        ::= { wlsxWlanStationEntry 9 }

	wlanStaTransmitRate OBJECT-TYPE
         SYNTAX       Unsigned32
         MAX-ACCESS   read-only
         STATUS       current
         DESCRIPTION
            "
			Transmit rate with which the Station is associated with this system.
            "
        ::= { wlsxWlanStationEntry 10 }

	wlanStaAssociationID OBJECT-TYPE
         SYNTAX       Unsigned32
         MAX-ACCESS   read-only
         STATUS       current
         DESCRIPTION
            "
			AID with which the Station is associated with this system.
            "
        ::= { wlsxWlanStationEntry 11 }

	wlanStaAccessPointESSID OBJECT-TYPE
         SYNTAX       DisplayString(SIZE(0..64))
         MAX-ACCESS   read-only
         STATUS       current
         DESCRIPTION
            "
			ESSID of the Access point
            "
        ::= { wlsxWlanStationEntry 12 }

	wlanStaPhyNumber OBJECT-TYPE
         SYNTAX       Integer32
         MAX-ACCESS   read-only
         STATUS       current
         DESCRIPTION
            "
			Radio PHY number to which the station is associated
            "
        ::= { wlsxWlanStationEntry 13 }

	wlanStaRSSI OBJECT-TYPE
         SYNTAX       Integer32
         MAX-ACCESS   read-only
         STATUS       current
         DESCRIPTION
            "
			Signal to Noise ratio for the station.
            "
        ::= { wlsxWlanStationEntry 14 }


	wlanStaUpTime OBJECT-TYPE
         SYNTAX       TimeTicks
         MAX-ACCESS   read-only
         STATUS       current
         DESCRIPTION
            "
			Time since the station associated to the current BSSID. 
            "
        ::= { wlsxWlanStationEntry 15 }

	wlanStaHTMode OBJECT-TYPE
         SYNTAX       ArubaHTMode
         MAX-ACCESS   read-only
         STATUS       current
         DESCRIPTION
            "
			The HT status of the station.
            "
        ::= { wlsxWlanStationEntry 16 }

    wlanStaTransmitRateCode OBJECT-TYPE
         SYNTAX       Unsigned32
         MAX-ACCESS   read-only
         STATUS       current
         DESCRIPTION
            "
            Transmit rate code with which the Station is associated with this system, unit is mbps.
            "
        ::= { wlsxWlanStationEntry 17 }

--Station Association Failure Table contains all the Stations that failed to 
--associate an ap.

   wlsxWlanStaAssociationFailureTable  OBJECT-TYPE 
	  SYNTAX       SEQUENCE OF WlanStaAssociationFailureEntry 
	  MAX-ACCESS   not-accessible		
      STATUS       current 
      DESCRIPTION 
	  	"
			This Table lists all the stations and the BSSID's to which they 
			failed to associate. Once a station successfully associates, 
			association failure entries are not reported for that station.
		"
	
      ::= { wlsxWlanStationInfoGroup 2} 

   wlsxWlanStaAssociationFailureEntry OBJECT-TYPE 
	  SYNTAX       WlanStaAssociationFailureEntry 
	  MAX-ACCESS   not-accessible		
      STATUS       current 
      DESCRIPTION 
             "Station Association Failure Entry"
	  INDEX {wlanStaPhyAddress, wlanAPBSSID}
      ::= { wlsxWlanStaAssociationFailureTable 1 } 

   WlanStaAssociationFailureEntry ::=
     SEQUENCE {
		 wlanStaAssocFailureApName			DisplayString,
		 wlanStaAssocFailureApEssid		DisplayString,
		 wlanStaAssocFailurePhyNum			Integer32,
		 wlanStaAssocFailurePhyType		ArubaPhyType,
		 wlanStaAssocFailureElapsedTime	TimeTicks,
		 wlanStaAssocFailureReason			DisplayString
   }

   	wlanStaAssocFailureApName OBJECT-TYPE
         SYNTAX       DisplayString(SIZE(0..64))
         MAX-ACCESS   read-only
         STATUS       current
         DESCRIPTION
            "
			Name of the Access Point to which this station tried to associate.
            "
        ::= { wlsxWlanStaAssociationFailureEntry 1 }

   	wlanStaAssocFailureApEssid OBJECT-TYPE
         SYNTAX       DisplayString(SIZE(0..64))
         MAX-ACCESS   read-only
         STATUS       current
         DESCRIPTION
            "
			ESSID to which the station association failed.
            "
        ::= { wlsxWlanStaAssociationFailureEntry 2 }

   	wlanStaAssocFailurePhyNum OBJECT-TYPE
         SYNTAX       Integer32
         MAX-ACCESS   read-only
         STATUS       current
         DESCRIPTION
            "
			Radio PHY number to which the station tried to associate.
            "
        ::= { wlsxWlanStaAssociationFailureEntry 3 }

   	wlanStaAssocFailurePhyType OBJECT-TYPE
         SYNTAX       ArubaPhyType
         MAX-ACCESS   read-only
         STATUS       current
         DESCRIPTION
            "
			Radio PHY Type of the Station.
            "
        ::= { wlsxWlanStaAssociationFailureEntry 4 }

   	wlanStaAssocFailureElapsedTime OBJECT-TYPE
         SYNTAX       TimeTicks
         MAX-ACCESS   read-only
         STATUS       current
         DESCRIPTION
            "
			Elapsed time in timeticks after the station's failure to associate.
            "
        ::= { wlsxWlanStaAssociationFailureEntry 5 }

   	wlanStaAssocFailureReason OBJECT-TYPE
         SYNTAX       DisplayString(SIZE(0..80))
         MAX-ACCESS   read-only
         STATUS       current
         DESCRIPTION
            "
			Reason for the Station association failure
            "
        ::= { wlsxWlanStaAssociationFailureEntry 6 }

-- Stats group contains tables for station statistics, BSSID statistics and
-- AP statistics.

   wlsxWlanAPStatsTable  OBJECT-TYPE 
	  SYNTAX       SEQUENCE OF WlanAPStatsEntry 
	  MAX-ACCESS   not-accessible		
      STATUS       current 
      DESCRIPTION 
	  	"
			This Table lists the statistics of all the Access Points connected 
			to the controller. 
		"
      ::= { wlsxWlanAccessPointStatsGroup 1 } 

   wlsxWlanAPStatsEntry OBJECT-TYPE 
	  SYNTAX       WlanAPStatsEntry 
	  MAX-ACCESS   not-accessible		
      STATUS       current 
      DESCRIPTION 
             "Access Point Stats entry"
	  INDEX {wlanAPMacAddress, wlanAPRadioNumber, wlanAPBSSID}
      ::= { wlsxWlanAPStatsTable 1 } 

   WlanAPStatsEntry ::=
     SEQUENCE {
		 wlanAPCurrentChannel		    Unsigned32,
		 wlanAPNumClients		    	Integer32,
		 wlanAPTxPkts					Counter32,
		 wlanAPTxBytes					Counter32,
		 wlanAPRxPkts					Counter32,
		 wlanAPRxBytes					Counter32,
		 wlanAPTxDeauthentications		Counter32,
		 wlanAPRxDeauthentications		Counter32,
		 wlanAPChannelThroughput		Integer32,
		 wlanAPFrameRetryRate			Integer32,
		 wlanAPFrameLowSpeedRate		Integer32,
		 wlanAPFrameNonUnicastRate		Integer32,
		 wlanAPFrameFragmentationRate	Integer32,
		 wlanAPFrameBandwidthRate		Integer32,
		 wlanAPFrameRetryErrorRate		Integer32,
		 wlanAPChannelErrorRate			Integer32,
		 wlanAPFrameReceiveErrorRate	Integer32,
		 wlanAPRxDataPkts				Counter32,
		 wlanAPRxDataBytes				Counter32,
		 wlanAPTxDataPkts				Counter32,
		 wlanAPTxDataBytes				Counter32,
		 wlanAPRxDataPkts64				Counter64,
		 wlanAPRxDataBytes64			Counter64,
		 wlanAPTxDataPkts64				Counter64,
         wlanAPTxDataBytes64            Counter64,
         wlanAPWiredRxErrorPkts         Counter32,
         wlanAPRxErrorPkts              Counter32
   }

	wlanAPCurrentChannel OBJECT-TYPE
         SYNTAX       Unsigned32
         MAX-ACCESS   read-only
         STATUS       current
         DESCRIPTION
            "
			The channel the AP is currently using.
            "
        ::= { wlsxWlanAPStatsEntry 1 }

	wlanAPNumClients OBJECT-TYPE
         SYNTAX       Integer32
         MAX-ACCESS   read-only
         STATUS       current
         DESCRIPTION
            "
			The number of clients associated to this BSSID.
            "
        ::= { wlsxWlanAPStatsEntry 2 }

	wlanAPTxPkts OBJECT-TYPE
         SYNTAX       Counter32
         MAX-ACCESS   read-only
         STATUS       current
         DESCRIPTION
            "
			The number of packets transmitted on this BSSID.
            "
        ::= { wlsxWlanAPStatsEntry 3 }

	wlanAPTxBytes OBJECT-TYPE
         SYNTAX       Counter32
         MAX-ACCESS   read-only
         STATUS       current
         DESCRIPTION
            "
			The number of bytes transmitted on this BSSID.
            "
        ::= { wlsxWlanAPStatsEntry 4 }

	wlanAPRxPkts OBJECT-TYPE
         SYNTAX       Counter32
         MAX-ACCESS   read-only
         STATUS       current
         DESCRIPTION
            "
			The number of packets received on this BSSID.
            "
        ::= { wlsxWlanAPStatsEntry 5 }

	wlanAPRxBytes OBJECT-TYPE
         SYNTAX       Counter32
         MAX-ACCESS   read-only
         STATUS       current
         DESCRIPTION
            "
			The number of bytes received on this BSSID.
            "
        ::= { wlsxWlanAPStatsEntry 6 }

	wlanAPTxDeauthentications OBJECT-TYPE
         SYNTAX       Counter32
         MAX-ACCESS   read-only
         STATUS       current
         DESCRIPTION
            "
			The number of deauthentications transmitted on this BSSID.
            "
        ::= { wlsxWlanAPStatsEntry 7 }

	wlanAPRxDeauthentications OBJECT-TYPE
         SYNTAX       Counter32
         MAX-ACCESS   read-only
         STATUS       current
         DESCRIPTION
            "
			The number of deauthentications received on this BSSID.
            "
        ::= { wlsxWlanAPStatsEntry 8 }

	wlanAPChannelThroughput OBJECT-TYPE
         SYNTAX       Integer32
         MAX-ACCESS   read-only
         STATUS       current
         DESCRIPTION
            "
			The throughput achieved on this channel.
            "
        ::= { wlsxWlanAPStatsEntry 9 }

	wlanAPFrameRetryRate OBJECT-TYPE
         SYNTAX       Integer32
         MAX-ACCESS   read-only
         STATUS       current
         DESCRIPTION
            "
			 The number of retry 
			 packets as a percentage of the total packets
			 transmitted and received by this BSSID.
            "
        ::= { wlsxWlanAPStatsEntry 10 }

	wlanAPFrameLowSpeedRate OBJECT-TYPE
         SYNTAX       Integer32
         MAX-ACCESS   read-only
         STATUS       current
         DESCRIPTION
            "
			 The number of low data rate (<= 18Mbps for A/G bands and <=2Mbps
			 for B band) packets as a percentage of the total packets
			 transmitted and received by this BSSID
            "
        ::= { wlsxWlanAPStatsEntry 11 }

	wlanAPFrameNonUnicastRate OBJECT-TYPE
         SYNTAX       Integer32
         MAX-ACCESS   read-only
         STATUS       current
         DESCRIPTION
            "
			 The number of broadcast and multicast
			 packets as a percentage of the total packets
			 transmitted on this BSSIDchannel.
            "
        ::= { wlsxWlanAPStatsEntry 12 }

	wlanAPFrameFragmentationRate OBJECT-TYPE
         SYNTAX       Integer32
         MAX-ACCESS   read-only
         STATUS       current
         DESCRIPTION
            "
			 The number of fragments
			 as a percentage of the total packets
			 transmitted by this BSSID.
            "
        ::= { wlsxWlanAPStatsEntry 13 }

	wlanAPFrameBandwidthRate OBJECT-TYPE
         SYNTAX       Integer32
         MAX-ACCESS   read-only
         STATUS       current
         DESCRIPTION
            "
			 The bandwidth of this BSSID in Kbps.
            "
        ::= { wlsxWlanAPStatsEntry 14 }

	wlanAPFrameRetryErrorRate OBJECT-TYPE
         SYNTAX       Integer32
         MAX-ACCESS   read-only
         STATUS       current
         DESCRIPTION
            "
			 The number of error packets
			 as a percentage of the total packets
			 received on this BSSID.
            "
        ::= { wlsxWlanAPStatsEntry 15 }
	
	wlanAPChannelErrorRate OBJECT-TYPE
         SYNTAX       Integer32
         MAX-ACCESS   read-only
         STATUS       current
         DESCRIPTION
            "
			The number of error packets 
			 as a percentage of the total packets received
			on the current channel.
            "
        ::= { wlsxWlanAPStatsEntry 16 }

	wlanAPFrameReceiveErrorRate OBJECT-TYPE
         SYNTAX       Integer32
         MAX-ACCESS   read-only
         STATUS       current
         DESCRIPTION
            "
			 The number of error packets
			 as a percentage of the total packets
			 received on this BSSID.
            "
        ::= { wlsxWlanAPStatsEntry 17 }

	wlanAPRxDataPkts OBJECT-TYPE
         SYNTAX       Counter32
         MAX-ACCESS   read-only
         STATUS       deprecated
         DESCRIPTION
            "
			The number of packets received on this BSSID.
            "
        ::= { wlsxWlanAPStatsEntry 18 }

	wlanAPRxDataBytes OBJECT-TYPE
         SYNTAX       Counter32
         MAX-ACCESS   read-only
         STATUS       deprecated
         DESCRIPTION
            "
			The number of bytes received on this BSSID.
            "
        ::= { wlsxWlanAPStatsEntry 19 }
	
	wlanAPTxDataPkts OBJECT-TYPE
         SYNTAX       Counter32
         MAX-ACCESS   read-only
         STATUS       deprecated
         DESCRIPTION
            "
			The number of packets transmitted on this BSSID.
            "
        ::= { wlsxWlanAPStatsEntry 20 }

	wlanAPTxDataBytes OBJECT-TYPE
         SYNTAX       Counter32
         MAX-ACCESS   read-only
         STATUS       deprecated
         DESCRIPTION
            "
			The number of bytes transmitted on this BSSID.
            "
        ::= { wlsxWlanAPStatsEntry 21 }

	wlanAPRxDataPkts64 OBJECT-TYPE
         SYNTAX       Counter64
         MAX-ACCESS   read-only
         STATUS       current
         DESCRIPTION
            "
			The number of packets received on this BSSID.
            "
        ::= { wlsxWlanAPStatsEntry 22 }

	wlanAPRxDataBytes64 OBJECT-TYPE
         SYNTAX       Counter64
         MAX-ACCESS   read-only
         STATUS       current
         DESCRIPTION
            "
			The number of bytes received on this BSSID.
            "
        ::= { wlsxWlanAPStatsEntry 23 }
	
	wlanAPTxDataPkts64 OBJECT-TYPE
         SYNTAX       Counter64
         MAX-ACCESS   read-only
         STATUS       current
         DESCRIPTION
            "
			The number of packets transmitted on this BSSID.
            "
        ::= { wlsxWlanAPStatsEntry 24 }

	wlanAPTxDataBytes64 OBJECT-TYPE
         SYNTAX       Counter64
         MAX-ACCESS   read-only
         STATUS       current
         DESCRIPTION
            "
			The number of bytes transmitted on this BSSID.
            "
        ::= { wlsxWlanAPStatsEntry 25 }

    wlanAPWiredRxErrorPkts OBJECT-TYPE
         SYNTAX       Counter32
         MAX-ACCESS   read-only
         STATUS       current
         DESCRIPTION
            "
            The number of error packets received from the controller on this BSSID.
            "
        ::= { wlsxWlanAPStatsEntry 26 }

    wlanAPRxErrorPkts OBJECT-TYPE
         SYNTAX       Counter32
         MAX-ACCESS   read-only
         STATUS       current
         DESCRIPTION
            "
            The number of error packets received from stations on this BSSID.
            "
        ::= { wlsxWlanAPStatsEntry 27 }

-- This table breaks down the AP statistics observed into different
-- rate categories.

   wlsxWlanAPRateStatsTable  OBJECT-TYPE 
	  SYNTAX       SEQUENCE OF WlsxWlanAPRateStatsEntry 
	  MAX-ACCESS   not-accessible		
      STATUS       current 
      DESCRIPTION 
	  	"
		This table contains all the AP Packet and Byte Counts
		 but represented in terms of rate categories.
		"
	
      ::= { wlsxWlanAccessPointStatsGroup 2 } 

     wlsxWlanAPRateStatsEntry OBJECT-TYPE 
	  SYNTAX       WlsxWlanAPRateStatsEntry 
	  MAX-ACCESS   not-accessible		
      STATUS       current 
      DESCRIPTION 
			 "Data rate based packet and byte count entry for an AP"
	  INDEX {wlanAPMacAddress, wlanAPRadioNumber, wlanAPBSSID}
      ::= { wlsxWlanAPRateStatsTable 1 } 
	
     WlsxWlanAPRateStatsEntry ::=
     SEQUENCE {
		 wlanAPStatsTotPktsAt1Mbps			Counter32,
		 wlanAPStatsTotBytesAt1Mbps			Counter32,
		 wlanAPStatsTotPktsAt2Mbps			Counter32,
		 wlanAPStatsTotBytesAt2Mbps			Counter32,
		 wlanAPStatsTotPktsAt5Mbps			Counter32,
		 wlanAPStatsTotBytesAt5Mbps			Counter32,
		 wlanAPStatsTotPktsAt11Mbps			Counter32,
		 wlanAPStatsTotBytesAt11Mbps		Counter32,
		 wlanAPStatsTotPktsAt6Mbps			Counter32,
		 wlanAPStatsTotBytesAt6Mbps			Counter32,
		 wlanAPStatsTotPktsAt12Mbps			Counter32,
		 wlanAPStatsTotBytesAt12Mbps		Counter32,
		 wlanAPStatsTotPktsAt18Mbps			Counter32,
		 wlanAPStatsTotBytesAt18Mbps		Counter32,
		 wlanAPStatsTotPktsAt24Mbps			Counter32,
		 wlanAPStatsTotBytesAt24Mbps		Counter32,
		 wlanAPStatsTotPktsAt36Mbps			Counter32,
		 wlanAPStatsTotBytesAt36Mbps		Counter32,
		 wlanAPStatsTotPktsAt48Mbps			Counter32,
		 wlanAPStatsTotBytesAt48Mbps		Counter32,
		 wlanAPStatsTotPktsAt54Mbps			Counter32,
		 wlanAPStatsTotBytesAt54Mbps		Counter32,
		 wlanAPStatsTotPktsAt9Mbps			Counter32,
		 wlanAPStatsTotBytesAt9Mbps		    Counter32
--		 wlanAPStatsTotPktsAtHT6dot5Mbps		Counter32,
--		 wlanAPStatsTotBytesAtHT6dot5Mbps		Counter32,
--		 wlanAPStatsTotPktsAtHT13Mbps			Counter32,
--		 wlanAPStatsTotBytesAtHT13Mbps		Counter32,
--		 wlanAPStatsTotPktsAtHT13dot5Mbps		Counter32,
--		 wlanAPStatsTotBytesAtHT13dot5Mbps	Counter32,
--		 wlanAPStatsTotPktsAtHT15Mbps			Counter32,
--		 wlanAPStatsTotBytesAtHT15Mbps		Counter32,
--		 wlanAPStatsTotPktsAtHT19dot5Mbps		Counter32,
--		 wlanAPStatsTotBytesAtHT19dot5Mbps	Counter32,
--		 wlanAPStatsTotPktsAtHT26Mbps			Counter32,
--		 wlanAPStatsTotBytesAtHT26Mbps		Counter32,
--		 wlanAPStatsTotPktsAtHT27Mbps			Counter32,
--		 wlanAPStatsTotBytesAtHT27Mbps		Counter32,
--		 wlanAPStatsTotPktsAtHT30Mbps			Counter32,
--		 wlanAPStatsTotBytesAtHT30Mbps		Counter32,
--		 wlanAPStatsTotPktsAtHT39Mbps			Counter32,
--		 wlanAPStatsTotBytesAtHT39Mbps		Counter32,
--		 wlanAPStatsTotPktsAtHT40dot5Mbps		Counter32,
--		 wlanAPStatsTotBytesAtHT40dot5Mbps	Counter32,
--		 wlanAPStatsTotPktsAtHT45Mbps			Counter32,
--		 wlanAPStatsTotBytesAtHT45Mbps		Counter32,
--		 wlanAPStatsTotPktsAtHT52Mbps			Counter32,
--		 wlanAPStatsTotBytesAtHT52Mbps		Counter32,
--		 wlanAPStatsTotPktsAtHT54Mbps			Counter32,
--		 wlanAPStatsTotBytesAtHT54Mbps		Counter32,
--		 wlanAPStatsTotPktsAtHT58dot5Mbps		Counter32,
--		 wlanAPStatsTotBytesAtHT58dot5Mbps	Counter32,
--		 wlanAPStatsTotPktsAtHT60Mbps			Counter32,
--		 wlanAPStatsTotBytesAtHT60Mbps		Counter32,
--		 wlanAPStatsTotPktsAtHT65Mbps			Counter32,
--		 wlanAPStatsTotBytesAtHT65Mbps		Counter32,
--		 wlanAPStatsTotPktsAtHT78Mbps			Counter32,
--		 wlanAPStatsTotBytesAtHT78Mbps		Counter32,
--		 wlanAPStatsTotPktsAtHT81Mbps			Counter32,
--		 wlanAPStatsTotBytesAtHT81Mbps		Counter32,
--		 wlanAPStatsTotPktsAtHT90Mbps			Counter32,
--		 wlanAPStatsTotBytesAtHT90Mbps		Counter32,
--		 wlanAPStatsTotPktsAtHT104Mbps		Counter32,
--		 wlanAPStatsTotBytesAtHT104Mbps		Counter32,
--		 wlanAPStatsTotPktsAtHT108Mbps		Counter32,
--		 wlanAPStatsTotBytesAtHT108Mbps		Counter32,
--		 wlanAPStatsTotPktsAtHT117Mbps		Counter32,
--		 wlanAPStatsTotBytesAtHT117Mbps		Counter32,
--		 wlanAPStatsTotPktsAtHT120Mbps		Counter32,
--		 wlanAPStatsTotBytesAtHT120Mbps		Counter32,
--		 wlanAPStatsTotPktsAtHT121dot5Mbps	Counter32,
--		 wlanAPStatsTotBytesAtHT121dot5Mbps	Counter32,
--		 wlanAPStatsTotPktsAtHT130Mbps		Counter32,
--		 wlanAPStatsTotBytesAtHT130Mbps		Counter32,
--		 wlanAPStatsTotPktsAtHT135Mbps		Counter32,
--		 wlanAPStatsTotBytesAtHT135Mbps		Counter32,
--		 wlanAPStatsTotPktsAtHT150Mbps		Counter32,
--		 wlanAPStatsTotBytesAtHT150Mbps		Counter32,
--		 wlanAPStatsTotPktsAtHT162Mbps		Counter32,
--		 wlanAPStatsTotBytesAtHT162Mbps		Counter32,
--		 wlanAPStatsTotPktsAtHT180Mbps		Counter32,
--		 wlanAPStatsTotBytesAtHT180Mbps		Counter32,
--		 wlanAPStatsTotPktsAtHT216Mbps		Counter32,
--		 wlanAPStatsTotBytesAtHT216Mbps		Counter32,
--		 wlanAPStatsTotPktsAtHT240Mbps		Counter32,
--		 wlanAPStatsTotBytesAtHT240Mbps		Counter32,
--		 wlanAPStatsTotPktsAtHT243Mbps		Counter32,
--		 wlanAPStatsTotBytesAtHT243Mbps		Counter32,
--		 wlanAPStatsTotPktsAtHT270Mbps		Counter32,
--		 wlanAPStatsTotBytesAtHT270Mbps		Counter32,
--		 wlanAPStatsTotPktsAtHT300Mbps		Counter32,
--		 wlanAPStatsTotBytesAtHT300Mbps		Counter32
     }

     wlanAPStatsTotPktsAt1Mbps OBJECT-TYPE
         SYNTAX       Counter32  
         MAX-ACCESS   read-only
         STATUS       current
         DESCRIPTION
            "
			 This attribute indicates the total number of packets observed
			  on this BSSID at 1Mbps rate.
            "
        ::= { wlsxWlanAPRateStatsEntry 1 }

     wlanAPStatsTotBytesAt1Mbps OBJECT-TYPE
         SYNTAX       Counter32  
         MAX-ACCESS   read-only
         STATUS       current
         DESCRIPTION
            "
			 This attribute indicates the total number of Bytes observed
			  on this BSSID at 1Mbps rate.
            "
        ::= { wlsxWlanAPRateStatsEntry 2 }

     wlanAPStatsTotPktsAt2Mbps OBJECT-TYPE
         SYNTAX       Counter32  
         MAX-ACCESS   read-only
         STATUS       current
         DESCRIPTION
            "
			 This attribute indicates the total number of packets observed
			  on this BSSID at 2Mbps rate.
            "
        ::= { wlsxWlanAPRateStatsEntry 3 }

     wlanAPStatsTotBytesAt2Mbps OBJECT-TYPE
         SYNTAX       Counter32  
         MAX-ACCESS   read-only
         STATUS       current
         DESCRIPTION
            "
			 This attribute indicates the total number of Bytes observed
			  on this BSSID at 2Mbps rate.
            "
        ::= { wlsxWlanAPRateStatsEntry 4 }

     wlanAPStatsTotPktsAt5Mbps OBJECT-TYPE
         SYNTAX       Counter32  
         MAX-ACCESS   read-only
         STATUS       current
         DESCRIPTION
            "
			 This attribute indicates the total number of packets observed
			  on this BSSID at 5Mbps rate.
            "
        ::= { wlsxWlanAPRateStatsEntry 5 }

     wlanAPStatsTotBytesAt5Mbps OBJECT-TYPE
         SYNTAX       Counter32  
         MAX-ACCESS   read-only
         STATUS       current
         DESCRIPTION
            "
			 This attribute indicates the total number of Bytes observed
			  on this BSSID at 5Mbps rate.
            "
        ::= { wlsxWlanAPRateStatsEntry 6 }

     wlanAPStatsTotPktsAt11Mbps OBJECT-TYPE
         SYNTAX       Counter32  
         MAX-ACCESS   read-only
         STATUS       current
         DESCRIPTION
            "
			 This attribute indicates the total number of packets observed
			  on this BSSID at 11Mbps rate.
            "
        ::= { wlsxWlanAPRateStatsEntry 7 }

     wlanAPStatsTotBytesAt11Mbps OBJECT-TYPE
         SYNTAX       Counter32  
         MAX-ACCESS   read-only
         STATUS       current
         DESCRIPTION
            "
			 This attribute indicates the total number of Bytes observed
			 on this BSSID at 11Mbps rate.
            "
        ::= { wlsxWlanAPRateStatsEntry 8 }

     wlanAPStatsTotPktsAt6Mbps OBJECT-TYPE
         SYNTAX       Counter32  
         MAX-ACCESS   read-only
         STATUS       current
         DESCRIPTION
            "
			 This attribute indicates the total number of packets observed
			  on this BSSID at 6Mbps rate.
            "
        ::= { wlsxWlanAPRateStatsEntry 9 }

     wlanAPStatsTotBytesAt6Mbps OBJECT-TYPE
         SYNTAX       Counter32  
         MAX-ACCESS   read-only
         STATUS       current
         DESCRIPTION
            "
			 This attribute indicates the total number of Bytes observed
			  on this BSSID at 6Mbps rate.
            "
        ::= { wlsxWlanAPRateStatsEntry 10 }

     wlanAPStatsTotPktsAt12Mbps OBJECT-TYPE
         SYNTAX       Counter32  
         MAX-ACCESS   read-only
         STATUS       current
         DESCRIPTION
            "
			 This attribute indicates the total number of packets observed
			  on this BSSID at 12Mbps rate.
            "
        ::= { wlsxWlanAPRateStatsEntry 11 }

     wlanAPStatsTotBytesAt12Mbps OBJECT-TYPE
         SYNTAX       Counter32  
         MAX-ACCESS   read-only
         STATUS       current
         DESCRIPTION
            "
			 This attribute indicates the total number of Bytes observed
			  on this BSSID at 12Mbps rate.
            "
        ::= { wlsxWlanAPRateStatsEntry 12 }

     wlanAPStatsTotPktsAt18Mbps OBJECT-TYPE
         SYNTAX       Counter32  
         MAX-ACCESS   read-only
         STATUS       current
         DESCRIPTION
            "
			 This attribute indicates the total number of packets observed
			  on this BSSID at 18Mbps rate.
            "
        ::= { wlsxWlanAPRateStatsEntry 13 }

     wlanAPStatsTotBytesAt18Mbps OBJECT-TYPE
         SYNTAX       Counter32  
         MAX-ACCESS   read-only
         STATUS       current
         DESCRIPTION
            "
			 This attribute indicates the total number of Bytes observed
			  on this BSSID at 18Mbps rate.
            "
        ::= { wlsxWlanAPRateStatsEntry 14 }

     wlanAPStatsTotPktsAt24Mbps OBJECT-TYPE
         SYNTAX       Counter32  
         MAX-ACCESS   read-only
         STATUS       current
         DESCRIPTION
            "
			 This attribute indicates the total number of packets observed
			  on this BSSID at 24Mbps rate.
            "
        ::= { wlsxWlanAPRateStatsEntry 15 }

     wlanAPStatsTotBytesAt24Mbps OBJECT-TYPE
         SYNTAX       Counter32  
         MAX-ACCESS   read-only
         STATUS       current
         DESCRIPTION
            "
			 This attribute indicates the total number of Bytes observed
			  on this BSSID at 24Mbps rate.
            "
        ::= { wlsxWlanAPRateStatsEntry 16 }

     wlanAPStatsTotPktsAt36Mbps OBJECT-TYPE
         SYNTAX       Counter32  
         MAX-ACCESS   read-only
         STATUS       current
         DESCRIPTION
            "
			 This attribute indicates the total number of packets observed
			  on this BSSID at 36Mbps rate.
            "
        ::= { wlsxWlanAPRateStatsEntry 17 }

     wlanAPStatsTotBytesAt36Mbps OBJECT-TYPE
         SYNTAX       Counter32  
         MAX-ACCESS   read-only
         STATUS       current
         DESCRIPTION
            "
			 This attribute indicates the total number of Bytes observed
			  on this BSSID at 36Mbps rate.
            "
        ::= { wlsxWlanAPRateStatsEntry 18 }

     wlanAPStatsTotPktsAt48Mbps OBJECT-TYPE
         SYNTAX       Counter32  
         MAX-ACCESS   read-only
         STATUS       current
         DESCRIPTION
            "
			 This attribute indicates the total number of packets observed
			  on this BSSID at 48Mbps rate.
            "
        ::= { wlsxWlanAPRateStatsEntry 19 }

     wlanAPStatsTotBytesAt48Mbps OBJECT-TYPE
         SYNTAX       Counter32  
         MAX-ACCESS   read-only
         STATUS       current
         DESCRIPTION
            "
			 This attribute indicates the total number of Bytes observed
			  on this BSSID at 48Mbps rate.
            "
        ::= { wlsxWlanAPRateStatsEntry 20 }

     wlanAPStatsTotPktsAt54Mbps OBJECT-TYPE
         SYNTAX       Counter32  
         MAX-ACCESS   read-only
         STATUS       current
         DESCRIPTION
            "
			 This attribute indicates the total number of packets observed
			  on this BSSID at 54Mbps rate.
            "
        ::= { wlsxWlanAPRateStatsEntry 21 }

     wlanAPStatsTotBytesAt54Mbps OBJECT-TYPE
         SYNTAX       Counter32  
         MAX-ACCESS   read-only
         STATUS       current
         DESCRIPTION
            "
			 This attribute indicates the total number of Bytes observed
		 	  on this BSSID at 54Mbps rate.
            "
        ::= { wlsxWlanAPRateStatsEntry 22 }

     wlanAPStatsTotPktsAt9Mbps OBJECT-TYPE
         SYNTAX       Counter32  
         MAX-ACCESS   read-only
         STATUS       current
         DESCRIPTION
            "
			 This attribute indicates the total number of packets observed
			  on this BSSID at 9Mbps rate.
            "
        ::= { wlsxWlanAPRateStatsEntry 23 }

     wlanAPStatsTotBytesAt9Mbps OBJECT-TYPE
         SYNTAX       Counter32  
         MAX-ACCESS   read-only
         STATUS       current
         DESCRIPTION
            "
			 This attribute indicates the total number of Bytes observed
			  on this BSSID at 9Mbps rate.
            "
        ::= { wlsxWlanAPRateStatsEntry 24 }

--	 wlanAPStatsTotPktsAtHT6dot5Mbps OBJECT-TYPE
--		 SYNTAX       Counter32  
--		 MAX-ACCESS   read-only
--		 STATUS       current
--		 DESCRIPTION
--			"
--			  This attribute indicates the total number of packets observed
--			  on this BSSID at the HT 6.5 rate.
--			"
--		::= { wlsxWlanAPRateStatsEntry 25 }
--
--	 wlanAPStatsTotBytesAtHT6dot5Mbps OBJECT-TYPE
--		 SYNTAX       Counter32  
--		 MAX-ACCESS   read-only
--		 STATUS       current
--		 DESCRIPTION
--			"
--			  This attribute indicates the total number of bytes observed
--			  on this BSSID at the HT 6.5 rate.
--			"
--		::= { wlsxWlanAPRateStatsEntry 26 }
--
--	 wlanAPStatsTotPktsAtHT13Mbps OBJECT-TYPE
--		 SYNTAX       Counter32  
--		 MAX-ACCESS   read-only
--		 STATUS       current
--		 DESCRIPTION
--			"
--			  This attribute indicates the total number of packets observed
--			  on this BSSID at the HT 13.0 rate.
--			"
--		::= { wlsxWlanAPRateStatsEntry 27 }
--
--	 wlanAPStatsTotBytesAtHT13Mbps OBJECT-TYPE
--		 SYNTAX       Counter32  
--		 MAX-ACCESS   read-only
--		 STATUS       current
--		 DESCRIPTION
--			"
--			  This attribute indicates the total number of bytes observed
--			  on this BSSID at the HT 13.0 rate.
--			"
--		::= { wlsxWlanAPRateStatsEntry 28 }
--
--	 wlanAPStatsTotPktsAtHT13dot5Mbps OBJECT-TYPE
--		 SYNTAX       Counter32  
--		 MAX-ACCESS   read-only
--		 STATUS       current
--		 DESCRIPTION
--			"
--			  This attribute indicates the total number of packets observed
--			  on this BSSID at the HT 13.5 rate.
--			"
--		::= { wlsxWlanAPRateStatsEntry 29 }
--
--	 wlanAPStatsTotBytesAtHT13dot5Mbps OBJECT-TYPE
--		 SYNTAX       Counter32  
--		 MAX-ACCESS   read-only
--		 STATUS       current
--		 DESCRIPTION
--			"
--			  This attribute indicates the total number of bytes observed
--			  on this BSSID at the HT 13.5 rate.
--			"
--		::= { wlsxWlanAPRateStatsEntry 30 }
--
--	 wlanAPStatsTotPktsAtHT15Mbps OBJECT-TYPE
--		 SYNTAX       Counter32  
--		 MAX-ACCESS   read-only
--		 STATUS       current
--		 DESCRIPTION
--			"
--			  This attribute indicates the total number of packets observed
--			  on this BSSID at the HT 15.0 rate.
--			"
--		::= { wlsxWlanAPRateStatsEntry 31 }
--
--	 wlanAPStatsTotBytesAtHT15Mbps OBJECT-TYPE
--		 SYNTAX       Counter32  
--		 MAX-ACCESS   read-only
--		 STATUS       current
--		 DESCRIPTION
--			"
--			  This attribute indicates the total number of bytes observed
--			  on this BSSID at the HT 15.0 rate.
--			"
--		::= { wlsxWlanAPRateStatsEntry 32 }
--
--	 wlanAPStatsTotPktsAtHT19dot5Mbps OBJECT-TYPE
--		 SYNTAX       Counter32  
--		 MAX-ACCESS   read-only
--		 STATUS       current
--		 DESCRIPTION
--			"
--			  This attribute indicates the total number of packets observed
--			  on this BSSID at the HT 19.5 rate.
--			"
--		::= { wlsxWlanAPRateStatsEntry 33 }
--
--	 wlanAPStatsTotBytesAtHT19dot5Mbps OBJECT-TYPE
--		 SYNTAX       Counter32  
--		 MAX-ACCESS   read-only
--		 STATUS       current
--		 DESCRIPTION
--			"
--			  This attribute indicates the total number of bytes observed
--			  on this BSSID at the HT 19.5 rate.
--			"
--		::= { wlsxWlanAPRateStatsEntry 34 }
--
--	 wlanAPStatsTotPktsAtHT26Mbps OBJECT-TYPE
--		 SYNTAX       Counter32  
--		 MAX-ACCESS   read-only
--		 STATUS       current
--		 DESCRIPTION
--			"
--			  This attribute indicates the total number of packets observed
--			  on this BSSID at the HT 26.0 rate.
--			"
--		::= { wlsxWlanAPRateStatsEntry 35 }
--
--	 wlanAPStatsTotBytesAtHT26Mbps OBJECT-TYPE
--		 SYNTAX       Counter32  
--		 MAX-ACCESS   read-only
--		 STATUS       current
--		 DESCRIPTION
--			"
--			  This attribute indicates the total number of bytes observed
--			  on this BSSID at the HT 26.0 rate.
--			"
--		::= { wlsxWlanAPRateStatsEntry 36 }
--
--	 wlanAPStatsTotPktsAtHT27Mbps OBJECT-TYPE
--		 SYNTAX       Counter32  
--		 MAX-ACCESS   read-only
--		 STATUS       current
--		 DESCRIPTION
--			"
--			  This attribute indicates the total number of packets observed
--			  on this BSSID at the HT 27.0 rate.
--			"
--		::= { wlsxWlanAPRateStatsEntry 37 }
--
--	 wlanAPStatsTotBytesAtHT27Mbps OBJECT-TYPE
--		 SYNTAX       Counter32  
--		 MAX-ACCESS   read-only
--		 STATUS       current
--		 DESCRIPTION
--			"
--			  This attribute indicates the total number of bytes observed
--			  on this BSSID at the HT 27.0 rate.
--			"
--		::= { wlsxWlanAPRateStatsEntry 38 }
--
--	 wlanAPStatsTotPktsAtHT30Mbps OBJECT-TYPE
--		 SYNTAX       Counter32  
--		 MAX-ACCESS   read-only
--		 STATUS       current
--		 DESCRIPTION
--			"
--			  This attribute indicates the total number of packets observed
--			  on this BSSID at the HT 30.0 rate.
--			"
--		::= { wlsxWlanAPRateStatsEntry 39 }
--
--	 wlanAPStatsTotBytesAtHT30Mbps OBJECT-TYPE
--		 SYNTAX       Counter32  
--		 MAX-ACCESS   read-only
--		 STATUS       current
--		 DESCRIPTION
--			"
--			  This attribute indicates the total number of bytes observed
--			  on this BSSID at the HT 30.0 rate.
--			"
--		::= { wlsxWlanAPRateStatsEntry 40 }
--
--	 wlanAPStatsTotPktsAtHT39Mbps OBJECT-TYPE
--		 SYNTAX       Counter32  
--		 MAX-ACCESS   read-only
--		 STATUS       current
--		 DESCRIPTION
--			"
--			  This attribute indicates the total number of packets observed
--			  on this BSSID at the HT 39.0 rate.
--			"
--		::= { wlsxWlanAPRateStatsEntry 41 }
--
--	 wlanAPStatsTotBytesAtHT39Mbps OBJECT-TYPE
--		 SYNTAX       Counter32  
--		 MAX-ACCESS   read-only
--		 STATUS       current
--		 DESCRIPTION
--			"
--			  This attribute indicates the total number of bytes observed
--			  on this BSSID at the HT 39.0 rate.
--			"
--		::= { wlsxWlanAPRateStatsEntry 42 }
--
--	 wlanAPStatsTotPktsAtHT40dot5Mbps OBJECT-TYPE
--		 SYNTAX       Counter32  
--		 MAX-ACCESS   read-only
--		 STATUS       current
--		 DESCRIPTION
--			"
--			  This attribute indicates the total number of packets observed
--			  on this BSSID at the HT 40.5 rate.
--			"
--		::= { wlsxWlanAPRateStatsEntry 43 }
--
--	 wlanAPStatsTotBytesAtHT40dot5Mbps OBJECT-TYPE
--		 SYNTAX       Counter32  
--		 MAX-ACCESS   read-only
--		 STATUS       current
--		 DESCRIPTION
--			"
--			  This attribute indicates the total number of bytes observed
--			  on this BSSID at the HT 40.5 rate.
--			"
--		::= { wlsxWlanAPRateStatsEntry 44 }
--
--	 wlanAPStatsTotPktsAtHT45Mbps OBJECT-TYPE
--		 SYNTAX       Counter32  
--		 MAX-ACCESS   read-only
--		 STATUS       current
--		 DESCRIPTION
--			"
--			  This attribute indicates the total number of packets observed
--			  on this BSSID at the HT 45.0 rate.
--			"
--		::= { wlsxWlanAPRateStatsEntry 45 }
--
--	 wlanAPStatsTotBytesAtHT45Mbps OBJECT-TYPE
--		 SYNTAX       Counter32  
--		 MAX-ACCESS   read-only
--		 STATUS       current
--		 DESCRIPTION
--			"
--			  This attribute indicates the total number of bytes observed
--			  on this BSSID at the HT 45.0 rate.
--			"
--		::= { wlsxWlanAPRateStatsEntry 46 }
--
--	 wlanAPStatsTotPktsAtHT52Mbps OBJECT-TYPE
--		 SYNTAX       Counter32  
--		 MAX-ACCESS   read-only
--		 STATUS       current
--		 DESCRIPTION
--			"
--			  This attribute indicates the total number of packets observed
--			  on this BSSID at the HT 52.0 rate.
--			"
--		::= { wlsxWlanAPRateStatsEntry 47 }
--
--	 wlanAPStatsTotBytesAtHT52Mbps OBJECT-TYPE
--		 SYNTAX       Counter32  
--		 MAX-ACCESS   read-only
--		 STATUS       current
--		 DESCRIPTION
--			"
--			  This attribute indicates the total number of bytes observed
--			  on this BSSID at the HT 52.0 rate.
--			"
--		::= { wlsxWlanAPRateStatsEntry 48 }
--
--	 wlanAPStatsTotPktsAtHT54Mbps OBJECT-TYPE
--		 SYNTAX       Counter32  
--		 MAX-ACCESS   read-only
--		 STATUS       current
--		 DESCRIPTION
--			"
--			  This attribute indicates the total number of packets observed
--			  on this BSSID at the HT 54.0 rate.
--			"
--		::= { wlsxWlanAPRateStatsEntry 49 }
--
--	 wlanAPStatsTotBytesAtHT54Mbps OBJECT-TYPE
--		 SYNTAX       Counter32  
--		 MAX-ACCESS   read-only
--		 STATUS       current
--		 DESCRIPTION
--			"
--			  This attribute indicates the total number of bytes observed
--			  on this BSSID at the HT 54.0 rate.
--			"
--		::= { wlsxWlanAPRateStatsEntry 50 }
--
--	 wlanAPStatsTotPktsAtHT58dot5Mbps OBJECT-TYPE
--		 SYNTAX       Counter32  
--		 MAX-ACCESS   read-only
--		 STATUS       current
--		 DESCRIPTION
--			"
--			  This attribute indicates the total number of packets observed
--			  on this BSSID at the HT 58.5 rate.
--			"
--		::= { wlsxWlanAPRateStatsEntry 51 }
--
--	 wlanAPStatsTotBytesAtHT58dot5Mbps OBJECT-TYPE
--		 SYNTAX       Counter32  
--		 MAX-ACCESS   read-only
--		 STATUS       current
--		 DESCRIPTION
--			"
--			  This attribute indicates the total number of bytes observed
--			  on this BSSID at the HT 58.5 rate.
--			"
--		::= { wlsxWlanAPRateStatsEntry 52 }
--
--	 wlanAPStatsTotPktsAtHT60Mbps OBJECT-TYPE
--		 SYNTAX       Counter32  
--		 MAX-ACCESS   read-only
--		 STATUS       current
--		 DESCRIPTION
--			"
--			  This attribute indicates the total number of packets observed
--			  on this BSSID at the HT 60.0 rate.
--			"
--		::= { wlsxWlanAPRateStatsEntry 53 }
--
--	 wlanAPStatsTotBytesAtHT60Mbps OBJECT-TYPE
--		 SYNTAX       Counter32  
--		 MAX-ACCESS   read-only
--		 STATUS       current
--		 DESCRIPTION
--			"
--			  This attribute indicates the total number of bytes observed
--			  on this BSSID at the HT 60.0 rate.
--			"
--		::= { wlsxWlanAPRateStatsEntry 54 }
--
--	 wlanAPStatsTotPktsAtHT65Mbps OBJECT-TYPE
--		 SYNTAX       Counter32  
--		 MAX-ACCESS   read-only
--		 STATUS       current
--		 DESCRIPTION
--			"
--			  This attribute indicates the total number of packets observed
--			  on this BSSID at the HT 65.0 rate.
--			"
--		::= { wlsxWlanAPRateStatsEntry 55 }
--
--	 wlanAPStatsTotBytesAtHT65Mbps OBJECT-TYPE
--		 SYNTAX       Counter32  
--		 MAX-ACCESS   read-only
--		 STATUS       current
--		 DESCRIPTION
--			"
--			  This attribute indicates the total number of bytes observed
--			  on this BSSID at the HT 65.0 rate.
--			"
--		::= { wlsxWlanAPRateStatsEntry 56 }
--
--	 wlanAPStatsTotPktsAtHT78Mbps OBJECT-TYPE
--		 SYNTAX       Counter32  
--		 MAX-ACCESS   read-only
--		 STATUS       current
--		 DESCRIPTION
--			"
--			  This attribute indicates the total number of packets observed
--			  on this BSSID at the HT 78.0 rate.
--			"
--		::= { wlsxWlanAPRateStatsEntry 57 }
--
--	 wlanAPStatsTotBytesAtHT78Mbps OBJECT-TYPE
--		 SYNTAX       Counter32  
--		 MAX-ACCESS   read-only
--		 STATUS       current
--		 DESCRIPTION
--			"
--			  This attribute indicates the total number of bytes observed
--			  on this BSSID at the HT 78.0 rate.
--			"
--		::= { wlsxWlanAPRateStatsEntry 58 }
--
--	 wlanAPStatsTotPktsAtHT81Mbps OBJECT-TYPE
--		 SYNTAX       Counter32  
--		 MAX-ACCESS   read-only
--		 STATUS       current
--		 DESCRIPTION
--			"
--			  This attribute indicates the total number of packets observed
--			  on this BSSID at the HT 81.0 rate.
--			"
--		::= { wlsxWlanAPRateStatsEntry 59 }
--
--	 wlanAPStatsTotBytesAtHT81Mbps OBJECT-TYPE
--		 SYNTAX       Counter32  
--		 MAX-ACCESS   read-only
--		 STATUS       current
--		 DESCRIPTION
--			"
--			  This attribute indicates the total number of bytes observed
--			  on this BSSID at the HT 81.0 rate.
--			"
--		::= { wlsxWlanAPRateStatsEntry 60 }
--
--	 wlanAPStatsTotPktsAtHT90Mbps OBJECT-TYPE
--		 SYNTAX       Counter32  
--		 MAX-ACCESS   read-only
--		 STATUS       current
--		 DESCRIPTION
--			"
--			  This attribute indicates the total number of packets observed
--			  on this BSSID at the HT 90.0 rate.
--			"
--		::= { wlsxWlanAPRateStatsEntry 61 }
--
--	 wlanAPStatsTotBytesAtHT90Mbps OBJECT-TYPE
--		 SYNTAX       Counter32  
--		 MAX-ACCESS   read-only
--		 STATUS       current
--		 DESCRIPTION
--			"
--			  This attribute indicates the total number of bytes observed
--			  on this BSSID at the HT 90.0 rate.
--			"
--		::= { wlsxWlanAPRateStatsEntry 62 }
--
--	 wlanAPStatsTotPktsAtHT104Mbps OBJECT-TYPE
--		 SYNTAX       Counter32  
--		 MAX-ACCESS   read-only
--		 STATUS       current
--		 DESCRIPTION
--			"
--			  This attribute indicates the total number of packets observed
--			  on this BSSID at the HT 104.0 rate.
--			"
--		::= { wlsxWlanAPRateStatsEntry 63 }
--
--	 wlanAPStatsTotBytesAtHT104Mbps OBJECT-TYPE
--		 SYNTAX       Counter32  
--		 MAX-ACCESS   read-only
--		 STATUS       current
--		 DESCRIPTION
--			"
--			  This attribute indicates the total number of bytes observed
--			  on this BSSID at the HT 104.0 rate.
--			"
--		::= { wlsxWlanAPRateStatsEntry 64 }
--
--	 wlanAPStatsTotPktsAtHT108Mbps OBJECT-TYPE
--		 SYNTAX       Counter32  
--		 MAX-ACCESS   read-only
--		 STATUS       current
--		 DESCRIPTION
--			"
--			  This attribute indicates the total number of packets observed
--			  on this BSSID at the HT 108.0 rate.
--			"
--		::= { wlsxWlanAPRateStatsEntry 65 }
--
--	 wlanAPStatsTotBytesAtHT108Mbps OBJECT-TYPE
--		 SYNTAX       Counter32  
--		 MAX-ACCESS   read-only
--		 STATUS       current
--		 DESCRIPTION
--			"
--			  This attribute indicates the total number of bytes observed
--			  on this BSSID at the HT 108.0 rate.
--			"
--		::= { wlsxWlanAPRateStatsEntry 66 }
--
--	 wlanAPStatsTotPktsAtHT117Mbps OBJECT-TYPE
--		 SYNTAX       Counter32  
--		 MAX-ACCESS   read-only
--		 STATUS       current
--		 DESCRIPTION
--			"
--			  This attribute indicates the total number of packets observed
--			  on this BSSID at the HT 117.0 rate.
--			"
--		::= { wlsxWlanAPRateStatsEntry 67 }
--
--	 wlanAPStatsTotBytesAtHT117Mbps OBJECT-TYPE
--		 SYNTAX       Counter32  
--		 MAX-ACCESS   read-only
--		 STATUS       current
--		 DESCRIPTION
--			"
--			  This attribute indicates the total number of bytes observed
--			  on this BSSID at the HT 117.0 rate.
--			"
--		::= { wlsxWlanAPRateStatsEntry 68 }
--
--	 wlanAPStatsTotPktsAtHT120Mbps OBJECT-TYPE
--		 SYNTAX       Counter32  
--		 MAX-ACCESS   read-only
--		 STATUS       current
--		 DESCRIPTION
--			"
--			  This attribute indicates the total number of packets observed
--			  on this BSSID at the HT 120.0 rate.
--			"
--		::= { wlsxWlanAPRateStatsEntry 69 }
--
--	 wlanAPStatsTotBytesAtHT120Mbps OBJECT-TYPE
--		 SYNTAX       Counter32  
--		 MAX-ACCESS   read-only
--		 STATUS       current
--		 DESCRIPTION
--			"
--			  This attribute indicates the total number of bytes observed
--			  on this BSSID at the HT 120.0 rate.
--			"
--		::= { wlsxWlanAPRateStatsEntry 70 }
--
--	 wlanAPStatsTotPktsAtHT121dot5Mbps OBJECT-TYPE
--		 SYNTAX       Counter32  
--		 MAX-ACCESS   read-only
--		 STATUS       current
--		 DESCRIPTION
--			"
--			  This attribute indicates the total number of packets observed
--			  on this BSSID at the HT 121.5 rate.
--			"
--		::= { wlsxWlanAPRateStatsEntry 71 }
--
--	 wlanAPStatsTotBytesAtHT121dot5Mbps OBJECT-TYPE
--		 SYNTAX       Counter32  
--		 MAX-ACCESS   read-only
--		 STATUS       current
--		 DESCRIPTION
--			"
--			  This attribute indicates the total number of bytes observed
--			  on this BSSID at the HT 121.5 rate.
--			"
--		::= { wlsxWlanAPRateStatsEntry 72 }
--
--	 wlanAPStatsTotPktsAtHT130Mbps OBJECT-TYPE
--		 SYNTAX       Counter32  
--		 MAX-ACCESS   read-only
--		 STATUS       current
--		 DESCRIPTION
--			"
--			  This attribute indicates the total number of packets observed
--			  on this BSSID at the HT 130.0 rate.
--			"
--		::= { wlsxWlanAPRateStatsEntry 73 }
--
--	 wlanAPStatsTotBytesAtHT130Mbps OBJECT-TYPE
--		 SYNTAX       Counter32  
--		 MAX-ACCESS   read-only
--		 STATUS       current
--		 DESCRIPTION
--			"
--			  This attribute indicates the total number of bytes observed
--			  on this BSSID at the HT 130.0 rate.
--			"
--		::= { wlsxWlanAPRateStatsEntry 74 }
--
--	 wlanAPStatsTotPktsAtHT135Mbps OBJECT-TYPE
--		 SYNTAX       Counter32  
--		 MAX-ACCESS   read-only
--		 STATUS       current
--		 DESCRIPTION
--			"
--			  This attribute indicates the total number of packets observed
--			  on this BSSID at the HT 135.0 rate.
--			"
--		::= { wlsxWlanAPRateStatsEntry 75 }
--
--	 wlanAPStatsTotBytesAtHT135Mbps OBJECT-TYPE
--		 SYNTAX       Counter32  
--		 MAX-ACCESS   read-only
--		 STATUS       current
--		 DESCRIPTION
--			"
--			  This attribute indicates the total number of bytes observed
--			  on this BSSID at the HT 135.0 rate.
--			"
--		::= { wlsxWlanAPRateStatsEntry 76 }
--
--	 wlanAPStatsTotPktsAtHT150Mbps OBJECT-TYPE
--		 SYNTAX       Counter32  
--		 MAX-ACCESS   read-only
--		 STATUS       current
--		 DESCRIPTION
--			"
--			  This attribute indicates the total number of packets observed
--			  on this BSSID at the HT 150.0 rate.
--			"
--		::= { wlsxWlanAPRateStatsEntry 77 }
--
--	 wlanAPStatsTotBytesAtHT150Mbps OBJECT-TYPE
--		 SYNTAX       Counter32  
--		 MAX-ACCESS   read-only
--		 STATUS       current
--		 DESCRIPTION
--			"
--			  This attribute indicates the total number of bytes observed
--			  on this BSSID at the HT 150.0 rate.
--			"
--		::= { wlsxWlanAPRateStatsEntry 78 }
--
--	 wlanAPStatsTotPktsAtHT162Mbps OBJECT-TYPE
--		 SYNTAX       Counter32  
--		 MAX-ACCESS   read-only
--		 STATUS       current
--		 DESCRIPTION
--			"
--			  This attribute indicates the total number of packets observed
--			  on this BSSID at the HT 162.0 rate.
--			"
--		::= { wlsxWlanAPRateStatsEntry 79 }
--
--	 wlanAPStatsTotBytesAtHT162Mbps OBJECT-TYPE
--		 SYNTAX       Counter32  
--		 MAX-ACCESS   read-only
--		 STATUS       current
--		 DESCRIPTION
--			"
--			  This attribute indicates the total number of bytes observed
--			  on this BSSID at the HT 162.0 rate.
--			"
--		::= { wlsxWlanAPRateStatsEntry 80 }
--
--	 wlanAPStatsTotPktsAtHT180Mbps OBJECT-TYPE
--		 SYNTAX       Counter32  
--		 MAX-ACCESS   read-only
--		 STATUS       current
--		 DESCRIPTION
--			"
--			  This attribute indicates the total number of packets observed
--			  on this BSSID at the HT 180.0 rate.
--			"
--		::= { wlsxWlanAPRateStatsEntry 81 }
--
--	 wlanAPStatsTotBytesAtHT180Mbps OBJECT-TYPE
--		 SYNTAX       Counter32  
--		 MAX-ACCESS   read-only
--		 STATUS       current
--		 DESCRIPTION
--			"
--			  This attribute indicates the total number of bytes observed
--			  on this BSSID at the HT 180.0 rate.
--			"
--		::= { wlsxWlanAPRateStatsEntry 82 }
--
--	 wlanAPStatsTotPktsAtHT216Mbps OBJECT-TYPE
--		 SYNTAX       Counter32  
--		 MAX-ACCESS   read-only
--		 STATUS       current
--		 DESCRIPTION
--			"
--			  This attribute indicates the total number of packets observed
--			  on this BSSID at the HT 216.0 rate.
--			"
--		::= { wlsxWlanAPRateStatsEntry 83 }
--
--	 wlanAPStatsTotBytesAtHT216Mbps OBJECT-TYPE
--		 SYNTAX       Counter32  
--		 MAX-ACCESS   read-only
--		 STATUS       current
--		 DESCRIPTION
--			"
--			  This attribute indicates the total number of bytes observed
--			  on this BSSID at the HT 216.0 rate.
--			"
--		::= { wlsxWlanAPRateStatsEntry 84 }
--
--	 wlanAPStatsTotPktsAtHT240Mbps OBJECT-TYPE
--		 SYNTAX       Counter32  
--		 MAX-ACCESS   read-only
--		 STATUS       current
--		 DESCRIPTION
--			"
--			  This attribute indicates the total number of packets observed
--			  on this BSSID at the HT 240.0 rate.
--			"
--		::= { wlsxWlanAPRateStatsEntry 85 }
--
--	 wlanAPStatsTotBytesAtHT240Mbps OBJECT-TYPE
--		 SYNTAX       Counter32  
--		 MAX-ACCESS   read-only
--		 STATUS       current
--		 DESCRIPTION
--			"
--			  This attribute indicates the total number of bytes observed
--			  on this BSSID at the HT 240.0 rate.
--			"
--		::= { wlsxWlanAPRateStatsEntry 86 }
--
--	 wlanAPStatsTotPktsAtHT243Mbps OBJECT-TYPE
--		 SYNTAX       Counter32  
--		 MAX-ACCESS   read-only
--		 STATUS       current
--		 DESCRIPTION
--			"
--			  This attribute indicates the total number of packets observed
--			  on this BSSID at the HT 243.0 rate.
--			"
--		::= { wlsxWlanAPRateStatsEntry 87 }
--
--	 wlanAPStatsTotBytesAtHT243Mbps OBJECT-TYPE
--		 SYNTAX       Counter32  
--		 MAX-ACCESS   read-only
--		 STATUS       current
--		 DESCRIPTION
--			"
--			  This attribute indicates the total number of bytes observed
--			  on this BSSID at the HT 243.0 rate.
--			"
--		::= { wlsxWlanAPRateStatsEntry 88 }
--
--	 wlanAPStatsTotPktsAtHT270Mbps OBJECT-TYPE
--		 SYNTAX       Counter32  
--		 MAX-ACCESS   read-only
--		 STATUS       current
--		 DESCRIPTION
--			"
--			  This attribute indicates the total number of packets observed
--			  on this BSSID at the HT 270.0 rate.
--			"
--		::= { wlsxWlanAPRateStatsEntry 89 }
--
--	 wlanAPStatsTotBytesAtHT270Mbps OBJECT-TYPE
--		 SYNTAX       Counter32  
--		 MAX-ACCESS   read-only
--		 STATUS       current
--		 DESCRIPTION
--			"
--			  This attribute indicates the total number of bytes observed
--			  on this BSSID at the HT 270.0 rate.
--			"
--		::= { wlsxWlanAPRateStatsEntry 90 }
--
--	 wlanAPStatsTotPktsAtHT300Mbps OBJECT-TYPE
--		 SYNTAX       Counter32  
--		 MAX-ACCESS   read-only
--		 STATUS       current
--		 DESCRIPTION
--			"
--			  This attribute indicates the total number of packets observed
--			  on this BSSID at the HT 300.0 rate.
--			"
--		::= { wlsxWlanAPRateStatsEntry 91 }
--
--	 wlanAPStatsTotBytesAtHT300Mbps OBJECT-TYPE
--		 SYNTAX       Counter32  
--		 MAX-ACCESS   read-only
--		 STATUS       current
--		 DESCRIPTION
--			"
--			  This attribute indicates the total number of bytes observed
--			  on this BSSID at the HT 300.0 rate.
--			"
--		::= { wlsxWlanAPRateStatsEntry 92 }

-- This table breaks down the BSSID statistics observed based on the
-- Destination Address Types. 

   wlsxWlanAPDATypeStatsTable  OBJECT-TYPE 
	  SYNTAX       SEQUENCE OF WlsxWlanAPDATypeStatsEntry 
	  MAX-ACCESS   not-accessible		
      STATUS       current 
      DESCRIPTION 
	  	"
		This table contains all the per BSSID Packet and Byte Counts
		 but broken down in terms of Destination Address Type. 
		"
      ::= { wlsxWlanAccessPointStatsGroup 3 } 

     wlsxWlanAPDATypeStatsEntry OBJECT-TYPE 
	  SYNTAX       WlsxWlanAPDATypeStatsEntry 
	  MAX-ACCESS   not-accessible		
      STATUS       current 
      DESCRIPTION 
			 "Destination Address based packet and byte count entry for an AP"
	  INDEX {wlanAPMacAddress, wlanAPRadioNumber, wlanAPBSSID}
      ::= { wlsxWlanAPDATypeStatsTable 1 } 
	
     WlsxWlanAPDATypeStatsEntry ::=
     SEQUENCE {
		 wlanAPStatsTotDABroadcastPkts		Counter32  ,
		 wlanAPStatsTotDABroadcastBytes		Counter32  ,
		 wlanAPStatsTotDAMulticastPkts		Counter32  ,
		 wlanAPStatsTotDAMulticastBytes		Counter32  ,
		 wlanAPStatsTotDAUnicastPkts			Counter32  ,
		 wlanAPStatsTotDAUnicastBytes		Counter32  

     }

     wlanAPStatsTotDABroadcastPkts OBJECT-TYPE
         SYNTAX       Counter32  
         MAX-ACCESS   read-only
         STATUS       current
         DESCRIPTION
            "
			 This attribute indicates the total number of Broadcast packets 
			  observed on this BSSID.
            "
        ::= { wlsxWlanAPDATypeStatsEntry 1 }

     wlanAPStatsTotDABroadcastBytes OBJECT-TYPE
         SYNTAX       Counter32  
         MAX-ACCESS   read-only
         STATUS       current
         DESCRIPTION
            "
			 This attribute indicates the total number of Broadcast Bytes 
			  observed on this BSSID.
            "
        ::= { wlsxWlanAPDATypeStatsEntry 2 }

     wlanAPStatsTotDAMulticastPkts OBJECT-TYPE
         SYNTAX       Counter32  
         MAX-ACCESS   read-only
         STATUS       current
         DESCRIPTION
            "
			 This attribute indicates the total number of Multicast packets 
			  observed on this BSSID.
            "
        ::= { wlsxWlanAPDATypeStatsEntry 3 }

     wlanAPStatsTotDAMulticastBytes OBJECT-TYPE
         SYNTAX       Counter32  
         MAX-ACCESS   read-only
         STATUS       current
         DESCRIPTION
            "
			 This attribute indicates the total number of Multicast Bytes 
			  observed on this BSSID.
            "
        ::= { wlsxWlanAPDATypeStatsEntry 4 }

     wlanAPStatsTotDAUnicastPkts OBJECT-TYPE
         SYNTAX       Counter32  
         MAX-ACCESS   read-only
         STATUS       current
         DESCRIPTION
            "
			 This attribute indicates the total number of Unicast packets 
			  observed on this BSSID.
            "
        ::= { wlsxWlanAPDATypeStatsEntry 5 }

     wlanAPStatsTotDAUnicastBytes OBJECT-TYPE
         SYNTAX       Counter32  
         MAX-ACCESS   read-only
         STATUS       current
         DESCRIPTION
            "
			 This attribute indicates the total number of Unicast Bytes 
			  observed on this BSSID.
            "
        ::= { wlsxWlanAPDATypeStatsEntry 6 }

-- This table breaks down the BSSID statistics observed based on the
-- the Type of the Packet. 

   wlsxWlanAPFrameTypeStatsTable  OBJECT-TYPE 
	  SYNTAX       SEQUENCE OF WlsxWlanAPFrameTypeStatsEntry 
	  MAX-ACCESS   not-accessible		
      STATUS       current 
      DESCRIPTION 
	  	"
		This table contains all the per BSSID Packet and Byte Counts
		 but broken down into different Frame Types. 
		"
      ::= { wlsxWlanAccessPointStatsGroup 4 } 

     wlsxWlanAPFrameTypeStatsEntry OBJECT-TYPE 
	  SYNTAX       WlsxWlanAPFrameTypeStatsEntry 
	  MAX-ACCESS   not-accessible		
      STATUS       current 
      DESCRIPTION 
			 "Frame Type based packet and byte count entry for an AP"
	  INDEX {wlanAPMacAddress, wlanAPRadioNumber, wlanAPBSSID}
      ::= { wlsxWlanAPFrameTypeStatsTable 1 } 
	
     WlsxWlanAPFrameTypeStatsEntry ::=
     SEQUENCE {
		 wlanAPStatsTotMgmtPkts		Counter32  ,
		 wlanAPStatsTotMgmtBytes	Counter32  ,
		 wlanAPStatsTotCtrlPkts		Counter32  ,
		 wlanAPStatsTotCtrlBytes	Counter32  ,
		 wlanAPStatsTotDataPkts		Counter32  ,
		 wlanAPStatsTotDataBytes	Counter32  

     }

     wlanAPStatsTotMgmtPkts OBJECT-TYPE
         SYNTAX       Counter32  
         MAX-ACCESS   read-only
         STATUS       current
         DESCRIPTION
            "
			 This attribute indicates the total number of Management packets 
			  observed on this BSSID.
            "
        ::= { wlsxWlanAPFrameTypeStatsEntry 1 }

     wlanAPStatsTotMgmtBytes OBJECT-TYPE
         SYNTAX       Counter32  
         MAX-ACCESS   read-only
         STATUS       current
         DESCRIPTION
            "
			 This attribute indicates the total number of Management Bytes 
			  observed on this BSSID.
            "
        ::= { wlsxWlanAPFrameTypeStatsEntry 2 }

     wlanAPStatsTotCtrlPkts OBJECT-TYPE
         SYNTAX       Counter32  
         MAX-ACCESS   read-only
         STATUS       current
         DESCRIPTION
            "
			 This attribute indicates the total number of Control packets 
			  observed on this BSSID.
            "
        ::= { wlsxWlanAPFrameTypeStatsEntry 3 }

     wlanAPStatsTotCtrlBytes OBJECT-TYPE
         SYNTAX       Counter32  
         MAX-ACCESS   read-only
         STATUS       current
         DESCRIPTION
            "
			 This attribute indicates the total number of Control Bytes 
			  observed on this BSSID.
            "
        ::= { wlsxWlanAPFrameTypeStatsEntry 4 }

     wlanAPStatsTotDataPkts OBJECT-TYPE
         SYNTAX       Counter32  
         MAX-ACCESS   read-only
         STATUS       current
         DESCRIPTION
            "
			 This attribute indicates the total number of Data packets 
			  observed on this BSSID.
            "
        ::= { wlsxWlanAPFrameTypeStatsEntry 5 }

     wlanAPStatsTotDataBytes OBJECT-TYPE
         SYNTAX       Counter32  
         MAX-ACCESS   read-only
         STATUS       current
         DESCRIPTION
            "
			 This attribute indicates the total number of Data Bytes 
			  observed on this BSSID.
            "
        ::= { wlsxWlanAPFrameTypeStatsEntry 6 }

-- This table breaks down the BSSID statistics observed into packet size 
-- buckets.

   wlsxWlanAPPktSizeStatsTable  OBJECT-TYPE 
	  SYNTAX       SEQUENCE OF WlsxWlanAPPktSizeStatsEntry 
	  MAX-ACCESS   not-accessible		
      STATUS       current 
      DESCRIPTION 
	  	"
		This table contains all the per BSSID Packet Count
		 but broken down into different Packet Sizes. 
		"
      ::= { wlsxWlanAccessPointStatsGroup 5 } 

     wlsxWlanAPPktSizeStatsEntry OBJECT-TYPE 
	  SYNTAX       WlsxWlanAPPktSizeStatsEntry 
	  MAX-ACCESS   not-accessible		
      STATUS       current 
      DESCRIPTION 
			 "Packet Size based packet count entry for a BSSID"
	  INDEX {wlanAPMacAddress, wlanAPRadioNumber, wlanAPBSSID}
      ::= { wlsxWlanAPPktSizeStatsTable 1 } 
	
     WlsxWlanAPPktSizeStatsEntry ::=
     SEQUENCE {
		 wlanAPStatsPkts63Bytes		Counter32  ,
		 wlanAPStatsPkts64To127		Counter32  ,
		 wlanAPStatsPkts128To255		Counter32  ,
		 wlanAPStatsPkts256To511		Counter32  ,
		 wlanAPStatsPkts512To1023	Counter32  ,
		 wlanAPStatsPkts1024To1518	Counter32  

     }

     wlanAPStatsPkts63Bytes OBJECT-TYPE
         SYNTAX       Counter32  
         MAX-ACCESS   read-only
         STATUS       current
         DESCRIPTION
            "
			 This attribute indicates the total number of packets that were
			  less than 64 bytes long.
            "
        ::= { wlsxWlanAPPktSizeStatsEntry 1 }

     wlanAPStatsPkts64To127 OBJECT-TYPE
         SYNTAX       Counter32  
         MAX-ACCESS   read-only
         STATUS       current
         DESCRIPTION
            "
			 This attribute indicates the total number of packets that were
			  between 64 and 127 bytes long.
            "
        ::= { wlsxWlanAPPktSizeStatsEntry 2 }

     wlanAPStatsPkts128To255 OBJECT-TYPE
         SYNTAX       Counter32  
         MAX-ACCESS   read-only
         STATUS       current
         DESCRIPTION
            "
			 This attribute indicates the total number of packets that were
			  between 128 and 255 bytes long.
            "
        ::= { wlsxWlanAPPktSizeStatsEntry 3 }

     wlanAPStatsPkts256To511 OBJECT-TYPE
         SYNTAX       Counter32  
         MAX-ACCESS   read-only
         STATUS       current
         DESCRIPTION
            "
			 This attribute indicates the total number of packets that were
			  between 256 and 511 bytes long.
            "
        ::= { wlsxWlanAPPktSizeStatsEntry 4 }

     wlanAPStatsPkts512To1023 OBJECT-TYPE
         SYNTAX       Counter32  
         MAX-ACCESS   read-only
         STATUS       current
         DESCRIPTION
            "
			 This attribute indicates the total number of packets that were
			  between 512 and 1023 bytes long.
            "
        ::= { wlsxWlanAPPktSizeStatsEntry 5 }

     wlanAPStatsPkts1024To1518 OBJECT-TYPE
         SYNTAX       Counter32  
         MAX-ACCESS   read-only
         STATUS       current
         DESCRIPTION
            "
			 This attribute indicates the total number of packets that were
			  between 1024 and 1518 bytes long.
            "
        ::= { wlsxWlanAPPktSizeStatsEntry 6 }


-- AP Chan Stats table 

   wlsxWlanAPChStatsTable  OBJECT-TYPE 
	  SYNTAX       SEQUENCE OF WlanAPChStatsEntry 
	  MAX-ACCESS   not-accessible		
      STATUS       current 
      DESCRIPTION 
	  	"
			This Table lists the Channel statistics of all the Access Points 
			 connected to the controller. 
		"
      ::= { wlsxWlanAccessPointStatsGroup 6 } 

   wlsxWlanAPChStatsEntry OBJECT-TYPE 
	  SYNTAX       WlanAPChStatsEntry 
	  MAX-ACCESS   not-accessible		
      STATUS       current 
      DESCRIPTION 
             "Access Point Channel Stats entry"
	  INDEX {wlanAPMacAddress, wlanAPRadioNumber}
      ::= { wlsxWlanAPChStatsTable 1 } 

   WlanAPChStatsEntry ::=
     SEQUENCE {
		 wlanAPChannelNumber			INTEGER,
		 wlanAPChNumStations			Integer32,
		 wlanAPChTotPkts				Counter32,
		 wlanAPChTotBytes				Counter32,
		 wlanAPChTotRetryPkts			Counter32,
		 wlanAPChTotFragmentedPkts		Counter32,
		 wlanAPChTotPhyErrPkts			Counter32,
		 wlanAPChTotMacErrPkts			Counter32,
		 wlanAPChNoise					Integer32,
		 wlanAPChCoverageIndex			Integer32,
		 wlanAPChInterferenceIndex		Integer32,
		 wlanAPChFrameRetryRate			Integer32,
		 wlanAPChFrameLowSpeedRate		Integer32,
		 wlanAPChFrameNonUnicastRate	Integer32,
		 wlanAPChFrameFragmentationRate	Integer32,
		 wlanAPChFrameBandwidthRate		Integer32,
		 wlanAPChFrameRetryErrorRate	Integer32,
		 wlanAPChBusyRate				Integer32,
		 wlanAPChNumAPs					Integer32,
		 wlanAPChFrameReceiveErrorRate	Integer32,
		 wlanAPChTransmittedFragmentCount	    Counter32,
		 wlanAPChMulticastTransmittedFrameCount Counter32,
		 wlanAPChFailedCount            Counter32,
		 wlanAPChRetryCount             Counter32,
		 wlanAPChMultipleRetryCount     Counter32,
		 wlanAPChFrameDuplicateCount    Counter32,
		 wlanAPChRTSSuccessCount        Counter32,
		 wlanAPChRTSFailureCount        Counter32,
		 wlanAPChACKFailureCount        Counter32,
		 wlanAPChReceivedFragmentCount  Counter32,
		 wlanAPChMulticastReceivedFrameCount    Counter32,
		 wlanAPChFCSErrorCount          Counter32,
		 wlanAPChTransmittedFrameCount  Counter32,
		 wlanAPChWEPUndecryptableCount  Counter32,
         wlanAPChRxUtilization       INTEGER,
         wlanAPChTxUtilization       INTEGER,
         wlanAPChUtilization  INTEGER
   }

	wlanAPChannelNumber OBJECT-TYPE
         SYNTAX       INTEGER(1..165)
         MAX-ACCESS   read-only
         STATUS       current
         DESCRIPTION
            "
			The channel the AP is currently using.
            "
        ::= { wlsxWlanAPChStatsEntry 1 }

   wlanAPChNumStations OBJECT-TYPE
         SYNTAX       Integer32 
         MAX-ACCESS   read-only
         STATUS       current
         DESCRIPTION
            "
			This attribute indicates the number of stations using this 
			channel.
            "
        ::= { wlsxWlanAPChStatsEntry 2 }

   wlanAPChTotPkts OBJECT-TYPE
         SYNTAX       Counter32 
         MAX-ACCESS   read-only
         STATUS       current
         DESCRIPTION
            "
			This attribute indicates the total packets observed on this
			 channel.
            "
        ::= { wlsxWlanAPChStatsEntry 3 }

   wlanAPChTotBytes OBJECT-TYPE
         SYNTAX       Counter32  
         MAX-ACCESS   read-only
         STATUS       current
         DESCRIPTION
            "
			This attribute indicates the total Bytes observed on this
			 channel.
            "
        ::= { wlsxWlanAPChStatsEntry 4 }

   wlanAPChTotRetryPkts OBJECT-TYPE
         SYNTAX       Counter32  
         MAX-ACCESS   read-only
         STATUS       current
         DESCRIPTION
            "
			This attribute indicates the total Retry Packets observed on this
			 channel.
            "
        ::= { wlsxWlanAPChStatsEntry 5 }

   wlanAPChTotFragmentedPkts OBJECT-TYPE
         SYNTAX       Counter32  
         MAX-ACCESS   read-only
         STATUS       current
         DESCRIPTION
            "
			This attribute indicates the total Fragmented Packets observed on 
			 this channel.
            "
        ::= { wlsxWlanAPChStatsEntry 6 }

   wlanAPChTotPhyErrPkts OBJECT-TYPE
         SYNTAX       Counter32  
         MAX-ACCESS   read-only
         STATUS       current
         DESCRIPTION
            "
			This attribute indicates the total Physical Error Packets observed 
			 on this channel. 
            "
        ::= { wlsxWlanAPChStatsEntry 7 }

   wlanAPChTotMacErrPkts OBJECT-TYPE
         SYNTAX       Counter32 
         MAX-ACCESS   read-only
         STATUS       current
         DESCRIPTION
            "
			This attribute indicates the total Mac errors packets observed on 
			 this channel.
            "
        ::= { wlsxWlanAPChStatsEntry 8 }

	wlanAPChNoise OBJECT-TYPE
         SYNTAX       Integer32
         MAX-ACCESS   read-only
         STATUS       current
         DESCRIPTION
            "
			This attribute indicates the noise observed on 
			 this channel.
            "
        ::= { wlsxWlanAPChStatsEntry 9 }

	wlanAPChCoverageIndex OBJECT-TYPE
         SYNTAX       Integer32
         MAX-ACCESS   read-only
         STATUS       current
         DESCRIPTION
            "
			This attribute indicates the coverage provided by the AP on
			 this channel.
            "
        ::= { wlsxWlanAPChStatsEntry 10 }

	wlanAPChInterferenceIndex OBJECT-TYPE
         SYNTAX       Integer32
         MAX-ACCESS   read-only
         STATUS       current
         DESCRIPTION
            "
			This attribute indicates the interference
			 observed on this channel.
            "
        ::= { wlsxWlanAPChStatsEntry 11 }

	wlanAPChFrameRetryRate OBJECT-TYPE
         SYNTAX       Integer32
         MAX-ACCESS   read-only
         STATUS       current
         DESCRIPTION
            "
			 The number of retry 
			 packets as a percentage of the total packets
			 transmitted and received on this channel.
            "
        ::= { wlsxWlanAPChStatsEntry 12 }

	wlanAPChFrameLowSpeedRate OBJECT-TYPE
         SYNTAX       Integer32
         MAX-ACCESS   read-only
         STATUS       current
         DESCRIPTION
            "
			 The number of low data rate (<= 18Mbps for A/G bands and <=2Mbps
			 for B band) packets as a percentage of the total packets
			 transmitted and received on this channel
            "
        ::= { wlsxWlanAPChStatsEntry 13 }

	wlanAPChFrameNonUnicastRate OBJECT-TYPE
         SYNTAX       Integer32
         MAX-ACCESS   read-only
         STATUS       current
         DESCRIPTION
            "
			 The number of broadcast and multicast
			 packets as a percentage of the total packets
			 transmitted on this channel.
            "
        ::= { wlsxWlanAPChStatsEntry 14 }

	wlanAPChFrameFragmentationRate OBJECT-TYPE
         SYNTAX       Integer32
         MAX-ACCESS   read-only
         STATUS       current
         DESCRIPTION
            "
			 The number of fragments
			 as a percentage of the total packets
			 transmitted on this channel
            "
        ::= { wlsxWlanAPChStatsEntry 15 }

	wlanAPChFrameBandwidthRate OBJECT-TYPE
         SYNTAX       Integer32
         MAX-ACCESS   read-only
         STATUS       current
         DESCRIPTION
            "
			 The bandwidth of this channel in Kbps.
            "
        ::= { wlsxWlanAPChStatsEntry 16 }

	wlanAPChFrameRetryErrorRate OBJECT-TYPE
         SYNTAX       Integer32
         MAX-ACCESS   read-only
         STATUS  	  deprecated
         DESCRIPTION
            "
			 The number of error packets
			 as a percentage of the total packets
			 received on this channel.
            "
        ::= { wlsxWlanAPChStatsEntry 17 }

	wlanAPChBusyRate OBJECT-TYPE
         SYNTAX       Integer32
         MAX-ACCESS   read-only
         STATUS       current
         DESCRIPTION
            "
			This attribute indicates the busy
			 this channel is.
            "
        ::= { wlsxWlanAPChStatsEntry 18 }

	wlanAPChNumAPs 	OBJECT-TYPE
         SYNTAX       Integer32
         MAX-ACCESS   read-only
         STATUS       current
         DESCRIPTION
            "
			This attribute indicates the number of Access Points
			 observed on this channel.
            "
        ::= { wlsxWlanAPChStatsEntry 19 }

	wlanAPChFrameReceiveErrorRate OBJECT-TYPE
         SYNTAX       Integer32
         MAX-ACCESS   read-only
         STATUS       current
         DESCRIPTION
            "
			 The number of error packets
			 as a percentage of the total packets
			 received on this channel.
            "
        ::= { wlsxWlanAPChStatsEntry 20 }

	wlanAPChTransmittedFragmentCount OBJECT-TYPE
         SYNTAX       Counter32
         MAX-ACCESS   read-only
         STATUS       current
         DESCRIPTION
            "
            This counter shall be incremented for an acknowledged MPDU
            with an individual address in the address 1 field or an MPDU
            with a multicast address in the address 1 field of type Data
            or Management.
            "
        ::= { wlsxWlanAPChStatsEntry 21 }

	wlanAPChMulticastTransmittedFrameCount OBJECT-TYPE
         SYNTAX       Counter32
         MAX-ACCESS   read-only
         STATUS       current
         DESCRIPTION
            "
            This counter shall increment only when the multicast bit
            is set in the destination MAC address of a successfully
            transmitted MSDU. When operating as a STA in an ESS, where
            these frames are directed to the AP, this implies having
            received an acknowledgment to all associated MPDUs.
            "
        ::= { wlsxWlanAPChStatsEntry 22 }

	wlanAPChFailedCount OBJECT-TYPE
         SYNTAX       Counter32
         MAX-ACCESS   read-only
         STATUS       current
         DESCRIPTION
            "
            This counter shall increment when an MSDU is not transmitted
            successfully due to the number of transmit attempts exceeding
            either the dot11ShortRetryLimit or dot11LongRetryLimit.
            "
        ::= { wlsxWlanAPChStatsEntry 23 }

	wlanAPChRetryCount OBJECT-TYPE
         SYNTAX       Counter32
         MAX-ACCESS   read-only
         STATUS       current
         DESCRIPTION
            "
            This counter shall increment when an MSDU is successfully
            transmitted after one or more retransmissions.
            "
        ::= { wlsxWlanAPChStatsEntry 24 }

	wlanAPChMultipleRetryCount OBJECT-TYPE
         SYNTAX       Counter32
         MAX-ACCESS   read-only
         STATUS       current
         DESCRIPTION
            "
            This counter shall increment when an MSDU is successfully
            transmitted after more than one retransmission.
            "
        ::= { wlsxWlanAPChStatsEntry 25 }

	wlanAPChFrameDuplicateCount OBJECT-TYPE
         SYNTAX       Counter32
         MAX-ACCESS   read-only
         STATUS       current
         DESCRIPTION
            "
            This counter shall increment when a frame is received
            that the Sequence Control field indicates is a
            duplicate.
            "
        ::= { wlsxWlanAPChStatsEntry 26 }

	wlanAPChRTSSuccessCount OBJECT-TYPE
         SYNTAX       Counter32
         MAX-ACCESS   read-only
         STATUS       current
         DESCRIPTION
            "
            This counter shall increment when a CTS is received in
            response to an RTS.
            "
        ::= { wlsxWlanAPChStatsEntry 27 }

	wlanAPChRTSFailureCount OBJECT-TYPE
         SYNTAX       Counter32
         MAX-ACCESS   read-only
         STATUS       current
         DESCRIPTION
            "
            This counter shall increment when a CTS is not received in
            response to an RTS.
            "
        ::= { wlsxWlanAPChStatsEntry 28 }

	wlanAPChACKFailureCount OBJECT-TYPE
         SYNTAX       Counter32
         MAX-ACCESS   read-only
         STATUS       current
         DESCRIPTION
            "
            This counter shall increment when an ACK is not received
            when expected.
            "
        ::= { wlsxWlanAPChStatsEntry 29 }

	wlanAPChReceivedFragmentCount OBJECT-TYPE
         SYNTAX       Counter32
         MAX-ACCESS   read-only
         STATUS       current
         DESCRIPTION
            "
            This counter shall be incremented for each successfully
            received MPDU of type Data or Management.
            "
        ::= { wlsxWlanAPChStatsEntry 30 }

	wlanAPChMulticastReceivedFrameCount OBJECT-TYPE
         SYNTAX       Counter32
         MAX-ACCESS   read-only
         STATUS       current
         DESCRIPTION
            "
            This counter shall increment when a MSDU is received
            with the multicast bit set in the destination
            MAC address.
            "
        ::= { wlsxWlanAPChStatsEntry 31 }

	wlanAPChFCSErrorCount OBJECT-TYPE
         SYNTAX       Counter32
         MAX-ACCESS   read-only
         STATUS       current
         DESCRIPTION
            "
            This counter shall increment when an FCS error is
            detected in a received MPDU.
            "
        ::= { wlsxWlanAPChStatsEntry 32 }

	wlanAPChTransmittedFrameCount OBJECT-TYPE
         SYNTAX       Counter32
         MAX-ACCESS   read-only
         STATUS       current
         DESCRIPTION
            "
            This counter shall increment for each successfully transmitted
            MSDU.
            "
        ::= { wlsxWlanAPChStatsEntry 33 }
        
	wlanAPChWEPUndecryptableCount OBJECT-TYPE
         SYNTAX       Counter32
         MAX-ACCESS   read-only
         STATUS       current
         DESCRIPTION
            "
            This counter shall increment when a frame is received with the
            Protected Frame subfield of the Frame Control field set to one and
            the WEPOn value for the key mapped to the transmitter's MAC address
            indicates that the frame should not have been encrypted or that frame
            is discarded due to the receiving STA not implementing the privacy
            option.
            "
        ::= { wlsxWlanAPChStatsEntry 34 }
        
    wlanAPChRxUtilization OBJECT-TYPE
        SYNTAX INTEGER(0..100)
        MAX-ACCESS read-only
        STATUS current
        DESCRIPTION
            "
            This is the percentage of time spent by the radio 
            in receiving packets.
            "
        ::= { wlsxWlanAPChStatsEntry 35 }

    wlanAPChTxUtilization OBJECT-TYPE
        SYNTAX INTEGER(0..100)
        MAX-ACCESS read-only
        STATUS current
        DESCRIPTION
            "
            This is the percentage of time spent by the radio 
            in transmitting packets.
            "
        ::= { wlsxWlanAPChStatsEntry 36 }

    wlanAPChUtilization OBJECT-TYPE
        SYNTAX INTEGER(0..100)
        MAX-ACCESS read-only
        STATUS current
        DESCRIPTION
            "
            This is the percentage of time the channel is busy.
            "
        ::= { wlsxWlanAPChStatsEntry 37 }

-- AP Wired Stats table

   wlsxWlanAPWiredStatsTable  OBJECT-TYPE
          SYNTAX       SEQUENCE OF WlanAPWiredStatsEntry
          MAX-ACCESS   not-accessible
      STATUS       current
      DESCRIPTION
                "
                        This Table lists the Wired statistics of all the Access Points
                         connected to the controller.
                "
      ::= { wlsxWlanAccessPointStatsGroup 7 }

   wlsxWlanAPWiredStatsEntry OBJECT-TYPE
          SYNTAX       WlanAPWiredStatsEntry
          MAX-ACCESS   not-accessible
      STATUS       current
      DESCRIPTION
             "Access Point Wired Stats entry"
          INDEX {wlanAPMacAddress}
      ::= { wlsxWlanAPWiredStatsTable 1 }

   WlanAPWiredStatsEntry ::=
     SEQUENCE {
                 wlanAPWiredRxPkts                      Counter32,
                 wlanAPWiredRxDroppedPkts               Counter32,
                 wlanAPWiredRxBytes                     Counter32,
                 wlanAPWiredTxBytes                     Counter32,
                 wlanAPWiredRxRate                      Gauge32,
                 wlanAPWiredTxRate                      Gauge32
   }

   wlanAPWiredRxPkts OBJECT-TYPE
         SYNTAX       Counter32
         MAX-ACCESS   read-only
         STATUS       current
         DESCRIPTION
            "
                        This attribute indicates the total packets received from the
                         AP wired side.
            "
        ::= { wlsxWlanAPWiredStatsEntry 1 }

   wlanAPWiredRxDroppedPkts OBJECT-TYPE
         SYNTAX       Counter32
         MAX-ACCESS   read-only
         STATUS       current
         DESCRIPTION
            "
                        This attribute indicates the total dropped packets received
                         from the AP wired side.
            "
        ::= { wlsxWlanAPWiredStatsEntry 2 }

   wlanAPWiredRxBytes OBJECT-TYPE
         SYNTAX       Counter32
         MAX-ACCESS   read-only
         STATUS       current
         DESCRIPTION
            "
                        This attribute indicates the total bytes of correct packets
                         received from the AP wired side.
            "
        ::= { wlsxWlanAPWiredStatsEntry 3 }

   wlanAPWiredTxBytes OBJECT-TYPE
         SYNTAX       Counter32
         MAX-ACCESS   read-only
         STATUS       current
         DESCRIPTION
            "
                        This attribute indicates the total bytes transmitted from
                         the AP wired side.
            "
        ::= { wlsxWlanAPWiredStatsEntry 4 }

   wlanAPWiredRxRate OBJECT-TYPE
         SYNTAX       Gauge32
         MAX-ACCESS   read-only
         STATUS       current
         DESCRIPTION
            "
                        This attribute indicates the data rate (kbyte/s)
                         received from AP wired side in sampling interval.
            "
        ::= { wlsxWlanAPWiredStatsEntry 5 }

   wlanAPWiredTxRate OBJECT-TYPE
         SYNTAX       Gauge32
         MAX-ACCESS   read-only
         STATUS       current
         DESCRIPTION
            "
                        This attribute indicates the data rate (kbyte/s)
                         transmitted from AP wired side in sampling interval.
            "
        ::= { wlsxWlanAPWiredStatsEntry 6 }

-- AP ESSID Stats table

   wlsxWlanAPESSIDStatsTable  OBJECT-TYPE
          SYNTAX       SEQUENCE OF WlanAPESSIDStatsEntry
          MAX-ACCESS   not-accessible
      STATUS       current
      DESCRIPTION
                "
                        This Table lists the ESSID statistics of all the Access Points
                         connected to the controller.
                "
      ::= { wlsxWlanAccessPointStatsGroup 8 }

   wlsxWlanAPESSIDStatsEntry OBJECT-TYPE
          SYNTAX       WlanAPESSIDStatsEntry
          MAX-ACCESS   not-accessible
      STATUS       current
      DESCRIPTION
             "Access Point ESSID Stats entry"
          INDEX {wlanAPMacAddress, wlanESSID}
      ::= { wlsxWlanAPESSIDStatsTable 1 }

   WlanAPESSIDStatsEntry ::=
     SEQUENCE {
                 wlanAPESSIDWirelessRxBytes             Counter32,
                 wlanAPESSIDWirelessTxBytes             Counter32,
                 wlanAPESSIDWiredRxBytes                Counter32,
                 wlanAPESSIDWiredTxBytes                Counter32
   }

   wlanAPESSIDWirelessRxBytes OBJECT-TYPE
         SYNTAX       Counter32
         MAX-ACCESS   read-only
         STATUS       current
         DESCRIPTION
            "
                        This attribute indicates the total bytes of correct packets
                         received from the AP ESSID wireless side.
            "
        ::= { wlsxWlanAPESSIDStatsEntry 1 }

   wlanAPESSIDWirelessTxBytes OBJECT-TYPE
         SYNTAX       Counter32
         MAX-ACCESS   read-only
         STATUS       current
         DESCRIPTION
            "
                        This attribute indicates the total bytes transmitted
                         from the AP ESSID wireless side.
            "
        ::= { wlsxWlanAPESSIDStatsEntry 2 }

   wlanAPESSIDWiredRxBytes OBJECT-TYPE
         SYNTAX       Counter32
         MAX-ACCESS   read-only
         STATUS       current
         DESCRIPTION
            "
                        This attribute indicates the total bytes of correct packets
                         received from the AP ESSID wired side.
            "
        ::= { wlsxWlanAPESSIDStatsEntry 3 }

   wlanAPESSIDWiredTxBytes OBJECT-TYPE
         SYNTAX       Counter32
         MAX-ACCESS   read-only
         STATUS       current
         DESCRIPTION
            "
                        This attribute indicates the total bytes transmitted from
                         the AP ESSID wired side.
            "
        ::= { wlsxWlanAPESSIDStatsEntry 4 }

-- AP Radio Stats table

   wlsxWlanAPRadioStatsTable  OBJECT-TYPE
          SYNTAX       SEQUENCE OF WlanAPRadioStatsEntry
          MAX-ACCESS   not-accessible
      STATUS       current
      DESCRIPTION
                "
                        This Table lists the Radio statistics of all the Access Points
                         connected to the controller.
                "
      ::= { wlsxWlanAccessPointStatsGroup 9 }

   wlsxWlanAPRadioStatsEntry OBJECT-TYPE
          SYNTAX       WlanAPRadioStatsEntry
          MAX-ACCESS   not-accessible
      STATUS       current
      DESCRIPTION
             "Access Point Radio Stats entry"
          INDEX {wlanAPMacAddress, wlanAPRadioNumber}
      ::= { wlsxWlanAPRadioStatsTable 1 }

   WlanAPRadioStatsEntry ::=
     SEQUENCE {
                 wlanAPRadioRxPkts                      Counter32,
                 wlanAPRadioRxBytes                     Counter32,
                 wlanAPRadioTxPkts                      Counter32,
                 wlanAPRadioTxBytes                     Counter32,
                 wlanAPRadioTxDroppedPkts               Counter32,
                 wlanAPRadioTxErrorPkts                 Counter32,
                 wlanAPRadioRxRate                      Gauge32,
                 wlanAPRadioTxRate                      Gauge32,
                 wlanApRadioAssocReqCount               Counter32,
                 wlanApRadioAssocReqSuccCount           Counter32,
                 wlanApRadioReAssocReqCount             Counter32,
                 wlanApRadioReAssocReqSuccCount         Counter32,
                 wlanAPRadioStationDuration             Integer32,
                 wlanAPRadioAssocSuccPercent            Gauge32,
                 wlanAPRadioTxDataBytes                 Counter32
   }

   wlanAPRadioRxPkts OBJECT-TYPE
         SYNTAX       Counter32
         MAX-ACCESS   read-only
         STATUS       current
         DESCRIPTION
            "
                        This attribute indicates the total packets transmitted
                         from the AP radio wireless side.
            "
        ::= { wlsxWlanAPRadioStatsEntry 1 }

   wlanAPRadioRxBytes OBJECT-TYPE
         SYNTAX       Counter32
         MAX-ACCESS   read-only
         STATUS       current
         DESCRIPTION
            "
                        This attribute indicates the total correct bytes
                         received from the AP radio wireless side.
            "
        ::= { wlsxWlanAPRadioStatsEntry 2 }

   wlanAPRadioTxPkts OBJECT-TYPE
         SYNTAX       Counter32
         MAX-ACCESS   read-only
         STATUS       current
         DESCRIPTION
            "
                        This attribute indicates the total packets
                         transmitted from the AP radio wireless side.
            "
        ::= { wlsxWlanAPRadioStatsEntry 3 }

   wlanAPRadioTxBytes OBJECT-TYPE
         SYNTAX       Counter32
         MAX-ACCESS   read-only
         STATUS       current
         DESCRIPTION
            "
                        This attribute indicates the total bytes
                         transmitted from the AP radio wireless side.
            "
        ::= { wlsxWlanAPRadioStatsEntry 4 }

   wlanAPRadioTxDroppedPkts OBJECT-TYPE
         SYNTAX       Counter32
         MAX-ACCESS   read-only
         STATUS       current
         DESCRIPTION
            "
                        This attribute indicates the dropped packets transmitted
                         from the AP radio wireless side.
            "
        ::= { wlsxWlanAPRadioStatsEntry 5 }

   wlanAPRadioTxErrorPkts OBJECT-TYPE
         SYNTAX       Counter32
         MAX-ACCESS   read-only
         STATUS       current
         DESCRIPTION
            "
                        This attribute indicates the error packets
                         transmitted from the AP radio wireless side.
            "
        ::= { wlsxWlanAPRadioStatsEntry 6 }

   wlanAPRadioRxRate OBJECT-TYPE
         SYNTAX       Gauge32
         MAX-ACCESS   read-only
         STATUS       current
         DESCRIPTION
            "
                        This attribute indicates the data rate (kbyte/s)
                         received from AP radio wireless side in sampling interval.
            "
        ::= { wlsxWlanAPRadioStatsEntry 7 }

   wlanAPRadioTxRate OBJECT-TYPE
         SYNTAX       Gauge32
         MAX-ACCESS   read-only
         STATUS       current
         DESCRIPTION
            "
                        This attribute indicates the data rate (kbyte/s)
                         transmitted from AP radio wireless side in sampling interval.
            "
        ::= { wlsxWlanAPRadioStatsEntry 8 }

    wlanApRadioAssocReqCount OBJECT-TYPE
        SYNTAX      Counter32
        MAX-ACCESS  read-only
        STATUS      current
        DESCRIPTION
            "This attribute indicates the times of associate request on this 
            radio."
        ::= { wlsxWlanAPRadioStatsEntry 9 }

    wlanApRadioAssocReqSuccCount OBJECT-TYPE
        SYNTAX      Counter32
        MAX-ACCESS  read-only
        STATUS      current
        DESCRIPTION
            "This attribute indicates the times of successful associate request
            on this radio."
        ::= { wlsxWlanAPRadioStatsEntry 10 }

    wlanApRadioReAssocReqCount OBJECT-TYPE
        SYNTAX      Counter32
        MAX-ACCESS  read-only
        STATUS      current
        DESCRIPTION
            "This attribute indicates the times of re-associate request on this
            radio."
        ::= { wlsxWlanAPRadioStatsEntry 11 }

    wlanApRadioReAssocReqSuccCount OBJECT-TYPE
        SYNTAX      Counter32
        MAX-ACCESS  read-only
        STATUS      current
        DESCRIPTION
            "This attribute indicates the times of successful re-associate 
            request on this radio.
            "
        ::= { wlsxWlanAPRadioStatsEntry 12 }

    wlanAPRadioStationDuration OBJECT-TYPE
         SYNTAX       Integer32
         MAX-ACCESS   read-only
         STATUS       current
         DESCRIPTION
            "
            This attribute indicates the total occupied duration, which is
            the total duration of user connecting.
            "
        ::= { wlsxWlanAPRadioStatsEntry 13 }

        wlanAPRadioAssocSuccPercent OBJECT-TYPE
         SYNTAX       Gauge32
         MAX-ACCESS   read-only
         STATUS       current
         DESCRIPTION
            "
            The Association Success Percent.
            "
        ::= { wlsxWlanAPRadioStatsEntry 14 }

   wlanAPRadioTxDataBytes OBJECT-TYPE
         SYNTAX       Counter32
         MAX-ACCESS   read-only
         STATUS       current
         DESCRIPTION
            "
                        This attribute indicates the total data bytes
                         transmitted from the AP radio wireless side.
            "
        ::= { wlsxWlanAPRadioStatsEntry 15 }

-- wlsxWlanStationStatsGroup contains all the statistics observed by different 
-- Air Monitors attached to this controller. 
-- Station Statistics are observed by the Air Monitor for that 
-- specific Station.

-- Station Statistics are grouped into Generic,
-- Rate, Destination Address and Frame Type Stats.

-- Station Statistics Group contains all the statistics related to 
-- a Station.

-- wlsxWlanStationStatsTable will contain all the aggregate statistics collected
-- for a Station

   wlsxWlanStationStatsTable  OBJECT-TYPE 
	  SYNTAX       SEQUENCE OF WlanStationStatsEntry 
	  MAX-ACCESS   not-accessible		
      STATUS       current 
      DESCRIPTION 
	  	"
			This Table lists statistics of all the wireless stations 
			associated with an AP connected to this controller. 
		"
      ::= { wlsxWlanStationStatsGroup 1} 

   wlsxWlanStationStatsEntry OBJECT-TYPE 
	  SYNTAX       WlanStationStatsEntry 
	  MAX-ACCESS   not-accessible		
      STATUS       current 
      DESCRIPTION 
             "Station Stats Entry"
	  INDEX {wlanStaPhyAddress}
      ::= { wlsxWlanStationStatsTable 1 } 

   WlanStationStatsEntry ::=
     SEQUENCE {
		 wlanStaChannelNum				Unsigned32,
		 wlanStaTxPkts					Counter32,
		 wlanStaTxBytes					Counter32,
		 wlanStaRxPkts					Counter32,
		 wlanStaRxBytes					Counter32,
		 wlanStaTxBCastPkts				Counter32,
		 wlanStaRxBCastBytes			Counter32,
		 wlanStaTxMCastPkts				Counter32,
		 wlanStaRxMCastBytes			Counter32,
		 wlanStaDataPkts				Counter32,
		 wlanStaCtrlPkts				Counter32,
		 wlanStaNumAssocRequests		Counter32,
		 wlanStaNumAuthRequests			Counter32,
		 wlanStaTxDeauthentications		Counter32,
		 wlanStaRxDeauthentications		Counter32,
		 wlanStaFrameRetryRate			Integer32,
		 wlanStaFrameLowSpeedRate		Integer32,
		 wlanStaFrameNonUnicastRate		Integer32,
		 wlanStaFrameFragmentationRate	Integer32,
		 wlanStaFrameBandwidthRate		Integer32,
		 wlanStaFrameRetryErrorRate		Integer32,
		 wlanStaFrameReceiveErrorRate	Integer32,
		 wlanStaTxBCastBytes			Counter32,
		 wlanStaTxMCastBytes			Counter32,
		 wlanStaTxBytes64				Counter64,
		 wlanStaRxBytes64				Counter64
   }

	wlanStaChannelNum OBJECT-TYPE
         SYNTAX       Unsigned32
         MAX-ACCESS   read-only
         STATUS       current
         DESCRIPTION
            "
			The channel the station is currently using.
            "
        ::= { wlsxWlanStationStatsEntry 1 }

	wlanStaTxPkts OBJECT-TYPE
         SYNTAX       Counter32
         MAX-ACCESS   read-only
         STATUS       current
         DESCRIPTION
            "
			The number of packets transmitted by this station.
            "
        ::= { wlsxWlanStationStatsEntry 2 }

	wlanStaTxBytes OBJECT-TYPE
         SYNTAX       Counter32
         MAX-ACCESS   read-only
         STATUS       current
         DESCRIPTION
            "
			The number of bytes transmitted by this station.
            "
        ::= { wlsxWlanStationStatsEntry 3 }

	wlanStaRxPkts OBJECT-TYPE
         SYNTAX       Counter32
         MAX-ACCESS   read-only
         STATUS       current
         DESCRIPTION
            "
			The number of packets received by this station.
            "
        ::= { wlsxWlanStationStatsEntry 4 }

	wlanStaRxBytes OBJECT-TYPE
         SYNTAX       Counter32
         MAX-ACCESS   read-only
         STATUS       current
         DESCRIPTION
            "
			The number of bytes received by this station.
            "
        ::= { wlsxWlanStationStatsEntry 5 }

	wlanStaTxBCastPkts OBJECT-TYPE
         SYNTAX       Counter32
         MAX-ACCESS   read-only
         STATUS       current
         DESCRIPTION
            "
			The number of broadcast packets transmitted by this station.
            "
        ::= { wlsxWlanStationStatsEntry 6 }

	wlanStaRxBCastBytes OBJECT-TYPE
         SYNTAX       Counter32
         MAX-ACCESS   read-only
         STATUS  	  deprecated
         DESCRIPTION
            "
			The number of broadcast bytes transmitted by this station.
            "
        ::= { wlsxWlanStationStatsEntry 7 }

	wlanStaTxMCastPkts OBJECT-TYPE
         SYNTAX       Counter32
         MAX-ACCESS   read-only
         STATUS       current
         DESCRIPTION
            "
			The number of multicast packets transmitted by this station.
            "
        ::= { wlsxWlanStationStatsEntry 8 }

	wlanStaRxMCastBytes OBJECT-TYPE
         SYNTAX       Counter32
         MAX-ACCESS   read-only
         STATUS  	  deprecated
         DESCRIPTION
            "
			The number of multicast bytes transmitted by this station.
            "
        ::= { wlsxWlanStationStatsEntry 9 }

	wlanStaDataPkts OBJECT-TYPE
         SYNTAX       Counter32
         MAX-ACCESS   read-only
         STATUS       current
         DESCRIPTION
            "
			 The total number of Data packets transmitted by this station.
            "
        ::= { wlsxWlanStationStatsEntry 10 }

	wlanStaCtrlPkts OBJECT-TYPE
         SYNTAX       Counter32
         MAX-ACCESS   read-only
         STATUS       current
         DESCRIPTION
            "
			 The total number of Control packets transmitted by this station.
            "
        ::= { wlsxWlanStationStatsEntry 11 }

	wlanStaNumAssocRequests OBJECT-TYPE
         SYNTAX       Counter32
         MAX-ACCESS   read-only
         STATUS       current
         DESCRIPTION
            "
			 The number of Association requests transmitted by this station.
            "
        ::= { wlsxWlanStationStatsEntry 12 }

	wlanStaNumAuthRequests OBJECT-TYPE
         SYNTAX       Counter32
         MAX-ACCESS   read-only
         STATUS       current
         DESCRIPTION
            "
			 The number of Authentication requests transmitted by this station.
            "
        ::= { wlsxWlanStationStatsEntry 13 }

	wlanStaTxDeauthentications OBJECT-TYPE
         SYNTAX       Counter32
         MAX-ACCESS   read-only
         STATUS       current
         DESCRIPTION
            "
			 The number of Deauthentication frames transmitted by this station.
            "
        ::= { wlsxWlanStationStatsEntry 14 }

	wlanStaRxDeauthentications OBJECT-TYPE
         SYNTAX       Counter32
         MAX-ACCESS   read-only
         STATUS       current
         DESCRIPTION
            "
			 The number of Deauthentication frames received by this station.
            "
        ::= { wlsxWlanStationStatsEntry 15 }

	wlanStaFrameRetryRate OBJECT-TYPE
         SYNTAX       Integer32
         MAX-ACCESS   read-only
         STATUS       current
         DESCRIPTION
            "
			 The number of retry 
			 packets as a percentage of the total packets
			 transmitted and received by this station.
            "
        ::= { wlsxWlanStationStatsEntry 16 }

	wlanStaFrameLowSpeedRate OBJECT-TYPE
         SYNTAX       Integer32
         MAX-ACCESS   read-only
         STATUS       current
         DESCRIPTION
            "
			 The number of low data rate (<= 18Mbps for A/G bands and <=2Mbps
			 for B band) packets as a percentage of the total packets
			 transmitted and received by this station.
            "
        ::= { wlsxWlanStationStatsEntry 17 }

	wlanStaFrameNonUnicastRate OBJECT-TYPE
         SYNTAX       Integer32
         MAX-ACCESS   read-only
         STATUS       current
         DESCRIPTION
            "
			 The number of broadcast and multicast
			 packets as a percentage of the total packets
			 transmitted by this station.
            "
        ::= { wlsxWlanStationStatsEntry 18 }

	wlanStaFrameFragmentationRate OBJECT-TYPE
         SYNTAX       Integer32
         MAX-ACCESS   read-only
         STATUS       current
         DESCRIPTION
            "
			 The number of fragments
			 as a percentage of the total packets
			 transmitted by this station.
            "
        ::= { wlsxWlanStationStatsEntry 19 }

	wlanStaFrameBandwidthRate OBJECT-TYPE
         SYNTAX       Integer32
         MAX-ACCESS   read-only
         STATUS       current
         DESCRIPTION
            "
			 The bandwidth of this station in Kbps.
            "
        ::= { wlsxWlanStationStatsEntry 20 }

	wlanStaFrameRetryErrorRate OBJECT-TYPE
         SYNTAX       Integer32
         MAX-ACCESS   read-only
         STATUS  	  deprecated
         DESCRIPTION
            "
			 The number of error packets
			 as a percentage of the total packets
			 received by this station.
            "
        ::= { wlsxWlanStationStatsEntry 21 }

	wlanStaFrameReceiveErrorRate OBJECT-TYPE
         SYNTAX       Integer32
         MAX-ACCESS   read-only
         STATUS       current
         DESCRIPTION
            "
			 The number of error packets
			 as a percentage of the total packets
			 received by this station.
            "
        ::= { wlsxWlanStationStatsEntry 22 }

	wlanStaTxBCastBytes OBJECT-TYPE
         SYNTAX       Counter32
         MAX-ACCESS   read-only
         STATUS       current
         DESCRIPTION
            "
			The number of broadcast bytes transmitted by this station.
            "
        ::= { wlsxWlanStationStatsEntry 23 }

	wlanStaTxMCastBytes OBJECT-TYPE
         SYNTAX       Counter32
         MAX-ACCESS   read-only
         STATUS       current
         DESCRIPTION
            "
			The number of multicast bytes transmitted by this station.
            "
        ::= { wlsxWlanStationStatsEntry 24 }

	wlanStaTxBytes64 OBJECT-TYPE
         SYNTAX       Counter64
         MAX-ACCESS   read-only
         STATUS       current
         DESCRIPTION
            "
			The number of bytes transmitted by this station, 64-bit value
            "
        ::= { wlsxWlanStationStatsEntry 25 }

	wlanStaRxBytes64 OBJECT-TYPE
         SYNTAX       Counter64
         MAX-ACCESS   read-only
         STATUS       current
         DESCRIPTION
            "
			The number of bytes received by this station, 64-bit value
            "
        ::= { wlsxWlanStationStatsEntry 26 }


-- This table breaks down the Station statistics into different
-- rate categories.

   wlsxWlanStaRateStatsTable  OBJECT-TYPE 
	  SYNTAX       SEQUENCE OF WlsxWlanStaRateStatsEntry 
	  MAX-ACCESS   not-accessible		
      STATUS       current 
      DESCRIPTION 
	  	"
		This table contains all the Packet and Byte Counts for a station
		represented in terms of rate categories.
		"
      ::= { wlsxWlanStationStatsGroup 2} 

     wlsxWlanStaRateStatsEntry OBJECT-TYPE 
	  SYNTAX       WlsxWlanStaRateStatsEntry 
	  MAX-ACCESS   not-accessible		
      STATUS       current 
      DESCRIPTION 
			 "Data rate based packet and byte count entry for a station"
	  INDEX {wlanStaPhyAddress}
      ::= { wlsxWlanStaRateStatsTable 1 } 
	
     WlsxWlanStaRateStatsEntry ::=
     SEQUENCE {
		 wlanStaTxPktsAt1Mbps			Counter32,
		 wlanStaTxBytesAt1Mbps			Counter32,
		 wlanStaTxPktsAt2Mbps			Counter32,
		 wlanStaTxBytesAt2Mbps			Counter32,
		 wlanStaTxPktsAt5Mbps			Counter32,
		 wlanStaTxBytesAt5Mbps			Counter32,
		 wlanStaTxPktsAt11Mbps			Counter32,
		 wlanStaTxBytesAt11Mbps			Counter32,
		 wlanStaTxPktsAt6Mbps			Counter32,
		 wlanStaTxBytesAt6Mbps			Counter32,
		 wlanStaTxPktsAt12Mbps			Counter32,
		 wlanStaTxBytesAt12Mbps			Counter32,
		 wlanStaTxPktsAt18Mbps			Counter32,
		 wlanStaTxBytesAt18Mbps			Counter32,
		 wlanStaTxPktsAt24Mbps			Counter32,
		 wlanStaTxBytesAt24Mbps			Counter32,
		 wlanStaTxPktsAt36Mbps			Counter32,
		 wlanStaTxBytesAt36Mbps			Counter32,
		 wlanStaTxPktsAt48Mbps			Counter32,
		 wlanStaTxBytesAt48Mbps			Counter32,
		 wlanStaTxPktsAt54Mbps			Counter32,
		 wlanStaTxBytesAt54Mbps			Counter32,
		 wlanStaRxPktsAt1Mbps			Counter32,
		 wlanStaRxBytesAt1Mbps			Counter32,
		 wlanStaRxPktsAt2Mbps			Counter32,
		 wlanStaRxBytesAt2Mbps			Counter32,
		 wlanStaRxPktsAt5Mbps			Counter32,
		 wlanStaRxBytesAt5Mbps			Counter32,
		 wlanStaRxPktsAt11Mbps			Counter32,
		 wlanStaRxBytesAt11Mbps			Counter32,
		 wlanStaRxPktsAt6Mbps			Counter32,
		 wlanStaRxBytesAt6Mbps			Counter32,
		 wlanStaRxPktsAt12Mbps			Counter32,
		 wlanStaRxBytesAt12Mbps			Counter32,
		 wlanStaRxPktsAt18Mbps			Counter32,
		 wlanStaRxBytesAt18Mbps			Counter32,
		 wlanStaRxPktsAt24Mbps			Counter32,
		 wlanStaRxBytesAt24Mbps			Counter32,
		 wlanStaRxPktsAt36Mbps			Counter32,
		 wlanStaRxBytesAt36Mbps			Counter32,
		 wlanStaRxPktsAt48Mbps			Counter32,
		 wlanStaRxBytesAt48Mbps			Counter32,
		 wlanStaRxPktsAt54Mbps			Counter32,
		 wlanStaRxBytesAt54Mbps			Counter32,
		 wlanStaTxPktsAt9Mbps			Counter32,
		 wlanStaTxBytesAt9Mbps			Counter32,
		 wlanStaRxPktsAt9Mbps			Counter32,
		 wlanStaRxBytesAt9Mbps			Counter32
     }

     wlanStaTxPktsAt1Mbps OBJECT-TYPE
         SYNTAX       Counter32  
         MAX-ACCESS   read-only
         STATUS       current
         DESCRIPTION
            "
			 This attribute indicates the number of Packets Transmitted by the 
			 station at 1Mbps rate.
            "
        ::= { wlsxWlanStaRateStatsEntry 1 }

     wlanStaTxBytesAt1Mbps OBJECT-TYPE
         SYNTAX       Counter32  
         MAX-ACCESS   read-only
         STATUS       current
         DESCRIPTION
            "
			 This attribute indicates the number of Octets Transmitted by the 
			 station at 1Mbps rate.
            "
        ::= { wlsxWlanStaRateStatsEntry 2 }

     wlanStaTxPktsAt2Mbps OBJECT-TYPE
         SYNTAX       Counter32  
         MAX-ACCESS   read-only
         STATUS       current
         DESCRIPTION
            "
			 This attribute indicates the number of Packets Transmitted by the 
			 station at 2Mbps rate.
            "
        ::= { wlsxWlanStaRateStatsEntry 3 }

     wlanStaTxBytesAt2Mbps OBJECT-TYPE
         SYNTAX       Counter32  
         MAX-ACCESS   read-only
         STATUS       current
         DESCRIPTION
            "
			 This attribute indicates the number of Octets Transmitted by the 
			 station at 2Mbps rate.
            "
        ::= { wlsxWlanStaRateStatsEntry 4 }

     wlanStaTxPktsAt5Mbps OBJECT-TYPE
         SYNTAX       Counter32  
         MAX-ACCESS   read-only
         STATUS       current
         DESCRIPTION
            "
			 This attribute indicates the number of Packets Transmitted by the 
			 station at 5Mbps rate.
            "
        ::= { wlsxWlanStaRateStatsEntry 5 }

     wlanStaTxBytesAt5Mbps OBJECT-TYPE
         SYNTAX       Counter32  
         MAX-ACCESS   read-only
         STATUS       current
         DESCRIPTION
            "
			 This attribute indicates the number of Octets Transmitted by the 
			 station at 5Mbps rate.
            "
        ::= { wlsxWlanStaRateStatsEntry 6 }

     wlanStaTxPktsAt11Mbps OBJECT-TYPE
         SYNTAX       Counter32  
         MAX-ACCESS   read-only
         STATUS       current
         DESCRIPTION
            "
			 This attribute indicates the number of Packets Transmitted by the 
			 station at 11Mbps rate.
            "
        ::= { wlsxWlanStaRateStatsEntry 7 }

     wlanStaTxBytesAt11Mbps OBJECT-TYPE
         SYNTAX       Counter32  
         MAX-ACCESS   read-only
         STATUS       current
         DESCRIPTION
            "
			 This attribute indicates the number of Octets Transmitted by the 
			 station at 11Mbps rate.
            "
        ::= { wlsxWlanStaRateStatsEntry 8 }

     wlanStaTxPktsAt6Mbps OBJECT-TYPE
         SYNTAX       Counter32  
         MAX-ACCESS   read-only
         STATUS       current
         DESCRIPTION
            "
			 This attribute indicates the number of Packets Transmitted by the 
			 station at 6Mbps rate.
            "
        ::= { wlsxWlanStaRateStatsEntry 9 }

     wlanStaTxBytesAt6Mbps OBJECT-TYPE
         SYNTAX       Counter32  
         MAX-ACCESS   read-only
         STATUS       current
         DESCRIPTION
            "
			 This attribute indicates the number of Octets Transmitted by the 
			 station at 6Mbps rate.
            "
        ::= { wlsxWlanStaRateStatsEntry 10 }

     wlanStaTxPktsAt12Mbps OBJECT-TYPE
         SYNTAX       Counter32  
         MAX-ACCESS   read-only
         STATUS       current
         DESCRIPTION
            "
			 This attribute indicates the number of Packets Transmitted by the 
			 station at 12Mbps rate.
            "
        ::= { wlsxWlanStaRateStatsEntry 11 }

     wlanStaTxBytesAt12Mbps OBJECT-TYPE
         SYNTAX       Counter32  
         MAX-ACCESS   read-only
         STATUS       current
         DESCRIPTION
            "
			 This attribute indicates the number of Octets Transmitted by the 
			 station at 12Mbps rate.
            "
        ::= { wlsxWlanStaRateStatsEntry 12 }

     wlanStaTxPktsAt18Mbps OBJECT-TYPE
         SYNTAX       Counter32  
         MAX-ACCESS   read-only
         STATUS       current
         DESCRIPTION
            "
			 This attribute indicates the number of Packets Transmitted by the 
			 station at 18Mbps rate.
            "
        ::= { wlsxWlanStaRateStatsEntry 13 }

     wlanStaTxBytesAt18Mbps OBJECT-TYPE
         SYNTAX       Counter32  
         MAX-ACCESS   read-only
         STATUS       current
         DESCRIPTION
            "
			 This attribute indicates the number of Octets Transmitted by the 
			 station at 18Mbps rate.
            "
        ::= { wlsxWlanStaRateStatsEntry 14 }

     wlanStaTxPktsAt24Mbps OBJECT-TYPE
         SYNTAX       Counter32  
         MAX-ACCESS   read-only
         STATUS       current
         DESCRIPTION
            "
			 This attribute indicates the number of Packets Transmitted by the 
			 station at 24Mbps rate.
            "
        ::= { wlsxWlanStaRateStatsEntry 15 }

     wlanStaTxBytesAt24Mbps OBJECT-TYPE
         SYNTAX       Counter32  
         MAX-ACCESS   read-only
         STATUS       current
         DESCRIPTION
            "
			 This attribute indicates the number of Octets Transmitted by the 
			 station at 24Mbps rate.
            "
        ::= { wlsxWlanStaRateStatsEntry 16 }

     wlanStaTxPktsAt36Mbps OBJECT-TYPE
         SYNTAX       Counter32  
         MAX-ACCESS   read-only
         STATUS       current
         DESCRIPTION
            "
			 This attribute indicates the number of Packets Transmitted by the 
			 station at 36Mbps rate.
            "
        ::= { wlsxWlanStaRateStatsEntry 17 }

     wlanStaTxBytesAt36Mbps OBJECT-TYPE
         SYNTAX       Counter32  
         MAX-ACCESS   read-only
         STATUS       current
         DESCRIPTION
            "
			 This attribute indicates the number of Octets Transmitted by the 
			 station at 36Mbps rate.
            "
        ::= { wlsxWlanStaRateStatsEntry 18 }

     wlanStaTxPktsAt48Mbps OBJECT-TYPE
         SYNTAX       Counter32  
         MAX-ACCESS   read-only
         STATUS       current
         DESCRIPTION
            "
			 This attribute indicates the number of Packets Transmitted by the 
			 station at 48Mbps rate.
            "
        ::= { wlsxWlanStaRateStatsEntry 19 }

     wlanStaTxBytesAt48Mbps OBJECT-TYPE
         SYNTAX       Counter32  
         MAX-ACCESS   read-only
         STATUS       current
         DESCRIPTION
            "
			 This attribute indicates the number of Octets Transmitted by the 
			 station at 48Mbps rate.
            "
        ::= { wlsxWlanStaRateStatsEntry 20 }

     wlanStaTxPktsAt54Mbps OBJECT-TYPE
         SYNTAX       Counter32  
         MAX-ACCESS   read-only
         STATUS       current
         DESCRIPTION
            "
			 This attribute indicates the number of Packets Transmitted by the 
			 station at 54Mbps rate.
            "
        ::= { wlsxWlanStaRateStatsEntry 21 }

     wlanStaTxBytesAt54Mbps OBJECT-TYPE
         SYNTAX       Counter32  
         MAX-ACCESS   read-only
         STATUS       current
         DESCRIPTION
            "
			 This attribute indicates the number of Octets Transmitted by the 
			 station at 54Mbps rate.
            "
        ::= { wlsxWlanStaRateStatsEntry 22 }

     wlanStaRxPktsAt1Mbps OBJECT-TYPE
         SYNTAX       Counter32  
         MAX-ACCESS   read-only
         STATUS       current
         DESCRIPTION
            "
			 This attribute indicates the number of Packets Received by the 
			 station at 1Mbps rate.
            "
        ::= { wlsxWlanStaRateStatsEntry 23 }

     wlanStaRxBytesAt1Mbps OBJECT-TYPE
         SYNTAX       Counter32  
         MAX-ACCESS   read-only
         STATUS       current
         DESCRIPTION
            "
			 This attribute indicates the number of Octets Received by the 
			 station at 1Mbps rate.
            "
        ::= { wlsxWlanStaRateStatsEntry 24 }

     wlanStaRxPktsAt2Mbps OBJECT-TYPE
         SYNTAX       Counter32  
         MAX-ACCESS   read-only
         STATUS       current
         DESCRIPTION
            "
			 This attribute indicates the number of Packets Received by the 
			 station at 2Mbps rate.
            "
        ::= { wlsxWlanStaRateStatsEntry 25 }

     wlanStaRxBytesAt2Mbps OBJECT-TYPE
         SYNTAX       Counter32  
         MAX-ACCESS   read-only
         STATUS       current
         DESCRIPTION
            "
			 This attribute indicates the number of Octets Received by the 
			 station at 2Mbps rate.
            "
        ::= { wlsxWlanStaRateStatsEntry 26 }

     wlanStaRxPktsAt5Mbps OBJECT-TYPE
         SYNTAX       Counter32  
         MAX-ACCESS   read-only
         STATUS       current
         DESCRIPTION
            "
			 This attribute indicates the number of Packets Received by the 
			 station at 5Mbps rate.
            "
        ::= { wlsxWlanStaRateStatsEntry 27 }

     wlanStaRxBytesAt5Mbps OBJECT-TYPE
         SYNTAX       Counter32  
         MAX-ACCESS   read-only
         STATUS       current
         DESCRIPTION
            "
			 This attribute indicates the number of Octets Received by the 
			 station at 5Mbps rate.
            "
        ::= { wlsxWlanStaRateStatsEntry 28 }

     wlanStaRxPktsAt11Mbps OBJECT-TYPE
         SYNTAX       Counter32  
         MAX-ACCESS   read-only
         STATUS       current
         DESCRIPTION
            "
			 This attribute indicates the number of Packets Received by the 
			 station at 11Mbps rate.
            "
        ::= { wlsxWlanStaRateStatsEntry 29 }

     wlanStaRxBytesAt11Mbps OBJECT-TYPE
         SYNTAX       Counter32  
         MAX-ACCESS   read-only
         STATUS       current
         DESCRIPTION
            "
			 This attribute indicates the number of Octets Received by the 
			 station at 11Mbps rate.
            "
        ::= { wlsxWlanStaRateStatsEntry 30 }

     wlanStaRxPktsAt6Mbps OBJECT-TYPE
         SYNTAX       Counter32  
         MAX-ACCESS   read-only
         STATUS       current
         DESCRIPTION
            "
			 This attribute indicates the number of Packets Received by the 
			 station at 6Mbps rate.
            "
        ::= { wlsxWlanStaRateStatsEntry 31 }

     wlanStaRxBytesAt6Mbps OBJECT-TYPE
         SYNTAX       Counter32  
         MAX-ACCESS   read-only
         STATUS       current
         DESCRIPTION
            "
			 This attribute indicates the number of Octets Received by the 
			 station at 6Mbps rate.
            "
        ::= { wlsxWlanStaRateStatsEntry 32 }

     wlanStaRxPktsAt12Mbps OBJECT-TYPE
         SYNTAX       Counter32  
         MAX-ACCESS   read-only
         STATUS       current
         DESCRIPTION
            "
			 This attribute indicates the number of Packets Received by the 
			 station at 12Mbps rate.
            "
        ::= { wlsxWlanStaRateStatsEntry 33 }

     wlanStaRxBytesAt12Mbps OBJECT-TYPE
         SYNTAX       Counter32  
         MAX-ACCESS   read-only
         STATUS       current
         DESCRIPTION
            "
			 This attribute indicates the number of Octets Received by the 
			 station at 12Mbps rate.
            "
        ::= { wlsxWlanStaRateStatsEntry 34 }

     wlanStaRxPktsAt18Mbps OBJECT-TYPE
         SYNTAX       Counter32  
         MAX-ACCESS   read-only
         STATUS       current
         DESCRIPTION
            "
			 This attribute indicates the number of Packets Received by the 
			 station at 18Mbps rate.
            "
        ::= { wlsxWlanStaRateStatsEntry 35 }

     wlanStaRxBytesAt18Mbps OBJECT-TYPE
         SYNTAX       Counter32  
         MAX-ACCESS   read-only
         STATUS       current
         DESCRIPTION
            "
			 This attribute indicates the number of Octets Received by the 
			 station at 18Mbps rate.
            "
        ::= { wlsxWlanStaRateStatsEntry 36 }

     wlanStaRxPktsAt24Mbps OBJECT-TYPE
         SYNTAX       Counter32  
         MAX-ACCESS   read-only
         STATUS       current
         DESCRIPTION
            "
			 This attribute indicates the number of Packets Received by the 
			 station at 24Mbps rate.
            "
        ::= { wlsxWlanStaRateStatsEntry 37 }

     wlanStaRxBytesAt24Mbps OBJECT-TYPE
         SYNTAX       Counter32  
         MAX-ACCESS   read-only
         STATUS       current
         DESCRIPTION
            "
			 This attribute indicates the number of Octets Received by the 
			 station at 24Mbps rate.
            "
        ::= { wlsxWlanStaRateStatsEntry 38 }

     wlanStaRxPktsAt36Mbps OBJECT-TYPE
         SYNTAX       Counter32  
         MAX-ACCESS   read-only
         STATUS       current
         DESCRIPTION
            "
			 This attribute indicates the number of Packets Received by the 
			 station at 36Mbps rate.
            "
        ::= { wlsxWlanStaRateStatsEntry 39 }

     wlanStaRxBytesAt36Mbps OBJECT-TYPE
         SYNTAX       Counter32  
         MAX-ACCESS   read-only
         STATUS       current
         DESCRIPTION
            "
			 This attribute indicates the number of Octets Received by the 
			 station at 36Mbps rate.
            "
        ::= { wlsxWlanStaRateStatsEntry 40 }

     wlanStaRxPktsAt48Mbps OBJECT-TYPE
         SYNTAX       Counter32  
         MAX-ACCESS   read-only
         STATUS       current
         DESCRIPTION
            "
			 This attribute indicates the number of Packets Received by the 
			 station at 48Mbps rate.
            "
        ::= { wlsxWlanStaRateStatsEntry 41 }

     wlanStaRxBytesAt48Mbps OBJECT-TYPE
         SYNTAX       Counter32  
         MAX-ACCESS   read-only
         STATUS       current
         DESCRIPTION
            "
			 This attribute indicates the number of Octets Received by the 
			 station at 48Mbps rate.
            "
        ::= { wlsxWlanStaRateStatsEntry 42 }

     wlanStaRxPktsAt54Mbps OBJECT-TYPE
         SYNTAX       Counter32  
         MAX-ACCESS   read-only
         STATUS       current
         DESCRIPTION
            "
			 This attribute indicates the number of Packets Received by the 
			 station at 54Mbps rate.
            "
        ::= { wlsxWlanStaRateStatsEntry 43 }

     wlanStaRxBytesAt54Mbps OBJECT-TYPE
         SYNTAX       Counter32  
         MAX-ACCESS   read-only
         STATUS       current
         DESCRIPTION
            "
			 This attribute indicates the number of Octets Received by the 
			 station at 54Mbps rate.
            "
        ::= { wlsxWlanStaRateStatsEntry 44 }

     wlanStaTxPktsAt9Mbps OBJECT-TYPE
         SYNTAX       Counter32  
         MAX-ACCESS   read-only
         STATUS       current
         DESCRIPTION
            "
			 This attribute indicates the number of Packets Transmitted by the 
			 station at 9Mbps rate.
            "
        ::= { wlsxWlanStaRateStatsEntry 45 }

     wlanStaTxBytesAt9Mbps OBJECT-TYPE
         SYNTAX       Counter32  
         MAX-ACCESS   read-only
         STATUS       current
         DESCRIPTION
            "
			 This attribute indicates the number of Octets Transmitted by the 
			 station at 9Mbps rate.
            "
        ::= { wlsxWlanStaRateStatsEntry 46 }


     wlanStaRxPktsAt9Mbps OBJECT-TYPE
         SYNTAX       Counter32  
         MAX-ACCESS   read-only
         STATUS       current
         DESCRIPTION
            "
			 This attribute indicates the number of Packets Received by the 
			 station at 9Mbps rate.
            "
        ::= { wlsxWlanStaRateStatsEntry 47 }

     wlanStaRxBytesAt9Mbps OBJECT-TYPE
         SYNTAX       Counter32  
         MAX-ACCESS   read-only
         STATUS       current
         DESCRIPTION
            "
			 This attribute indicates the number of Octets Received by the 
			 station at 9Mbps rate.
            "
        ::= { wlsxWlanStaRateStatsEntry 48 }

-- This table breaks down the Station statistics based on the
-- Destination Address Types. 

   wlsxWlanStaDATypeStatsTable  OBJECT-TYPE 
	  SYNTAX       SEQUENCE OF WlsxWlanStaDATypeStatsEntry 
	  MAX-ACCESS   not-accessible		
      STATUS       current 
      DESCRIPTION 
	  	"
		This table contains all the Packet and Byte Counts for a station but
		but broken down in terms of Destination Address Type. 
		"
      ::= { wlsxWlanStationStatsGroup 3} 

     wlsxWlanStaDATypeStatsEntry OBJECT-TYPE 
	  SYNTAX       WlsxWlanStaDATypeStatsEntry 
	  MAX-ACCESS   not-accessible		
      STATUS       current 
      DESCRIPTION 
			 "
			  Destination Address based packet and byte count entry for a
			  station
			 "
	  INDEX {wlanStaPhyAddress}
      ::= { wlsxWlanStaDATypeStatsTable 1 } 
	
     WlsxWlanStaDATypeStatsEntry ::=
     SEQUENCE {
		 wlanStaTxDABroadcastPkts		Counter32  ,
		 wlanStaTxDABroadcastBytes		Counter32  ,
		 wlanStaTxDAMulticastPkts		Counter32  ,
		 wlanStaTxDAMulticastBytes		Counter32  ,
		 wlanStaTxDAUnicastPkts			Counter32  ,
		 wlanStaTxDAUnicastBytes		Counter32  

     }

     wlanStaTxDABroadcastPkts OBJECT-TYPE
         SYNTAX       Counter32  
         MAX-ACCESS   read-only
         STATUS       current
         DESCRIPTION
            "
			 This attribute indicates the number of Broadcast packets 
			 transmitted by this Station.
            "
        ::= { wlsxWlanStaDATypeStatsEntry 1 }

     wlanStaTxDABroadcastBytes OBJECT-TYPE
         SYNTAX       Counter32  
         MAX-ACCESS   read-only
         STATUS       current
         DESCRIPTION
            "
			 This attribute indicates the number of Broadcast Bytes 
			 transmitted by this Station.
            "
        ::= { wlsxWlanStaDATypeStatsEntry 2 }

     wlanStaTxDAMulticastPkts OBJECT-TYPE
         SYNTAX       Counter32  
         MAX-ACCESS   read-only
         STATUS       current
         DESCRIPTION
            "
			 This attribute indicates the number of Multicast packets 
			 transmitted by this station.
            "
        ::= { wlsxWlanStaDATypeStatsEntry 3 }

     wlanStaTxDAMulticastBytes OBJECT-TYPE
         SYNTAX       Counter32  
         MAX-ACCESS   read-only
         STATUS       current
         DESCRIPTION
            "
			 This attribute indicates the number of Multicast Bytes 
			 transmitted by this station.
            "
        ::= { wlsxWlanStaDATypeStatsEntry 4 }

     wlanStaTxDAUnicastPkts OBJECT-TYPE
         SYNTAX       Counter32  
         MAX-ACCESS   read-only
         STATUS       current
         DESCRIPTION
            "
			 This attribute indicates the total of Unicast packets 
			 transmitted by this station.
            "
        ::= { wlsxWlanStaDATypeStatsEntry 5 }

     wlanStaTxDAUnicastBytes OBJECT-TYPE
         SYNTAX       Counter32  
         MAX-ACCESS   read-only
         STATUS       current
         DESCRIPTION
            "
			 This attribute indicates the total of Unicast Bytes 
			 transmitted by this station.
            "
        ::= { wlsxWlanStaDATypeStatsEntry 6 }

-- This table breaks down the Station statistics based on the
-- the Type of the Packet. 

   wlsxWlanStaFrameTypeStatsTable  OBJECT-TYPE 
	  SYNTAX       SEQUENCE OF WlsxWlanStaFrameTypeStatsEntry 
	  MAX-ACCESS   not-accessible		
      STATUS       current 
      DESCRIPTION 
	  	"
		This table contains all the Packet and Byte Counts for stations
		but broken down into different Frame Types. 
		"
      ::= { wlsxWlanStationStatsGroup 4} 

     wlsxWlanStaFrameTypeStatsEntry OBJECT-TYPE 
	  SYNTAX       WlsxWlanStaFrameTypeStatsEntry 
	  MAX-ACCESS   not-accessible		
      STATUS       current 
      DESCRIPTION 
			 "Frame Type based packet and byte count entry for a station"
	  INDEX {wlanStaPhyAddress}
      ::= { wlsxWlanStaFrameTypeStatsTable 1 } 
	
     WlsxWlanStaFrameTypeStatsEntry ::=
     SEQUENCE {
		 wlanStaTxMgmtPkts		Counter32  ,
		 wlanStaTxMgmtBytes		Counter32  ,
		 wlanStaTxCtrlPkts		Counter32  ,
		 wlanStaTxCtrlBytes		Counter32  ,
		 wlanStaTxDataPkts		Counter32  ,
		 wlanStaTxDataBytes		Counter32  ,
		 wlanStaRxMgmtPkts		Counter32  ,
		 wlanStaRxMgmtBytes		Counter32  ,
		 wlanStaRxCtrlPkts		Counter32  ,
		 wlanStaRxCtrlBytes		Counter32  ,
		 wlanStaRxDataPkts		Counter32  ,
		 wlanStaRxDataBytes		Counter32  

     }

     wlanStaTxMgmtPkts OBJECT-TYPE
         SYNTAX       Counter32  
         MAX-ACCESS   read-only
         STATUS       current
         DESCRIPTION
            "
			 This attribute indicates the Transmitted Management packets 
			 from a station.
            "
        ::= { wlsxWlanStaFrameTypeStatsEntry 1 }

     wlanStaTxMgmtBytes OBJECT-TYPE
         SYNTAX       Counter32  
         MAX-ACCESS   read-only
         STATUS       current
         DESCRIPTION
            "
			 This attribute indicates the Transmitted Management Bytes 
			 from a station
            "
        ::= { wlsxWlanStaFrameTypeStatsEntry 2 }

     wlanStaTxCtrlPkts OBJECT-TYPE
         SYNTAX       Counter32  
         MAX-ACCESS   read-only
         STATUS       current
         DESCRIPTION
            "
			 This attribute indicates the Transmitted Control packets 
			 from a station
            "
        ::= { wlsxWlanStaFrameTypeStatsEntry 3 }

     wlanStaTxCtrlBytes OBJECT-TYPE
         SYNTAX       Counter32  
         MAX-ACCESS   read-only
         STATUS       current
         DESCRIPTION
            "
			 This attribute indicates the Transmitted Control Bytes 
			 from a station
            "
        ::= { wlsxWlanStaFrameTypeStatsEntry 4 }

     wlanStaTxDataPkts OBJECT-TYPE
         SYNTAX       Counter32  
         MAX-ACCESS   read-only
         STATUS       current
         DESCRIPTION
            "
			 This attribute indicates the Transmitted Data packets 
			 from a station
            "
        ::= { wlsxWlanStaFrameTypeStatsEntry 5 }

     wlanStaTxDataBytes OBJECT-TYPE
         SYNTAX       Counter32  
         MAX-ACCESS   read-only
         STATUS       current
         DESCRIPTION
            "
			 This attribute indicates the Transmitted Data Bytes 
			 observed on this channel.
            "
        ::= { wlsxWlanStaFrameTypeStatsEntry 6 }

     wlanStaRxMgmtPkts OBJECT-TYPE
         SYNTAX       Counter32  
         MAX-ACCESS   read-only
         STATUS       current
         DESCRIPTION
            "
			 This attribute indicates the number of received Management packets 
			 at a station.
            "
        ::= { wlsxWlanStaFrameTypeStatsEntry 7 }

     wlanStaRxMgmtBytes OBJECT-TYPE
         SYNTAX       Counter32  
         MAX-ACCESS   read-only
         STATUS       current
         DESCRIPTION
            "
			 This attribute indicates the number of received Management Bytes 
			 at a station.
            "
        ::= { wlsxWlanStaFrameTypeStatsEntry 8 }

     wlanStaRxCtrlPkts OBJECT-TYPE
         SYNTAX       Counter32  
         MAX-ACCESS   read-only
         STATUS       current
         DESCRIPTION
            "
			 This attribute indicates the number of received Control packets 
			 at a station.
            "
        ::= { wlsxWlanStaFrameTypeStatsEntry 9 }

     wlanStaRxCtrlBytes OBJECT-TYPE
         SYNTAX       Counter32  
         MAX-ACCESS   read-only
         STATUS       current
         DESCRIPTION
            "
			 This attribute indicates the number of received Control Bytes 
			 at a station.
            "
        ::= { wlsxWlanStaFrameTypeStatsEntry 10 }

     wlanStaRxDataPkts OBJECT-TYPE
         SYNTAX       Counter32  
         MAX-ACCESS   read-only
         STATUS       current
         DESCRIPTION
            "
			 This attribute indicates the number of received Data packets 
			 at a station.
            "
        ::= { wlsxWlanStaFrameTypeStatsEntry 11 }

     wlanStaRxDataBytes OBJECT-TYPE
         SYNTAX       Counter32  
         MAX-ACCESS   read-only
         STATUS       current
         DESCRIPTION
            "
			 This attribute indicates the number of received Data Bytes 
			 at a station.
            "
        ::= { wlsxWlanStaFrameTypeStatsEntry 12 }


-- This table breaks down the Station statistics received or transmitted by a 
-- station into packet size buckets. 

   wlsxWlanStaPktSizeStatsTable  OBJECT-TYPE 
	  SYNTAX       SEQUENCE OF WlsxWlanStaPktSizeStatsEntry 
	  MAX-ACCESS   not-accessible		
      STATUS       current 
      DESCRIPTION 
	  	"
		This table contains all the  Packet and Byte Counts for stations
		but broken down into different Packet Sizes. 
		"
      ::= { wlsxWlanStationStatsGroup 5} 

     wlsxWlanStaPktSizeStatsEntry OBJECT-TYPE 
	  SYNTAX       WlsxWlanStaPktSizeStatsEntry 
	  MAX-ACCESS   not-accessible		
      STATUS       current 
      DESCRIPTION 
			 "Packet Size based packet count entry for a station"
	  INDEX {wlanStaPhyAddress}
      ::= { wlsxWlanStaPktSizeStatsTable 1 } 
	
     WlsxWlanStaPktSizeStatsEntry ::=
     SEQUENCE {
		 wlanStaTxPkts63Bytes		Counter32  ,
		 wlanStaTxPkts64To127		Counter32  ,
		 wlanStaTxPkts128To255		Counter32  ,
		 wlanStaTxPkts256To511		Counter32  ,
		 wlanStaTxPkts512To1023	Counter32  ,
		 wlanStaTxPkts1024To1518	Counter32  ,
		 wlanStaRxPkts63Bytes		Counter32  ,
		 wlanStaRxPkts64To127		Counter32  ,
		 wlanStaRxPkts128To255		Counter32  ,
		 wlanStaRxPkts256To511		Counter32  ,
		 wlanStaRxPkts512To1023	Counter32  ,
		 wlanStaRxPkts1024To1518	Counter32  

     }

     wlanStaTxPkts63Bytes OBJECT-TYPE
         SYNTAX       Counter32  
         MAX-ACCESS   read-only
         STATUS       current
         DESCRIPTION
            "
			 This attribute indicates the number of packets transmitted by the 
			 station that were less than 64 bytes long.
            "
        ::= { wlsxWlanStaPktSizeStatsEntry 1 }

     wlanStaTxPkts64To127 OBJECT-TYPE
         SYNTAX       Counter32  
         MAX-ACCESS   read-only
         STATUS       current
         DESCRIPTION
            "
			 This attribute indicates the number of packets transmitted by the 
			 station that were between 64 and 127 bytes long.
            "
        ::= { wlsxWlanStaPktSizeStatsEntry 2 }

     wlanStaTxPkts128To255 OBJECT-TYPE
         SYNTAX       Counter32  
         MAX-ACCESS   read-only
         STATUS       current
         DESCRIPTION
            "
			 This attribute indicates the number of packets transmitted by the 
			 station that were between 128 and 255 bytes long.
            "
        ::= { wlsxWlanStaPktSizeStatsEntry 3 }

     wlanStaTxPkts256To511 OBJECT-TYPE
         SYNTAX       Counter32  
         MAX-ACCESS   read-only
         STATUS       current
         DESCRIPTION
            "
			 This attribute indicates the number of packets transmitted by the 
			 station that were between 256 and 511 bytes long.
            "
        ::= { wlsxWlanStaPktSizeStatsEntry 4 }

     wlanStaTxPkts512To1023 OBJECT-TYPE
         SYNTAX       Counter32  
         MAX-ACCESS   read-only
         STATUS       current
         DESCRIPTION
            "
			 This attribute indicates the number of packets transmitted by the 
			 station that were between 512 and 1023 bytes long.
            "
        ::= { wlsxWlanStaPktSizeStatsEntry 5 }

     wlanStaTxPkts1024To1518 OBJECT-TYPE
         SYNTAX       Counter32  
         MAX-ACCESS   read-only
         STATUS       current
         DESCRIPTION
            "
			 This attribute indicates the number of packets transmitted by the 
			 station that were between 1024 and 1518 bytes long.
            "
        ::= { wlsxWlanStaPktSizeStatsEntry 6 }

     wlanStaRxPkts63Bytes OBJECT-TYPE
         SYNTAX       Counter32  
         MAX-ACCESS   read-only
         STATUS       current
         DESCRIPTION
            "
			 This attribute indicates the number of packets Received by the 
			 station that were less than 64 bytes long.
            "
        ::= { wlsxWlanStaPktSizeStatsEntry 7 }

     wlanStaRxPkts64To127 OBJECT-TYPE
         SYNTAX       Counter32  
         MAX-ACCESS   read-only
         STATUS       current
         DESCRIPTION
            "
			 This attribute indicates the number of packets Received by the 
			 station that were between 64 and 127 bytes long.
            "
        ::= { wlsxWlanStaPktSizeStatsEntry 8 }

     wlanStaRxPkts128To255 OBJECT-TYPE
         SYNTAX       Counter32  
         MAX-ACCESS   read-only
         STATUS       current
         DESCRIPTION
            "
			 This attribute indicates the number of packets Received by the 
			 station that were between 128 and 255 bytes long.
            "
        ::= { wlsxWlanStaPktSizeStatsEntry 9 }

     wlanStaRxPkts256To511 OBJECT-TYPE
         SYNTAX       Counter32  
         MAX-ACCESS   read-only
         STATUS       current
         DESCRIPTION
            "
			 This attribute indicates the number of packets Received by the 
			 station that were between 256 and 511 bytes long.
            "
        ::= { wlsxWlanStaPktSizeStatsEntry 10 }

     wlanStaRxPkts512To1023 OBJECT-TYPE
         SYNTAX       Counter32  
         MAX-ACCESS   read-only
         STATUS       current
         DESCRIPTION
            "
			 This attribute indicates the number of packets Received by the 
			 station that were between 512 and 1023 bytes long.
            "
        ::= { wlsxWlanStaPktSizeStatsEntry 11 }

     wlanStaRxPkts1024To1518 OBJECT-TYPE
         SYNTAX       Counter32  
         MAX-ACCESS   read-only
         STATUS       current
         DESCRIPTION
            "
			 This attribute indicates the number of packets Received by the 
			 station that were between 1024 and 1518 bytes long.
            "
        ::= { wlsxWlanStaPktSizeStatsEntry 12 }

-- wlsxWlanSwitchStatsGroup contains all statistics related to
-- the whole network controlled by the controller.

-- wlsxWlanESSIDStatsTable contains all statistics collected
-- for an ESSID on the switch

   wlsxWlanESSIDStatsTable  OBJECT-TYPE
          SYNTAX       SEQUENCE OF WlanESSIDStatsEntry
          MAX-ACCESS   not-accessible
      STATUS       current
      DESCRIPTION
                "
                        This Table lists statistics of the ESSID
                        controlled by this controller.
                "
      ::= { wlsxWlanSwitchStatsGroup 1}

   wlsxWlanESSIDStatsEntry OBJECT-TYPE
          SYNTAX       WlanESSIDStatsEntry
          MAX-ACCESS   not-accessible
      STATUS       current
      DESCRIPTION
             "ESSID Stats Entry"
          INDEX {wlanESSID}
      ::= { wlsxWlanESSIDStatsTable 1 }

   WlanESSIDStatsEntry ::=
     SEQUENCE {
                 wlanESSIDRxPkts                           Counter32,
                 wlanESSIDRxDroppedPkts                    Counter32,
                 wlanESSIDRxRetryPkts                      Counter32,
                 wlanESSIDTxPkts                           Counter32,
                 wlanESSIDTxDroppedPkts                    Counter32,
                 wlanESSIDTxRetryPkts                      Counter32,
                 wlanESSIDTxErrorPkts                      Counter32,
                 wlanESSIDRxRate                           Gauge32,
                 wlanESSIDTxRate                           Gauge32,
                 wlanESSIDWiredRxPkts                      Counter32,
                 wlanESSIDWiredRxBytes                     Counter32,
                 wlanESSIDWiredTxBytes                     Counter32
   }

        wlanESSIDRxPkts OBJECT-TYPE
         SYNTAX       Counter32
         MAX-ACCESS   read-only
         STATUS       current
         DESCRIPTION
            "
                        The total number of packets on the ESSID uplink channel
                         of wireless side.
            "
        ::= { wlsxWlanESSIDStatsEntry 1 }

        wlanESSIDRxDroppedPkts OBJECT-TYPE
         SYNTAX       Counter32
         MAX-ACCESS   read-only
         STATUS       current
         DESCRIPTION
            "
                        The total number of dropped packets on the ESSID uplink
                         channel of wireless side.
            "
        ::= { wlsxWlanESSIDStatsEntry 2 }

        wlanESSIDRxRetryPkts OBJECT-TYPE
         SYNTAX       Counter32
         MAX-ACCESS   read-only
         STATUS       current
         DESCRIPTION
            "
                        The total number of re-transmission packets on the ESSID
                         uplink channel of wireless side.
            "
        ::= { wlsxWlanESSIDStatsEntry 3 }

        wlanESSIDTxPkts OBJECT-TYPE
         SYNTAX       Counter32
         MAX-ACCESS   read-only
         STATUS       current
         DESCRIPTION
            "
                        The total number of packets on the ESSID downlink channel
                         of wireless side.
            "
        ::= { wlsxWlanESSIDStatsEntry 4 }

        wlanESSIDTxDroppedPkts OBJECT-TYPE
         SYNTAX       Counter32
         MAX-ACCESS   read-only
         STATUS       current
         DESCRIPTION
            "
                        The total number of dropped packets on the ESSID downlink
                         channel of wireless side.
            "
        ::= { wlsxWlanESSIDStatsEntry 5 }

        wlanESSIDTxRetryPkts OBJECT-TYPE
         SYNTAX       Counter32
         MAX-ACCESS   read-only
         STATUS       current
         DESCRIPTION
            "
                        The total number of re-transmission packets on the ESSID
                         downlink channel of wireless side.
            "
        ::= { wlsxWlanESSIDStatsEntry 6 }

        wlanESSIDTxErrorPkts OBJECT-TYPE
         SYNTAX       Counter32
         MAX-ACCESS   read-only
         STATUS       current
         DESCRIPTION
            "
                        The total number of error packets on the ESSID downlink
                         channel of wireless side.
            "
        ::= { wlsxWlanESSIDStatsEntry 7 }

        wlanESSIDRxRate OBJECT-TYPE
         SYNTAX       Gauge32
         MAX-ACCESS   read-only
         STATUS       current
         DESCRIPTION
            "
                        The data rate received from the ESSID in sampling interval,
                         unit is kbyte/s.
            "
        ::= { wlsxWlanESSIDStatsEntry 8 }

        wlanESSIDTxRate OBJECT-TYPE
         SYNTAX       Gauge32
         MAX-ACCESS   read-only
         STATUS       current
         DESCRIPTION
            "
                        The data rate transmitted from the ESSID in sampling interval,
                         unit is kbyte/s.
            "
        ::= { wlsxWlanESSIDStatsEntry 9 }

        wlanESSIDWiredRxPkts OBJECT-TYPE
         SYNTAX       Counter32
         MAX-ACCESS   read-only
         STATUS       current
         DESCRIPTION
            "
                        The total number of packets on the ESSID uplink
                         channel of wired side.
            "
        ::= { wlsxWlanESSIDStatsEntry 10 }

        wlanESSIDWiredRxBytes OBJECT-TYPE
         SYNTAX       Counter32
         MAX-ACCESS   read-only
         STATUS       current
         DESCRIPTION
            "
                        The total number of bytes on the ESSID uplink
                         channel of wireless side.
            "
        ::= { wlsxWlanESSIDStatsEntry 11 }

        wlanESSIDWiredTxBytes OBJECT-TYPE
         SYNTAX       Counter32
         MAX-ACCESS   read-only
         STATUS       current
         DESCRIPTION
            "
                        The total number of bytes on the ESSID downlink
                         channel of wireless side.
            "
        ::= { wlsxWlanESSIDStatsEntry 12 }

-- wlsxWlanEthStatsTable will contain all the statistics collected
-- for all ethernet ports

   wlsxWlanEthStatsTable  OBJECT-TYPE
          SYNTAX       SEQUENCE OF WlanEthStatsEntry
          MAX-ACCESS   not-accessible
      STATUS       current
      DESCRIPTION
                "
                        This Table lists statistics of all ethernet ports
                        of this controller.
                "
      ::= { wlsxWlanSwitchStatsGroup 2}

   wlsxWlanEthStatsEntry OBJECT-TYPE
          SYNTAX       WlanEthStatsEntry
          MAX-ACCESS   not-accessible
      STATUS       current
      DESCRIPTION
             "Ethernet Port Stats Entry"
          INDEX {ifIndex}
      ::= { wlsxWlanEthStatsTable 1 }

   WlanEthStatsEntry ::=
     SEQUENCE {
                 wlanEthRxRate                           Gauge32,
                 wlanEthTxRate                           Gauge32
   }

        wlanEthRxRate OBJECT-TYPE
         SYNTAX       Gauge32
         MAX-ACCESS   read-only
         STATUS       current
         DESCRIPTION
            "
                        The data rate received from the ethernet port in sampling interval,
                         unit is kbyte/s.
            "
        ::= { wlsxWlanEthStatsEntry 1 }

        wlanEthTxRate OBJECT-TYPE
         SYNTAX       Gauge32
         MAX-ACCESS   read-only
         STATUS       current
         DESCRIPTION
            "
                        The data rate transmitted from the ethernet port in sampling interval,
                         unit is kbyte/s.
            "
        ::= { wlsxWlanEthStatsEntry 2 }

-- wlsxSSIDConfigGroup contains all configuration related to
-- the SSID controlled by the controller.

-- wlsxSSIDConfigTable contains the global configuration of the SSID

   wlsxSSIDConfigTable  OBJECT-TYPE
          SYNTAX       SEQUENCE OF WlanSSIDConfigEntry
          MAX-ACCESS   not-accessible
      STATUS       current
      DESCRIPTION
                "
                        This Table lists the configuration of the SSID.
                        Note: Currently, this table doesn't return any data.
                "
      ::= { wlsxSSIDConfigGroup 1}

   wlsxSSIDConfigEntry OBJECT-TYPE
          SYNTAX       WlanSSIDConfigEntry
          MAX-ACCESS   not-accessible
      STATUS       current
      DESCRIPTION
             "AP Configuration Entry"
          INDEX {wlanAPMacAddress, wlanAPRadioNumber, wlanESSID, wlanESSIDIndex}
      ::= { wlsxSSIDConfigTable 1 }

   WlanSSIDConfigEntry ::=
     SEQUENCE {
                 wlanESSIDIndex                              Integer32,
                 wlanSSIDConfigHideSSID                      TruthValue,
                 wlanSSIDConfigNumStaAllowed                 Unsigned32,
                 wlanSSIDConfigWmmBeDscp                     Unsigned32,
                 wlanSSIDConfigWmmBkDscp                     Unsigned32,
                 wlanSSIDConfigWmmViDscp                     Unsigned32,
                 wlanSSIDConfigWmmVoDscp                     Unsigned32
   }

        wlanESSIDIndex OBJECT-TYPE
         SYNTAX       Integer32(1..16)
         MAX-ACCESS   not-accessible
         STATUS       current
         DESCRIPTION
            "
                        This attribute indicates the index of ESSID. We support up to 16 ESSIDs.
            "
        ::= { wlsxSSIDConfigEntry 1 }

        wlanSSIDConfigHideSSID OBJECT-TYPE
         SYNTAX       TruthValue
         MAX-ACCESS   read-only
         STATUS       current
         DESCRIPTION
            "
                        This attribute indicates if SSID is hidden or not.
            "
        ::= { wlsxSSIDConfigEntry 2 }

        wlanSSIDConfigNumStaAllowed OBJECT-TYPE
         SYNTAX       Unsigned32
         MAX-ACCESS   read-only
         STATUS       current
         DESCRIPTION
            "
                        This attribute indicates the maximum number of stations that are allowed to access into the network.
            "
        ::= { wlsxSSIDConfigEntry 3 }

        wlanSSIDConfigWmmBeDscp OBJECT-TYPE
         SYNTAX       Unsigned32
         MAX-ACCESS   read-only
         STATUS       current
         DESCRIPTION
            "
                        This attribute indicates the QoS priority of best-effort service.
            "
        ::= { wlsxSSIDConfigEntry 4 }

        wlanSSIDConfigWmmBkDscp OBJECT-TYPE
         SYNTAX       Unsigned32
         MAX-ACCESS   read-only
         STATUS       current
         DESCRIPTION
            "
                        This attribute indicates the QoS priority of background service.
            "
        ::= { wlsxSSIDConfigEntry 5 }

        wlanSSIDConfigWmmViDscp OBJECT-TYPE
         SYNTAX       Unsigned32
         MAX-ACCESS   read-only
         STATUS       current
         DESCRIPTION
            "
                        This attribute indicates the QoS priority of video service.
            "
        ::= { wlsxSSIDConfigEntry 6 }

        wlanSSIDConfigWmmVoDscp OBJECT-TYPE
         SYNTAX       Unsigned32
         MAX-ACCESS   read-only
         STATUS       current
         DESCRIPTION
            "
                        This attribute indicates the QoS priority of voice service.
            "
        ::= { wlsxSSIDConfigEntry 7 }

-- wlsxAPConfigGroup contains all configuration related to
-- the APs controlled by the controller.

-- wlsxAPConfigTable contains the global configuration of the AP

   wlsxAPConfigTable  OBJECT-TYPE
          SYNTAX       SEQUENCE OF WlanAPConfigEntry
          MAX-ACCESS   not-accessible
      STATUS       current
      DESCRIPTION
                "
                        This Table lists the configuration of the Access Point.
                "
      ::= { wlsxAPConfigGroup 1}

   wlsxAPConfigEntry OBJECT-TYPE
          SYNTAX       WlanAPConfigEntry
          MAX-ACCESS   not-accessible
      STATUS       current
      DESCRIPTION
             "AP Configuration Entry"
          INDEX {wlanAPMacAddress}
      ::= { wlsxAPConfigTable 1 }

   WlanAPConfigEntry ::=
     SEQUENCE {
                 wlanAPConfigNetmask                       IpAddress,
                 wlanAPConfigGateway                       IpAddress
   }

        wlanAPConfigNetmask OBJECT-TYPE
         SYNTAX       IpAddress
         MAX-ACCESS   read-only
         STATUS       current
         DESCRIPTION
            "
                        The netmask of AP IP Address.
            "
        ::= { wlsxAPConfigEntry 1 }

        wlanAPConfigGateway OBJECT-TYPE
         SYNTAX       IpAddress
         MAX-ACCESS   read-only
         STATUS       current
         DESCRIPTION
            "
                        The gateway of the AP.
            "
        ::= { wlsxAPConfigEntry 2 }

        --Trap Definition
         wlsxRAPActiveUplink NOTIFICATION-TYPE
         OBJECTS {wlanAPActiveUplink, wlanAPMacAddress}
         STATUS  current
         DESCRIPTION
                         "A trap which indicates the RAP Active Uplink"
         ::= { wlsxRAPTraps 1 }
END
